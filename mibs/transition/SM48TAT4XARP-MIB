-- *****************************************************************
-- SM48TAT4XARP-MIB
-- *****************************************************************

SM48TAT4XARP-MIB DEFINITIONS ::= BEGIN

IMPORTS
    DisplayString,MacAddress,TEXTUAL-CONVENTION,RowStatus                                              FROM SNMPv2-TC
    MODULE-COMPLIANCE,OBJECT-GROUP, NOTIFICATION-GROUP                                                 FROM SNMPv2-CONF
    ifIndex                                                                                            FROM IF-MIB
    enterprises,MODULE-IDENTITY,OBJECT-TYPE,NOTIFICATION-TYPE,Unsigned32,Integer32,Counter32,Counter64,IpAddress  FROM SNMPv2-SMI
--  PortList                                                                                           FROM Q-BRIDGE-MIB
    InetAddress, InetAddressType                                                                       FROM INET-ADDRESS-MIB
    OwnerString                                                                                        FROM RMON-MIB
    sysObjectID                                                                                        FROM SNMPv2-MIB
    SnmpAdminString                                                                                    FROM SNMP-FRAMEWORK-MIB;
--  MacAddress FROM BRIDGE-MIB;

transition MODULE-IDENTITY
        LAST-UPDATED "202112300214Z"
        ORGANIZATION "Corp."
        CONTACT-INFO
            " "
        DESCRIPTION "Managed PoE+ Switch, 48-port 10/100/1000Base-T PoE Plus + (4) 1G/10G SFP+ slots"
        REVISION      "202112300214Z"
        DESCRIPTION   "Rev 1.0 Initial version."
        ::= { enterprises 868 }


-- =======================================================================================================================

     OperState ::= TEXTUAL-CONVENTION
       STATUS         current
       DESCRIPTION
                      "Oper state."
       SYNTAX         INTEGER  { up ( 1 ) , down ( 2 ) }

     AdminMode ::= TEXTUAL-CONVENTION
       STATUS      current
       DESCRIPTION
            "The Admin state - default: disable(0)."
       SYNTAX  INTEGER { disable(0), enable(1) }

     AdminMode2 ::= TEXTUAL-CONVENTION
       STATUS      current
       DESCRIPTION
            "The Admin state - default: disable(0)."
       SYNTAX  INTEGER { disable(0), enable(1), notSupported(2) }

     ActivateCmd ::= TEXTUAL-CONVENTION
       STATUS      current
       DESCRIPTION
            "Used to activate commands. default: noAction(0). "
       SYNTAX         INTEGER  {  noAction ( 0 ),
                                  activate ( 1 )
                               }

     KeyType ::= TEXTUAL-CONVENTION
       STATUS      current
       DESCRIPTION
           "The key type specifying the key generated for frames received
            on the port.
            0 : Normal,
            1 : Double Tag,
            2 : IP Address,
            3 : MAC and IP Address."
        SYNTAX      INTEGER  { normal  ( 0 ),
                               doubleTag ( 1 ),
                               ipAddr ( 2 ),
                               macAndIpAddr ( 3 )
                             }

     FrameRate ::= TEXTUAL-CONVENTION
       STATUS      current
       DESCRIPTION
           "The values for frame rate"
       SYNTAX       INTEGER {
                            threeHundredFramesPerSec (0),
                            oneHundredFramesPerSec (1),
                            tenFramesPerSec (2),
                            oneFramePerSec (3),
                            sixFramesPerMin (4),
                            oneFramePerMin  (5),
                            sixFramesPerHour (6)
                            }

     DayOfWeek ::= TEXTUAL-CONVENTION
       STATUS      current
       DESCRIPTION
            "Used to set the days of the week."
       SYNTAX       INTEGER {mon(1),tue(2),wed(3),thur(4),
                             fri(5),sat(6),sun(7) }

     Month ::= TEXTUAL-CONVENTION
       STATUS      current
       DESCRIPTION
            "Used to set the month."
       SYNTAX       INTEGER {jan(1),feb(2),march(3),april(4),
                             may(5),june(6),july(7),aug(8),
                             sept(9),oct(10),nov(11),dec(12)}


switch                                                            OBJECT IDENTIFIER ::= { transition 2 }

sm48tat4xarpProductLevel1                                         OBJECT IDENTIFIER ::= { switch 77 }
sm48tat4xarpProductId                                             OBJECT IDENTIFIER ::= { sm48tat4xarpProductLevel1 4 }

sm48tat4xarpSystem                                                OBJECT IDENTIFIER ::= { sm48tat4xarpProductId 1 }

sm48tat4xarpSystemInformation                                     OBJECT IDENTIFIER ::= { sm48tat4xarpSystem 1 }

sm48tat4xarpSystemInfo                                            OBJECT IDENTIFIER ::= { sm48tat4xarpSystemInformation 1 }

sm48tat4xarpSystemInfoModelName OBJECT-TYPE
   SYNTAX       DisplayString
   MAX-ACCESS   read-only
   STATUS       current
   DESCRIPTION
       " "
   ::= { sm48tat4xarpSystemInfo 2 }

sm48tat4xarpSystemInfoSystemDescript OBJECT-TYPE
   SYNTAX       DisplayString
   MAX-ACCESS   read-only
   STATUS       current
   DESCRIPTION
       " "
   ::= { sm48tat4xarpSystemInfo 3 }

sm48tat4xarpSystemInfoLocation OBJECT-TYPE
   SYNTAX       DisplayString
   MAX-ACCESS   read-write
   STATUS       current
   DESCRIPTION
       " "
   ::= { sm48tat4xarpSystemInfo 4 }

sm48tat4xarpSystemInfoContact OBJECT-TYPE
   SYNTAX       DisplayString
   MAX-ACCESS   read-write
   STATUS       current
   DESCRIPTION
       " "
   ::= { sm48tat4xarpSystemInfo 5 }

sm48tat4xarpSystemInfoSystemName OBJECT-TYPE
   SYNTAX       DisplayString
   MAX-ACCESS   read-write
   STATUS       current
   DESCRIPTION
       " "
   ::= { sm48tat4xarpSystemInfo 6 }

sm48tat4xarpSystemInfoSystemDate OBJECT-TYPE
   SYNTAX       DisplayString
   MAX-ACCESS   read-only
   STATUS       current
   DESCRIPTION
       " "
   ::= { sm48tat4xarpSystemInfo 7 }

sm48tat4xarpSystemInfoSystemUptime OBJECT-TYPE
   SYNTAX       DisplayString
   MAX-ACCESS   read-only
   STATUS       current
   DESCRIPTION
       " "
   ::= { sm48tat4xarpSystemInfo 8 }

sm48tat4xarpSystemInfoBootloaderVersion OBJECT-TYPE
   SYNTAX       DisplayString
   MAX-ACCESS   read-only
   STATUS       current
   DESCRIPTION
       " "
   ::= { sm48tat4xarpSystemInfo 9 }

sm48tat4xarpSystemInfoFirmwareVersion OBJECT-TYPE
   SYNTAX       DisplayString
   MAX-ACCESS   read-only
   STATUS       current
   DESCRIPTION
       " "
   ::= { sm48tat4xarpSystemInfo 10 }

sm48tat4xarpSystemInfoHardwareVersion OBJECT-TYPE
   SYNTAX       DisplayString
   MAX-ACCESS   read-only
   STATUS       current
   DESCRIPTION
       " "
   ::= { sm48tat4xarpSystemInfo 11 }

sm48tat4xarpSystemInfoMechanicalVersion OBJECT-TYPE
   SYNTAX       DisplayString
   MAX-ACCESS   read-only
   STATUS       current
   DESCRIPTION
       " "
   ::= { sm48tat4xarpSystemInfo 12 }

sm48tat4xarpSystemInfoSeriesNumber OBJECT-TYPE
   SYNTAX       DisplayString
   MAX-ACCESS   read-only
   STATUS       current
   DESCRIPTION
       " "
   ::= { sm48tat4xarpSystemInfo 13 }

sm48tat4xarpSystemInfoHostMACAddress OBJECT-TYPE
   SYNTAX       DisplayString
   MAX-ACCESS   read-only
   STATUS       current
   DESCRIPTION
       " "
   ::= { sm48tat4xarpSystemInfo 14 }

-- sm48tat4xarpSystemInfoMemory OBJECT-TYPE
--   SYNTAX       DisplayString
--   MAX-ACCESS   read-only
--   STATUS       current
--   DESCRIPTION
--       " "
--   ::= { sm48tat4xarpSystemInfo 15 }

-- sm48tat4xarpSystemInfoFlash OBJECT-TYPE
--   SYNTAX       DisplayString
--   MAX-ACCESS   read-only
--   STATUS       current
--   DESCRIPTION
--       " "
--   ::= { sm48tat4xarpSystemInfo 16 }

sm48tat4xarpSystemInfoFanSpeed OBJECT-TYPE
   SYNTAX       DisplayString
   MAX-ACCESS   read-only
   STATUS       current
   DESCRIPTION
       "Fan Speed"
   ::= { sm48tat4xarpSystemInfo 17 }

-- sm48tat4xarpSystemInfoPowerStatus OBJECT-TYPE
--   SYNTAX       DisplayString
--   MAX-ACCESS   read-only
--   STATUS       current
--   DESCRIPTION
--       " "
--   ::= { sm48tat4xarpSystemInfo 19 }

-- sm48tat4xarpSystemInfoPowers OBJECT-TYPE
--   SYNTAX       DisplayString
--   MAX-ACCESS   read-only
--   STATUS       current
--   DESCRIPTION
--       " "
--   ::= { sm48tat4xarpSystemInfo 20 }

-- sm48tat4xarpSystemInfoTemperatureStatus OBJECT-TYPE
--   SYNTAX       DisplayString
--   MAX-ACCESS   read-only
--   STATUS       current
--   DESCRIPTION
--       " "
--   ::= { sm48tat4xarpSystemInfo 21 }

--sm48tat4xarpSystemInfoTemperature1 OBJECT-TYPE
--   SYNTAX       DisplayString
--   MAX-ACCESS   read-only
--   STATUS       current
--   DESCRIPTION
--       " "
--   ::= { sm48tat4xarpSystemInfo 22 }

--sm48tat4xarpSystemInfoTemperature2 OBJECT-TYPE
--   SYNTAX       DisplayString
--   MAX-ACCESS   read-only
--   STATUS       current
--   DESCRIPTION
--       " "
--   ::= { sm48tat4xarpSystemInfo 23 }

sm48tat4xarpSystemInfoCPULoad OBJECT-TYPE
   SYNTAX       DisplayString
   MAX-ACCESS   read-only
   STATUS       current
   DESCRIPTION
       "CPU Utilization."
   ::= { sm48tat4xarpSystemInfo 24 }

sm48tat4xarpSystemInfoPoEFirmwareVersion OBJECT-TYPE
   SYNTAX       DisplayString
   MAX-ACCESS   read-only
   STATUS       current
   DESCRIPTION
       " "
   ::= { sm48tat4xarpSystemInfo 32 }

-- sm48tat4xarpSystemInfoProductionDate OBJECT-TYPE
--    SYNTAX       DisplayString
--    MAX-ACCESS   read-only
--    STATUS       current
--    DESCRIPTION
--        "Production Date."
--    ::= { sm48tat4xarpSystemInfo 33 }

sm48tat4xarpPowerInformation    OBJECT IDENTIFIER ::= { sm48tat4xarpSystemInformation 2 }

sm48tat4xarpPowerInfoDetectedPSUA OBJECT-TYPE
   SYNTAX      DisplayString
   MAX-ACCESS  read-only
   STATUS      current
   DESCRIPTION
       "Is the power supply unit present. "
   ::= {sm48tat4xarpPowerInformation 2 }

sm48tat4xarpPowerInfoDetectedPSUB OBJECT-TYPE
   SYNTAX      DisplayString
   MAX-ACCESS  read-only
   STATUS      current
   DESCRIPTION
       "Is the power supply unit present. "
   ::= {sm48tat4xarpPowerInformation 3 }

sm48tat4xarpPowerInfoPowerGoodA OBJECT-TYPE
   SYNTAX      DisplayString
   MAX-ACCESS  read-only
   STATUS      current
   DESCRIPTION
       "The status of power supply unit. "
   ::= {sm48tat4xarpPowerInformation 4 }

sm48tat4xarpPowerInfoPowerGoodB OBJECT-TYPE
   SYNTAX      DisplayString
   MAX-ACCESS  read-only
   STATUS      current
   DESCRIPTION
       "The status of power supply unit. "
   ::= {sm48tat4xarpPowerInformation 5 }

sm48tat4xarpPowerInfoFANSpeedA OBJECT-TYPE
   SYNTAX      Integer32
   MAX-ACCESS  read-only
   STATUS      current
   DESCRIPTION
       "The fan speed of power supply unit. "
   ::= {sm48tat4xarpPowerInformation 6 }

sm48tat4xarpPowerInfoFANSpeedB OBJECT-TYPE
   SYNTAX      Integer32
   MAX-ACCESS  read-only
   STATUS      current
   DESCRIPTION
       "The fan speed of power supply unit. "
   ::= {sm48tat4xarpPowerInformation 7 }

sm48tat4xarpPowerInfoTemperatureA OBJECT-TYPE
   SYNTAX      Integer32
   MAX-ACCESS  read-only
   STATUS      current
   DESCRIPTION
       "The temperature of power supply unit. "
   ::= {sm48tat4xarpPowerInformation 8 }

sm48tat4xarpPowerInfoTemperatureB OBJECT-TYPE
   SYNTAX      Integer32
   MAX-ACCESS  read-only
   STATUS      current
   DESCRIPTION
       "The temperature of power supply unit. "
   ::= {sm48tat4xarpPowerInformation 9 }

sm48tat4xarpPowerInfoOperatingMode OBJECT-TYPE
   SYNTAX      Integer32 (0|1)
   MAX-ACCESS  read-write
   STATUS      current
   DESCRIPTION
       "The operating mode of power supply unit.
       0:Boost
       1:Redundant"
   ::= {sm48tat4xarpPowerInformation 10 }

sm48tat4xarpSystemTimeConf                                    OBJECT IDENTIFIER ::= { sm48tat4xarpSystem 2 }

-- sm48tat4xarpSystemNTP                                      OBJECT IDENTIFIER ::= { sm48tat4xarpSystemTimeConf  1 }

sm48tat4xarpSystemTime                                      OBJECT IDENTIFIER ::= { sm48tat4xarpSystemTimeConf  2 }
sm48tat4xarpSystemTimeZone                              OBJECT IDENTIFIER ::= { sm48tat4xarpSystemTime 1 }
sm48tat4xarpSystemTimeDaylightSaving             OBJECT IDENTIFIER ::= { sm48tat4xarpSystemTime 2 }
sm48tat4xarpSystemTimeConfiguration              OBJECT IDENTIFIER ::= { sm48tat4xarpSystemTime 3 }

    --
-- =======================================================================================================================
-- Objects in the sm48tat4xarpSystemNTP Group
-- =======================================================================================================================
--    sm48tat4xarpSystemNTPMode OBJECT-TYPE
--               SYNTAX       INTEGER {useLocal(0),useNTP(1)}
--               MAX-ACCESS   read-write
--               STATUS       current
--               DESCRIPTION
--                   "The system NTP Mode.
--                    useLocal(0) : Use Local Settings,
--                    useNTP(1)   : Use NTP Server."
--               DEFVAL  { useLocal }
--               ::= {     sm48tat4xarpSystemNTP 1 }
--
--    sm48tat4xarpSystemNTPServer1    OBJECT-TYPE
--               SYNTAX            DisplayString
--               MAX-ACCESS        read-write
--               STATUS            current
--               DESCRIPTION
--                   "Get/Set the NTP Time Server1.
--                    You can use the IP address or domain name."
--               ::= {     sm48tat4xarpSystemNTP 2 }
--
--    sm48tat4xarpSystemNTPServer2    OBJECT-TYPE
--               SYNTAX            DisplayString
--               MAX-ACCESS        read-write
--               STATUS            current
--               DESCRIPTION
--                   "Get/Set the NTP Time Server2.
--                    You can use the IP address or domain name."
--               ::= {     sm48tat4xarpSystemNTP 3 }
--
--    sm48tat4xarpSystemNTPServer3    OBJECT-TYPE
--               SYNTAX            DisplayString
--               MAX-ACCESS        read-write
--               STATUS            current
--               DESCRIPTION
--                   "Get/Set the NTP Time Server3.
--                    You can use the IP address or domain name."
--               ::= {     sm48tat4xarpSystemNTP 4 }
--
--    sm48tat4xarpSystemNTPServer4    OBJECT-TYPE
--               SYNTAX            DisplayString
--               MAX-ACCESS        read-write
--               STATUS            current
--               DESCRIPTION
--                   "Get/Set the NTP Time Server4.
--                    You can use the IP address or domain name."
--               ::= {     sm48tat4xarpSystemNTP 5 }
--
--    sm48tat4xarpSystemNTPServer5    OBJECT-TYPE
--               SYNTAX            DisplayString
--               MAX-ACCESS        read-write
--               STATUS            current
--               DESCRIPTION
--                   "Get/Set the NTP Time Server5.
--                    You can use the IP address or domain name."
--               ::= {     sm48tat4xarpSystemNTP 6 }


--
-- =======================================================================================================================
-- Objects in the sm48tat4xarpSystemTime Group
-- =======================================================================================================================
--sm48tat4xarpSystemTimeZone

    sm48tat4xarpSystemTimeZoneConf OBJECT-TYPE
               SYNTAX       Integer32(-7200..7201)
               MAX-ACCESS   read-write
               STATUS       current
               DESCRIPTION
                   "Get/Set the NTP Time Zone.
                    The value range is between -7200 and 7201 (minutes).
                    0 : None.
                    -7200 : (GMT-12:00).
                    -6600 : (GMT-11:00).
                    -6000 : (GMT-10:00).
                    -5400 : (GMT-09:00).
                    -4800 : (GMT-08:00)Pacific Time.
                    -4801 : (GMT-08:00)Tijuana, Baja California.
                    -4200 : (GMT-07:00)Arizona.
                    -4201 : (GMT-07:00)Chihuahua, La Paz, Mazatlan - New.
                    -4202 : (GMT-07:00)Chihuahua, La Paz, Mazatlan - Old.
                    -4203 : (GMT-07:00)Mountain Time.
                    -3600 : (GMT-06:00)Central America.
                    -3601 : (GMT-06:00)Central Time.
                    -3602 : (GMT-06:00)Guadalajara, Mexico City, Monterrey - New.
                    -3603 : (GMT-06:00)Guadalajara, Mexico City, Monterrey - Old.
                    -3604 : (GMT-06:00)Saskatchewan.
                    -3000 : (GMT-05:00)Bogota, Lima, Quito, Rio Branco.
                    -3001 : (GMT-05:00)Eastern Time.
                    -3002 : (GMT-05:00)Indiana.
                    -2700 : (GMT-04:30).
                    -2400 : (GMT-04:00)Atlantic Time.
                    -2401 : (GMT-04:00)La Paz.
                    -2402 : (GMT-04:00)Manaus.
                    -2403 : (GMT-04:00)Santiago.
                    -2100 : (GMT-03:30).
                    -1800 : (GMT-03:00)Brasilia.
                    -1801 : (GMT-03:00)Buenos Aires.
                    -1802 : (GMT-03:00)Georgetown.
                    -1803 : (GMT-03:00)Greenland.
                    -1804 : (GMT-03:00)Montevideo.
                    -1805 : (GMT-02:00).
                    -600 : (GMT-01:00)Azores.
                    -601 : (GMT-01:00)Cape Verde Is.
                    1 : (GMT) Casablanca.
                    2 : (GMT) Greenwich Mean Time.
                    3 : (GMT) Monrovia, Reykjavik.
                    600 : (GMT+01:00) Amsterdam, Berlin, Bern, Rome, Stockholm, Vienna.
                    601 : (GMT+01:00) Belgrade, Bratislava, Budapest, Ljubljana, Prague.
                    602 : (GMT+01:00) Brussels, Copenhagen, Madrid, Paris.
                    603 : (GMT+01:00) Sarajevo, Skopje, Warsaw, Zagreb.
                    604 : (GMT+01:00) West Central Africa.
                    1200 : (GMT+02:00) Amman.
                    1201 : (GMT+02:00) Athens, Bucharest, Istanbul.
                    1202 : (GMT+02:00) Beirut.
                    1203 : (GMT+02:00) Cairo.
                    1204 : (GMT+02:00) Harare, Pretoria.
                    1205 : (GMT+02:00) Helsinki, Kyiv, Riga, Sofia, Tallinn, Vilnius.
                    1206 : (GMT+02:00) Jerusalem.
                    1207 : (GMT+02:00) Minsk.
                    1208 : (GMT+02:00) Windhoek.
                    1800 : (GMT+03:00) Baghdad.
                    1801 : (GMT+03:00) Kuwait, Riyadh.
                    1802 : (GMT+03:00) Moscow, St. Petersburg, Volgograd.
                    1803 : (GMT+03:00) Nairobi.
                    1804 : (GMT+03:00) Tbilisi.
                    2100 : (GMT+03:30) Tehran.
                    2400 : (GMT+04:00) Abu Dhabi, Muscat.
                    2401 : (GMT+04:00) Baku.
                    2402 : (GMT+04:00) Caucasus Standard Time.
                    2403 : (GMT+04:00) Port Louis.
                    2404 : (GMT+04:00) Yerevan.
                    2700 : (GMT+04:30) Kabul.
                    3000 : (GMT+05:00) Ekaterinburg.
                    3001 : (GMT+05:00) Islamabad, Karachi.
                    3002 : (GMT+05:00) Tashkent.
                    3300 : (GMT+05:30) Chennai, Kolkata, Mumbai, New Delhi.
                    3301 : (GMT+05:30) Sri Jayawardenepura.
                    3455 : (GMT+05:45) Kathmandu.
                    3600 : (GMT+06:00) Almaty, Novosibirsk.
                    3601 : (GMT+06:00) Astana, Dhaka.
                    3600 : (GMT+06:30) Yangon (Rangoon).
                    4200 : (GMT+07:00) Bangkok, Hanoi, Jakarta.
                    4201 : (GMT+07:00) Krasnoyarsk.
                    4800 : (GMT+08:00) Beijing, Chongqing, Hong Kong, Urumqi.
                    4801 : (GMT+08:00) Irkutsk, Ulaan Bataar.
                    4802 : (GMT+08:00) Kuala Lumpur, Singapore.
                    4803 : (GMT+08:00) Perth.
                    4804 : (GMT+08:00) Taipei.
                    5400 : (GMT+09:00) Osaka, Sapporo, Tokyo.
                    5401 : (GMT+09:00) Seoul.
                    5402 : (GMT+09:00) Yakutsk.
                    5700 : (GMT+09:30) Adelaide.
                    5701 : (GMT+09:30) Darwin.
                    6000 : (GMT+10:00) Brisbane.
                    6001 : (GMT+10:00) Canberra, Melbourne, Sydney.
                    6002 : (GMT+10:00) Guam, Port Moresby.
                    6003 : (GMT+10:00) Hobart.
                    6004 : (GMT+10:00) Vladivostok.
                    6600 : (GMT+11:00) Magadan, Solomon Is., New Caledonia.
                    7200 : (GMT+12:00) Auckland, Wellington.
                    7201 : (GMT+12:00) Fiji, Kamchatka, Marshall Is."
               ::= {     sm48tat4xarpSystemTimeZone 1 }

    sm48tat4xarpSystemTimeZoneAcronym OBJECT-TYPE
               SYNTAX       DisplayString
               MAX-ACCESS   read-write
               STATUS       current
               DESCRIPTION
                   "Acronym - User can set the acronym of the time zone.
                    This is a User configurable acronym to identify the time zone.
                    Range : 0 - 16 characters."
               ::= {     sm48tat4xarpSystemTimeZone 2 }

--sm48tat4xarpSystemTimeDaylightSaving

    sm48tat4xarpSystemTimeDaylightSavingMode OBJECT-TYPE
               SYNTAX       INTEGER { disable(0), recurring(1), nonRecurring(2) }
               MAX-ACCESS   read-write
               STATUS       current
               DESCRIPTION
                   "The system Daylight Savings Mode.
                    disable(0)   : Disable.
                    recurring(1) : Recurring
                        - configure the Daylight Saving Time duration
                        to repeat the configuration every year.
                    nonRecurring(2): Non-Recurring - configure the Daylight Saving Time
                        duration for single time configuration."
               DEFVAL  { disable }
               ::= {     sm48tat4xarpSystemTimeDaylightSaving 1 }

    sm48tat4xarpSystemTimeDaylightSavingStartWeek OBJECT-TYPE
               SYNTAX       DisplayString
               MAX-ACCESS   read-write
               STATUS       current
               DESCRIPTION
                   "Start time Week. Use in Recurring Mode.
                    Range : 1 - 5.
                    Default : 1."
               ::= {     sm48tat4xarpSystemTimeDaylightSaving 2 }

    sm48tat4xarpSystemTimeDaylightSavingStartDay OBJECT-TYPE
               SYNTAX       DayOfWeek
               MAX-ACCESS   read-write
               STATUS       current
               DESCRIPTION
                   "Start time Day. Use in Recurring Mode."
               DEFVAL  { mon }
               ::= {     sm48tat4xarpSystemTimeDaylightSaving 3 }

    sm48tat4xarpSystemTimeDaylightSavingStartMonth OBJECT-TYPE
               SYNTAX       Month
               MAX-ACCESS   read-write
               STATUS       current
               DESCRIPTION
                   "Start time Month."
               DEFVAL  { jan }
               ::= {     sm48tat4xarpSystemTimeDaylightSaving 4 }

    sm48tat4xarpSystemTimeDaylightSavingStartDate OBJECT-TYPE
               SYNTAX       Integer32 (1..31)
               MAX-ACCESS   read-write
               STATUS       current
               DESCRIPTION
                   "Start time Date. Use in Non-Recurring Mode.
                    Range : 1 - 31.
                    Default : 1."
               ::= {     sm48tat4xarpSystemTimeDaylightSaving 5 }

    sm48tat4xarpSystemTimeDaylightSavingStartYear OBJECT-TYPE
               SYNTAX       Integer32 (2000..2097)
               MAX-ACCESS   read-write
               STATUS       current
               DESCRIPTION
                   "Start time Year. Use in Non-Recurring Mode.
                    Range : 2000 - 2097.
                    Default : 2000."
               ::= {     sm48tat4xarpSystemTimeDaylightSaving 6 }

    sm48tat4xarpSystemTimeDaylightSavingStartHours OBJECT-TYPE
               SYNTAX       Integer32 (0..23)
               MAX-ACCESS   read-write
               STATUS       current
               DESCRIPTION
                   "Start time Hours.
                     Range : 0 - 23.
                     Default : 0."
               ::= {     sm48tat4xarpSystemTimeDaylightSaving 7 }

    sm48tat4xarpSystemTimeDaylightSavingStartMinutes OBJECT-TYPE
               SYNTAX       Integer32 (0..59)
               MAX-ACCESS   read-write
               STATUS       current
               DESCRIPTION
                   "Start time Minutes.
                    Range : 0 - 59.
                    Default : 0."
               ::= {     sm48tat4xarpSystemTimeDaylightSaving 8 }

    sm48tat4xarpSystemTimeDaylightSavingEndWeek OBJECT-TYPE
               SYNTAX       DisplayString
               MAX-ACCESS   read-write
               STATUS       current
               DESCRIPTION
                   "End time Week. Use in Recurring Mode.
                    Range : 1 - 5.
                    Default : 1."
               ::= {     sm48tat4xarpSystemTimeDaylightSaving 9 }

    sm48tat4xarpSystemTimeDaylightSavingEndDay OBJECT-TYPE
               SYNTAX       DayOfWeek
               MAX-ACCESS   read-write
               STATUS       current
               DESCRIPTION
                   "End time Day. Use in Recurring Mode."
               DEFVAL  { mon }
               ::= {     sm48tat4xarpSystemTimeDaylightSaving 10 }

    sm48tat4xarpSystemTimeDaylightSavingEndMonth OBJECT-TYPE
               SYNTAX       Month
               MAX-ACCESS   read-write
               STATUS       current
               DESCRIPTION
                   "End time Month."
              DEFVAL  { jan }
              ::= {     sm48tat4xarpSystemTimeDaylightSaving 11 }

    sm48tat4xarpSystemTimeDaylightSavingEndDate OBJECT-TYPE
               SYNTAX       Integer32 (1..31)
               MAX-ACCESS   read-write
               STATUS       current
               DESCRIPTION
                   "End time Date. Use in Non-Recurring Mode.
                    Range : 1 - 31.
                    Default : 1."
               ::= {     sm48tat4xarpSystemTimeDaylightSaving 12 }

    sm48tat4xarpSystemTimeDaylightSavingEndYear OBJECT-TYPE
               SYNTAX       Integer32 (2000..2097)
               MAX-ACCESS   read-write
               STATUS       current
               DESCRIPTION
                   "End time Year. Use in Non-Recurring Mode.
                    Range : 2000 - 2097.
                    Default : 2000."
               ::= {     sm48tat4xarpSystemTimeDaylightSaving 13 }

    sm48tat4xarpSystemTimeDaylightSavingEndHours OBJECT-TYPE
               SYNTAX       Integer32 (0..23)
               MAX-ACCESS   read-write
               STATUS       current
               DESCRIPTION
                   "End time Hours.
                    Range : 0 - 23.
                    Default : 0."
               ::= {     sm48tat4xarpSystemTimeDaylightSaving 14 }

    sm48tat4xarpSystemTimeDaylightSavingEndMinutes OBJECT-TYPE
               SYNTAX       Integer32 (0..59)
               MAX-ACCESS   read-write
               STATUS       current
               DESCRIPTION
                   "End time Minutes.
                    Range : 0 - 59.
                    Default : 0."
               ::= {     sm48tat4xarpSystemTimeDaylightSaving 15 }

    sm48tat4xarpSystemTimeDaylightSavingOffset OBJECT-TYPE
               SYNTAX       Integer32 (1..1440)
               MAX-ACCESS   read-write
               STATUS       current
               DESCRIPTION
                   "Offset - the number of minutes to add during Daylight Saving Time.
                    Range : 1 - 1440(Minutes).
                    Default : 1."
               ::= {     sm48tat4xarpSystemTimeDaylightSaving 16 }

    sm48tat4xarpSystemTimeConfigurationClockSource OBJECT-TYPE
               SYNTAX       Integer32
               MAX-ACCESS   read-write
               STATUS       current
               DESCRIPTION
                   "0:Use Local Settings.
                    1:Use NTP Server."
	           ::= {     sm48tat4xarpSystemTimeConfiguration 1}

    sm48tat4xarpSystemTimeConfigurationSystemDate OBJECT-TYPE
               SYNTAX       DisplayString
               MAX-ACCESS   read-write
               STATUS       current
               DESCRIPTION
                   "System date. Default format:yyyy-mm-dd.
                    When ClockSource is Use Local Settings, you can set this field."
	           ::= {     sm48tat4xarpSystemTimeConfiguration 2}

    sm48tat4xarpSystemTimeConfigurationDateFormat OBJECT-TYPE
               SYNTAX       Integer32 (0|1|2)
               MAX-ACCESS   read-write
               STATUS       current
               DESCRIPTION
                   "The date format of the system.
				   0:yyyy-mm-dd
				   1:mm-dd-yyyy
				   2:dd-mm-yyyy"
	           ::= {     sm48tat4xarpSystemTimeConfiguration 3}

    sm48tat4xarpSystemTimeConfigurationTimeFormat OBJECT-TYPE
               SYNTAX       Integer32 (0|1)
               MAX-ACCESS   read-write
               STATUS       current
               DESCRIPTION
                   "The time format of the system.
				   0:24-hr, format:hh:mm:ss
				   1:12-hr, format:hh:mm:ss am/pm"
	           ::= {     sm48tat4xarpSystemTimeConfiguration 4}

    sm48tat4xarpSystemTimeConfigurationSystemTime OBJECT-TYPE
               SYNTAX       DisplayString
               MAX-ACCESS   read-write
               STATUS       current
               DESCRIPTION
                   "System date.
				    24-hr, format:hh:mm:ss
				    12-hr, format:hh:mm:ss am/pm
                    When ClockSource is Use Local Settings, you can set this field."
	           ::= {     sm48tat4xarpSystemTimeConfiguration 5}

-- =======================================================================================================================
sm48tat4xarpSystemAccount                                         OBJECT IDENTIFIER ::= { sm48tat4xarpSystem 3 }

sm48tat4xarpSystemAccountUsers                                     OBJECT IDENTIFIER  ::= { sm48tat4xarpSystemAccount 1 }

--
-- =======================================================================================================================
-- Start sm48tat4xarpUserConfig group
-- =======================================================================================================================
--sm48tat4xarpUserConfigTable

    sm48tat4xarpUserConfigTable OBJECT-TYPE
               SYNTAX      SEQUENCE OF     SM48TAT4XARPUserConfigEntry
               MAX-ACCESS  not-accessible
               STATUS      current
               DESCRIPTION
                   "The User Config Table. "
               ::= {     sm48tat4xarpSystemAccountUsers 1 }

    sm48tat4xarpUserConfigEntry OBJECT-TYPE
               SYNTAX          SM48TAT4XARPUserConfigEntry
               MAX-ACCESS  not-accessible
               STATUS      current
               DESCRIPTION
                   "The User Config Entry."
               INDEX    {    sm48tat4xarpUserConfigIndex  }
               ::= {     sm48tat4xarpUserConfigTable 1 }

    SM48TAT4XARPUserConfigEntry             ::= SEQUENCE {
                 sm48tat4xarpUserConfigIndex            Integer32,
                 sm48tat4xarpUserConfigUserName         DisplayString,
                 sm48tat4xarpUserConfigPassword         DisplayString,
                 sm48tat4xarpUserConfigPrivilegeLevel   Integer32,
                 sm48tat4xarpUserConfigRowStatus        RowStatus
                }

    sm48tat4xarpUserConfigIndex OBJECT-TYPE
               SYNTAX      Integer32 (1..4095)
               MAX-ACCESS  not-accessible
               STATUS      current
               DESCRIPTION
                   "The user Config Index. "
               ::= {     sm48tat4xarpUserConfigEntry 1 }

    sm48tat4xarpUserConfigUserName OBJECT-TYPE
               SYNTAX      DisplayString(SIZE (1..31))
               MAX-ACCESS  read-create
               STATUS      current
               DESCRIPTION
                   "A string identifying the user name for the entry.
                    string length: 1-31. "
               ::= {     sm48tat4xarpUserConfigEntry 2 }

    sm48tat4xarpUserConfigPassword OBJECT-TYPE
               SYNTAX      DisplayString(SIZE (0..31))
               MAX-ACCESS  read-create
               STATUS      current
               DESCRIPTION
                   "The password of the user.
                    string length: 0-31. "
               ::= {     sm48tat4xarpUserConfigEntry 3 }

    sm48tat4xarpUserConfigPrivilegeLevel OBJECT-TYPE
               SYNTAX      Integer32(1..15)
               MAX-ACCESS  read-create
               STATUS      current
               DESCRIPTION
                   "The privilege level of the user.If the privilege level
                    value is 15, it can access all groups.range: 1-15. "
               ::= {     sm48tat4xarpUserConfigEntry 4 }

    sm48tat4xarpUserConfigRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sm48tat4xarpUserConfigEntry 5 }


--
-- =======================================================================================================================
-- Start sm48tat4xarpPrivilegeLevelConfig group
-- =======================================================================================================================
--sm48tat4xarpPrivilegeLevelConfigTable

    sm48tat4xarpPrivilegeLevelConfigTable OBJECT-TYPE
               SYNTAX      SEQUENCE OF     SM48TAT4XARPPrivilegeLevelConfigEntry
               MAX-ACCESS  not-accessible
               STATUS      current
               DESCRIPTION
                   "The Privilege Level Config Table. "
               ::= {     sm48tat4xarpSystemAccountUsers 2 }

    sm48tat4xarpPrivilegeLevelConfigEntry OBJECT-TYPE
               SYNTAX          SM48TAT4XARPPrivilegeLevelConfigEntry
               MAX-ACCESS  not-accessible
               STATUS      current
               DESCRIPTION
                   "The Privilege Level Config Entry."
               INDEX    {    sm48tat4xarpPrivilegeLevelIndex  }
               ::= {     sm48tat4xarpPrivilegeLevelConfigTable 1 }

    SM48TAT4XARPPrivilegeLevelConfigEntry             ::= SEQUENCE {
                 sm48tat4xarpPrivilegeLevelIndex                Integer32,
                 sm48tat4xarpPrivilegeLevelGroupName            DisplayString,
                 sm48tat4xarpPrivilegeLevelConfigReadOnly       Integer32,
                 sm48tat4xarpPrivilegeLevelConfigReadWrite      Integer32,
                 sm48tat4xarpPrivilegeLevelStatusReadOnly       Integer32,
                 sm48tat4xarpPrivilegeLevelStatusReadWrite      Integer32
                 }

    sm48tat4xarpPrivilegeLevelIndex OBJECT-TYPE
               SYNTAX      Integer32 (1..4095)
               MAX-ACCESS  not-accessible
               STATUS      current
               DESCRIPTION
                   "The Privilege Level Index. "
               ::= {     sm48tat4xarpPrivilegeLevelConfigEntry 1 }

    sm48tat4xarpPrivilegeLevelGroupName OBJECT-TYPE
               SYNTAX      DisplayString
               MAX-ACCESS  read-only
               STATUS      current
               DESCRIPTION
                   "The name identifying the privilege group."
               ::= {     sm48tat4xarpPrivilegeLevelConfigEntry 2 }

    sm48tat4xarpPrivilegeLevelConfigReadOnly OBJECT-TYPE
               SYNTAX      Integer32(1..15)
               MAX-ACCESS  read-write
               STATUS      current
               DESCRIPTION
                   "The privilege level of configuration read-only.If the
                    privilege level value is 15,it can access all groups.
                    range: 1-15.  "
               ::= {     sm48tat4xarpPrivilegeLevelConfigEntry 3 }

    sm48tat4xarpPrivilegeLevelConfigReadWrite OBJECT-TYPE
               SYNTAX      Integer32(1..15)
               MAX-ACCESS  read-write
               STATUS      current
               DESCRIPTION
                   "The privilege level of configuration/execute read/write.
                    If the privilege level value is 15,it can access all groups.
                    range: 1-15. "
               ::= {     sm48tat4xarpPrivilegeLevelConfigEntry 4 }

    sm48tat4xarpPrivilegeLevelStatusReadOnly OBJECT-TYPE
               SYNTAX      Integer32(1..15)
               MAX-ACCESS  read-write
               STATUS      current
               DESCRIPTION
                   "The privilege level of status/statistics read-only.
                    If the privilege level value is 15,it can access all groups.
                    range: 1-15. "
               ::= {     sm48tat4xarpPrivilegeLevelConfigEntry 5 }

    sm48tat4xarpPrivilegeLevelStatusReadWrite OBJECT-TYPE
               SYNTAX      Integer32(1..15)
               MAX-ACCESS  read-write
               STATUS      current
               DESCRIPTION
                   "The privilege level of status/statistics read-write.
                    If the privilege level value is 15,it can access all groups.
                    range: 1-15. "
               ::= {     sm48tat4xarpPrivilegeLevelConfigEntry 6 }
-- =======================================================================================================================

sm48tat4xarpIP                                                    OBJECT IDENTIFIER ::= { sm48tat4xarpSystem 4 }

sm48tat4xarpIPConfigurationBasic OBJECT IDENTIFIER ::= { sm48tat4xarpIP 1 }

sm48tat4xarpIPConfigIPv4DHCPClientEnable OBJECT-TYPE
   SYNTAX      Integer32 (0|1)
   MAX-ACCESS  read-write
   STATUS      current
   DESCRIPTION
       "IPv4 DHCP Client Enabled
        0: Disable
        1: Enable"
   ::= {sm48tat4xarpIPConfigurationBasic 1 }

sm48tat4xarpIPConfigIPv4Address OBJECT-TYPE
   SYNTAX      DisplayString
   MAX-ACCESS  read-write
   STATUS      current
   DESCRIPTION
       "IPv4 Address."
   ::= {sm48tat4xarpIPConfigurationBasic 2 }

sm48tat4xarpIPConfigSubnetMask OBJECT-TYPE
   SYNTAX      DisplayString
   MAX-ACCESS  read-write
   STATUS      current
   DESCRIPTION
       "IPv4 SubnetMask."
   ::= {sm48tat4xarpIPConfigurationBasic 3 }

sm48tat4xarpIPConfigGateway OBJECT-TYPE
   SYNTAX      DisplayString
   MAX-ACCESS  read-write
   STATUS      current
   DESCRIPTION
       "IPv4 Gateway."
   ::= {sm48tat4xarpIPConfigurationBasic 4 }

sm48tat4xarpIPConfigDNSServer OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sm48tat4xarpIPConfigurationBasic 5 }

sm48tat4xarpIPConfigDNSServerValue OBJECT-TYPE
   SYNTAX      DisplayString
   MAX-ACCESS  read-write
   STATUS      current
   DESCRIPTION
       "DNS IPv4 Address or VLAN value."
   ::= {sm48tat4xarpIPConfigurationBasic 6 }

sm48tat4xarpIPConfiguration OBJECT IDENTIFIER ::= { sm48tat4xarpIP 2 }

sm48tat4xarpMode OBJECT-TYPE
   SYNTAX      Integer32 (0|1)
   MAX-ACCESS  read-write
   STATUS      current
   DESCRIPTION
       "IP Configuration Mode.
        default:0
        0: Host
        1: Router"
   ::= {sm48tat4xarpIPConfiguration 2 }

sm48tat4xarpDNSServerSource1 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sm48tat4xarpIPConfiguration 3 }

sm48tat4xarpDNSServerSource2 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
		4. DNS configuration is derived from DHCPv6.
		5. DNS configuration is derived from DHCPv6 on specific VLAN.
		"
   ::= {sm48tat4xarpIPConfiguration 4 }

sm48tat4xarpDNSServerSource3 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sm48tat4xarpIPConfiguration 5 }

sm48tat4xarpDNSServerSource4 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sm48tat4xarpIPConfiguration 6 }

sm48tat4xarpDNSServerValue1 OBJECT-TYPE
   SYNTAX      DisplayString
   MAX-ACCESS  read-write
   STATUS      current
   DESCRIPTION
       "DNS IPv4/IPv6 Address or VLAN value."
   ::= {sm48tat4xarpIPConfiguration 7 }

sm48tat4xarpDNSServerValue2 OBJECT-TYPE
   SYNTAX      DisplayString
   MAX-ACCESS  read-write
   STATUS      current
   DESCRIPTION
      "DNS IPv4/IPv6 Address or VLAN value."
   ::= {sm48tat4xarpIPConfiguration 8 }

sm48tat4xarpDNSServerValue3 OBJECT-TYPE
   SYNTAX      DisplayString
   MAX-ACCESS  read-write
   STATUS      current
   DESCRIPTION
       "DNS IPv4/IPv6 Address or VLAN value."
   ::= {sm48tat4xarpIPConfiguration 9 }

sm48tat4xarpDNSServerValue4 OBJECT-TYPE
   SYNTAX      DisplayString
   MAX-ACCESS  read-write
   STATUS      current
   DESCRIPTION
       "DNS IPv4/IPv6 Address or VLAN value."
   ::= {sm48tat4xarpIPConfiguration 10 }

sm48tat4xarpDNSProxy OBJECT-TYPE
   SYNTAX      Integer32 (0|1)
   MAX-ACCESS  read-write
   STATUS      current
   DESCRIPTION
       "DNS Proxy enable/disable.
        default:0
        0: disable
        1: enable"
   ::= {sm48tat4xarpIPConfiguration 11 }


sm48tat4xarpIPInterfaces OBJECT IDENTIFIER ::= { sm48tat4xarpIP 3 }

sm48tat4xarpIPInterfacesDHCPPerPortMode OBJECT-TYPE
   SYNTAX      INTEGER { disable(0), enable(1) }
   MAX-ACCESS  read-write
   STATUS      current
   DESCRIPTION
       "The dhcp per-port mode for the interface.
        0: Disable,
        1: Enable,
        default: Disable. "
   ::= { sm48tat4xarpIPInterfaces 1 }

sm48tat4xarpIPInterfacesDHCPPerPortIPRangeLow OBJECT-TYPE
   SYNTAX      IpAddress
   MAX-ACCESS  read-write
   STATUS      current
   DESCRIPTION
       "The dhcp per-port ip low for the interface."
   ::= { sm48tat4xarpIPInterfaces 2 }

sm48tat4xarpIPInterfacesDHCPPerPortIPRangeHigh OBJECT-TYPE
   SYNTAX      IpAddress
   MAX-ACCESS  read-write
   STATUS      current
   DESCRIPTION
       "The dhcp per-port ip high for the interface."
   ::= { sm48tat4xarpIPInterfaces 3 }

sm48tat4xarpIPInterfacesDHCPPerPortApply OBJECT-TYPE
   SYNTAX      Integer32 (1)
   MAX-ACCESS  read-write
   STATUS      current
   DESCRIPTION
       "1: Apply DHCP Per Port settings."
   ::= { sm48tat4xarpIPInterfaces 4 }

sm48tat4xarpIPInterfacesDHCPPerPortVLAN OBJECT-TYPE
   SYNTAX      Integer32 (1..4095)
   MAX-ACCESS  read-write
   STATUS      current
   DESCRIPTION
       "dhcp per-port VLAN."
   ::= { sm48tat4xarpIPInterfaces 6 }

sm48tat4xarpIPInterfacesTable OBJECT-TYPE
   SYNTAX      SEQUENCE OF SM48TAT4XARPIPInterfacesEntry
   MAX-ACCESS  not-accessible
   STATUS      current
   DESCRIPTION
       "A table of IP interface for switch."
    ::= { sm48tat4xarpIPInterfaces 5 }

sm48tat4xarpIPInterfacesEntry OBJECT-TYPE
    SYNTAX        SM48TAT4XARPIPInterfacesEntry
    MAX-ACCESS    not-accessible
    STATUS        current
    DESCRIPTION
        "An entry in the sm48tat4xarpIPInterfacesTable."
    INDEX        { sm48tat4xarpIPInterfacesIndex }
    ::= { sm48tat4xarpIPInterfacesTable 1 }

SM48TAT4XARPIPInterfacesEntry ::=
    SEQUENCE {
        sm48tat4xarpIPInterfacesIndex                       Integer32,
        sm48tat4xarpIPInterfacesVLAN                        Integer32,
        sm48tat4xarpIPInterfacesIPv4DHCP                    Integer32,
        sm48tat4xarpIPInterfacesIPv4DHCPFallback            DisplayString,
        sm48tat4xarpIPInterfacesIPv4DHCPCurrentLease        IpAddress,
        sm48tat4xarpIPInterfacesIPv4Address                 IpAddress,
        sm48tat4xarpIPInterfacesIPv4Mask                    Integer32,
	sm48tat4xarpIPInterfacesIPv6DHCP                    Integer32,
	sm48tat4xarpIPInterfacesIPv6RapidCommit             Integer32,
	sm48tat4xarpIPInterfacesIPv6CurrentLease            DisplayString,
        sm48tat4xarpIPInterfacesIPv6Address                 DisplayString,
        sm48tat4xarpIPInterfacesIPv6Mask                    Integer32,
	sm48tat4xarpIPInterfacesRowStatus                   RowStatus
    }

sm48tat4xarpIPInterfacesIndex OBJECT-TYPE
   SYNTAX      Integer32 (1..128)
   MAX-ACCESS  not-accessible
   STATUS      current
   DESCRIPTION
       "interface table index"
   ::= {sm48tat4xarpIPInterfacesEntry 1 }

sm48tat4xarpIPInterfacesVLAN OBJECT-TYPE
   SYNTAX      Integer32 (1..4095)
   MAX-ACCESS  read-write
   STATUS      current
   DESCRIPTION
       "VLAN ID for interface, range: 1-4095."
   ::= {sm48tat4xarpIPInterfacesEntry 2 }

sm48tat4xarpIPInterfacesIPv4DHCP OBJECT-TYPE
   SYNTAX      Integer32 (0|1)
   MAX-ACCESS  read-write
   STATUS      current
   DESCRIPTION
       "IPv4 DHCP Setting for interface.
        default:0
        0: disable
        1: enable"
   ::= {sm48tat4xarpIPInterfacesEntry 3 }

sm48tat4xarpIPInterfacesIPv4DHCPFallback OBJECT-TYPE
   SYNTAX      DisplayString
   MAX-ACCESS  read-write
   STATUS      current
   DESCRIPTION
       "IPv4 DHCP fallbcak. range: 1-4294967295 seconds."
   ::= {sm48tat4xarpIPInterfacesEntry 4 }


sm48tat4xarpIPInterfacesIPv4DHCPCurrentLease OBJECT-TYPE
   SYNTAX      IpAddress
   MAX-ACCESS  read-only
   STATUS      current
   DESCRIPTION
       "IPv4 DHCP Current Lease Address for interface."
   ::= {sm48tat4xarpIPInterfacesEntry 5 }


sm48tat4xarpIPInterfacesIPv4Address OBJECT-TYPE
   SYNTAX      IpAddress
   MAX-ACCESS  read-write
   STATUS      current
   DESCRIPTION
       "IPv4 address for interface."
   ::= {sm48tat4xarpIPInterfacesEntry 6 }

sm48tat4xarpIPInterfacesIPv4Mask OBJECT-TYPE
   SYNTAX      Integer32 (1..32)
   MAX-ACCESS  read-write
   STATUS      current
   DESCRIPTION
       "IPv4 mask for interface."
   ::= { sm48tat4xarpIPInterfacesEntry 7 }

sm48tat4xarpIPInterfacesIPv6DHCP OBJECT-TYPE
   SYNTAX      Integer32 (0|1)
   MAX-ACCESS  read-write
   STATUS      current
   DESCRIPTION
       "IPv6 DHCP Setting for interface.
        default:0
        0: disable
        1: enable"
   ::= {sm48tat4xarpIPInterfacesEntry 8 }

sm48tat4xarpIPInterfacesIPv6RapidCommit OBJECT-TYPE
   SYNTAX      Integer32 (0|1)
   MAX-ACCESS  read-write
   STATUS      current
   DESCRIPTION
       "Enable the DHCPv6 Rapid-Commit option.
        default:0
        0: disable
        1: enable"
   ::= {sm48tat4xarpIPInterfacesEntry 9 }

sm48tat4xarpIPInterfacesIPv6CurrentLease OBJECT-TYPE
   SYNTAX      DisplayString
   MAX-ACCESS  read-only
   STATUS      current
   DESCRIPTION
       "IPv6 DHCP Current Lease Address for interface."
   ::= {sm48tat4xarpIPInterfacesEntry 10 }


sm48tat4xarpIPInterfacesIPv6Address OBJECT-TYPE
   SYNTAX      DisplayString (SIZE (0..30))
   MAX-ACCESS  read-write
   STATUS      current
   DESCRIPTION
       "IPv6 address for interface."
   ::= { sm48tat4xarpIPInterfacesEntry 11 }

sm48tat4xarpIPInterfacesIPv6Mask OBJECT-TYPE
   SYNTAX      Integer32 (1..128)
   MAX-ACCESS  read-write
   STATUS      current
   DESCRIPTION
       "IPv6 mask for interface."
   ::= { sm48tat4xarpIPInterfacesEntry 12 }

sm48tat4xarpIPInterfacesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sm48tat4xarpIPInterfacesEntry 13 }


sm48tat4xarpIPRoutes OBJECT IDENTIFIER ::= { sm48tat4xarpIP 4 }

sm48tat4xarpIPRoutesTable OBJECT-TYPE
   SYNTAX      SEQUENCE OF SM48TAT4XARPIPRoutesEntry
   MAX-ACCESS  not-accessible
   STATUS      current
   DESCRIPTION
       "IP routes table for switch."
    ::= { sm48tat4xarpIPRoutes 1 }

sm48tat4xarpIPRoutesEntry OBJECT-TYPE
    SYNTAX        SM48TAT4XARPIPRoutesEntry
    MAX-ACCESS    not-accessible
    STATUS        current
    DESCRIPTION
        "Entry in the sm48tat4xarpIPRoutesTable."
    INDEX        { sm48tat4xarpIPRoutesIndex }
    ::= { sm48tat4xarpIPRoutesTable 1 }

SM48TAT4XARPIPRoutesEntry ::=
    SEQUENCE {
        sm48tat4xarpIPRoutesIndex                       Integer32,
        sm48tat4xarpIPRoutesNetwork                     DisplayString,
        sm48tat4xarpIPRoutesMaskLength                  Integer32,
        sm48tat4xarpIPRoutesGateway                     DisplayString,
        sm48tat4xarpIPRoutesNextHopVLAN                 Integer32,
	sm48tat4xarpIPRoutesRowStatus                   RowStatus
    }

sm48tat4xarpIPRoutesIndex OBJECT-TYPE
   SYNTAX      Integer32 (1..32)
   MAX-ACCESS  not-accessible
   STATUS      current
   DESCRIPTION
       "routes table index"
   ::= {sm48tat4xarpIPRoutesEntry 2 }

sm48tat4xarpIPRoutesNetwork OBJECT-TYPE
   SYNTAX      DisplayString (SIZE (0..30))
   MAX-ACCESS  read-write
   STATUS      current
   DESCRIPTION
       "IPv4/IPv6 Network address.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry.
        If Set IPRoutesNetwork, please also set IPRoutesMaskLength, IPRoutesGateway, IPRoutesNextHopVLAN."
   ::= {sm48tat4xarpIPRoutesEntry 3 }

sm48tat4xarpIPRoutesMaskLength OBJECT-TYPE
   SYNTAX      Integer32 (1..32)
   MAX-ACCESS  read-write
   STATUS      current
   DESCRIPTION
       "IPv4/IPv6 mask length.
        Please set IPRoutesNetwork first.
        Note: All entries in routes table will be sort by 1.network address 2.mask length 3. gateway 4. next hop VLAN, if you add/modify an entry, all entries will be reordered. Please check all entries in table to find your modified entry after set/add an entry."
   ::= { sm48tat4xarpIPRoutesEntry 4 }

sm48tat4xarpIPRoutesGateway OBJECT-TYPE
   SYNTAX      DisplayString (SIZE (0..30))
   MAX-ACCESS  read-write
   STATUS      current
   DESCRIPTION
       "IPv4/IPv6 Gateway.
        Please set IPRoutesNetwork first.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry."
   ::= {sm48tat4xarpIPRoutesEntry 5 }

sm48tat4xarpIPRoutesNextHopVLAN OBJECT-TYPE
   SYNTAX      Integer32 (1..4095)
   MAX-ACCESS  read-write
   STATUS      current
   DESCRIPTION
       "Next Hop VLAN ID, range: 1-4095.
        Please set IPRoutesNetwork first.
        This entry only work when 1.network address is IPv6, 2.Gateway is link-local, 3.Interface of specific VLAN ID is IPv6.
        Note: All entries in routes table will be sort by 1.network address 2.mask length 3. gateway 4. next hop VLAN, if you add/modify an entry, all entries will be reordered. Please check all entries in table to find your modified entry after set/add an entry."
   ::= {sm48tat4xarpIPRoutesEntry 6 }

sm48tat4xarpIPRoutesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sm48tat4xarpIPRoutesEntry 7 }

sm48tat4xarpIPStatusInterface OBJECT IDENTIFIER ::= { sm48tat4xarpIP 8 }

sm48tat4xarpIPStatusInterfaceTable OBJECT-TYPE
              SYNTAX      SEQUENCE OF     SM48TAT4XARPIPStatusInterfaceEntry
              MAX-ACCESS  not-accessible
              STATUS      current
              DESCRIPTION
                       "The system IP Status table to show all IP interfaces."
                   ::= {     sm48tat4xarpIPStatusInterface 1 }

    sm48tat4xarpIPStatusInterfaceEntry OBJECT-TYPE
               SYNTAX          SM48TAT4XARPIPStatusInterfaceEntry
               MAX-ACCESS  not-accessible
               STATUS      current
               DESCRIPTION
                       "An entry in the IP Status Table."
               INDEX    {    sm48tat4xarpIPStatusInterfaceIndex  }
               ::= {     sm48tat4xarpIPStatusInterfaceTable 1 }

    SM48TAT4XARPIPStatusInterfaceEntry             ::= SEQUENCE {
            sm48tat4xarpIPStatusInterfaceIndex         Integer32,
            sm48tat4xarpIPStatusInterfaceName          DisplayString,
            sm48tat4xarpIPStatusInterfaceType          DisplayString,
            sm48tat4xarpIPStatusInterfaceAddress       DisplayString,
            sm48tat4xarpIPStatusInterfaceStatus        DisplayString
            }

    sm48tat4xarpIPStatusInterfaceIndex OBJECT-TYPE
               SYNTAX      Integer32(1..1024)
               MAX-ACCESS  not-accessible
               STATUS      current
               DESCRIPTION
                   "The entry of table to show all IP interfaces."
               ::= {     sm48tat4xarpIPStatusInterfaceEntry 1 }

    sm48tat4xarpIPStatusInterfaceName OBJECT-TYPE
               SYNTAX      DisplayString
               MAX-ACCESS  read-only
               STATUS      current
               DESCRIPTION
                   "The name of the interface."
               ::= {     sm48tat4xarpIPStatusInterfaceEntry 2 }

    sm48tat4xarpIPStatusInterfaceType OBJECT-TYPE
               SYNTAX      DisplayString
               MAX-ACCESS  read-only
               STATUS      current
               DESCRIPTION
                   "The address type of the entry. This may be LINK or IPv4."
               ::= {     sm48tat4xarpIPStatusInterfaceEntry 3 }

    sm48tat4xarpIPStatusInterfaceAddress OBJECT-TYPE
               SYNTAX      DisplayString
               MAX-ACCESS  read-only
               STATUS      current
               DESCRIPTION
                   "The current address of the interface (of the given type)."
               ::= {     sm48tat4xarpIPStatusInterfaceEntry 4 }

    sm48tat4xarpIPStatusInterfaceStatus OBJECT-TYPE
               SYNTAX      DisplayString
               MAX-ACCESS  read-only
               STATUS      current
               DESCRIPTION
                   "The status flags of the interface (and/or address)."
               ::= {     sm48tat4xarpIPStatusInterfaceEntry 5 }

sm48tat4xarpIPStatusRoute OBJECT IDENTIFIER ::= { sm48tat4xarpIP 9 }

    sm48tat4xarpIPStatusRouteTable OBJECT-TYPE
              SYNTAX      SEQUENCE OF     SM48TAT4XARPIPStatusRouteEntry
              MAX-ACCESS  not-accessible
              STATUS      current
              DESCRIPTION
                       "The IP Status Route table show all routing entries."
                   ::= {     sm48tat4xarpIPStatusRoute 1 }

    sm48tat4xarpIPStatusRouteEntry OBJECT-TYPE
               SYNTAX          SM48TAT4XARPIPStatusRouteEntry
               MAX-ACCESS  not-accessible
               STATUS      current
               DESCRIPTION
                       "an entry in the IP Status route table."
               INDEX    {     sm48tat4xarpIPStatusRouteIndex  }
               ::= {     sm48tat4xarpIPStatusRouteTable 1 }

    SM48TAT4XARPIPStatusRouteEntry             ::= SEQUENCE {
            sm48tat4xarpIPStatusRouteIndex          Integer32,
            sm48tat4xarpIPStatusRouteNetwork        DisplayString,
            sm48tat4xarpIPStatusRouteGateway        DisplayString,
            sm48tat4xarpIPStatusRouteAddress        DisplayString
     }

    sm48tat4xarpIPStatusRouteIndex OBJECT-TYPE
               SYNTAX      Integer32(1..2048)
               MAX-ACCESS  not-accessible
               STATUS      current
               DESCRIPTION
                   "The entry of table to show all routing entries."
               ::= {     sm48tat4xarpIPStatusRouteEntry 1 }

    sm48tat4xarpIPStatusRouteNetwork OBJECT-TYPE
               SYNTAX      DisplayString
               MAX-ACCESS  read-only
               STATUS      current
               DESCRIPTION
                   "The destination IP network or host address of this route."
               ::= {     sm48tat4xarpIPStatusRouteEntry 2 }

    sm48tat4xarpIPStatusRouteGateway OBJECT-TYPE
               SYNTAX      DisplayString
               MAX-ACCESS  read-only
               STATUS      current
               DESCRIPTION
                   "The gateway address of this route."
               ::= {     sm48tat4xarpIPStatusRouteEntry 3 }

    sm48tat4xarpIPStatusRouteAddress OBJECT-TYPE
               SYNTAX      DisplayString
               MAX-ACCESS  read-only
               STATUS      current
               DESCRIPTION
                   "The route address."
               ::= {     sm48tat4xarpIPStatusRouteEntry 4 }

sm48tat4xarpIPStatusNeighborCache OBJECT IDENTIFIER ::= { sm48tat4xarpIP 10 }

    sm48tat4xarpIPStatusNeighborCacheTable OBJECT-TYPE
               SYNTAX      SEQUENCE OF     SM48TAT4XARPIPStatusNeighborCacheEntry
               MAX-ACCESS  not-accessible
               STATUS      current
               DESCRIPTION
                       "The Ip Status Neighbor Cache Table."
                   ::= {     sm48tat4xarpIPStatusNeighborCache 1 }

    sm48tat4xarpIPStatusNeighborCacheEntry OBJECT-TYPE
               SYNTAX          SM48TAT4XARPIPStatusNeighborCacheEntry
               MAX-ACCESS  not-accessible
               STATUS      current
               DESCRIPTION
                       "An entry in the Ip Status Neighbor Cache Table."
               INDEX    {     sm48tat4xarpIPStatusNeighborCacheIndex  }
               ::= {     sm48tat4xarpIPStatusNeighborCacheTable 1 }

    SM48TAT4XARPIPStatusNeighborCacheEntry             ::= SEQUENCE {
            sm48tat4xarpIPStatusNeighborCacheIndex            Integer32,
            sm48tat4xarpIPStatusNeighborCacheIPAddress        DisplayString,
            sm48tat4xarpIPStatusNeighborCacheLinkAddress      DisplayString
            }

    sm48tat4xarpIPStatusNeighborCacheIndex OBJECT-TYPE
               SYNTAX      Integer32(1..1024)
               MAX-ACCESS  not-accessible
               STATUS      current
               DESCRIPTION
                   "The index for the Ip Status Neighbor Cache Table."
               ::= {     sm48tat4xarpIPStatusNeighborCacheEntry 1 }

    sm48tat4xarpIPStatusNeighborCacheIPAddress OBJECT-TYPE
               SYNTAX      DisplayString
               MAX-ACCESS  read-only
               STATUS      current
               DESCRIPTION
                   "The IP address of the entry."
               ::= {     sm48tat4xarpIPStatusNeighborCacheEntry 2 }

    sm48tat4xarpIPStatusNeighborCacheLinkAddress OBJECT-TYPE
               SYNTAX      DisplayString
               MAX-ACCESS  read-only
               STATUS      current
               DESCRIPTION
                   "The Link (MAC) address for which a binding to the
                    IP address given exist."
               ::= {     sm48tat4xarpIPStatusNeighborCacheEntry 3 }

sm48tat4xarpIPStatusDNSServer OBJECT IDENTIFIER ::= { sm48tat4xarpIP 11 }

    sm48tat4xarpIPStatusDNSServerType OBJECT-TYPE
               SYNTAX      DisplayString
               MAX-ACCESS  read-only
               STATUS      current
               DESCRIPTION
                   "The configuration type of DNS server."
               ::= {     sm48tat4xarpIPStatusDNSServer 1 }

    sm48tat4xarpIPStatusDNSServerIPAddress OBJECT-TYPE
               SYNTAX      DisplayString
               MAX-ACCESS  read-only
               STATUS      current
               DESCRIPTION
                   "The IP address of the DNS server."
               ::= {     sm48tat4xarpIPStatusDNSServer 2 }

    sm48tat4xarpIPStatusDNSServerInterface OBJECT-TYPE
               SYNTAX      DisplayString
               MAX-ACCESS  read-only
               STATUS      current
               DESCRIPTION
                   "The name of the interface."
               ::= {     sm48tat4xarpIPStatusDNSServer 3 }

-- =======================================================================================================================
sm48tat4xarpSyslog                                                OBJECT IDENTIFIER ::= { sm48tat4xarpSystem 5 }

sm48tat4xarpSyslogConf                                            OBJECT IDENTIFIER ::= { sm48tat4xarpSyslog 1 }

sm48tat4xarpSysLogInfo                                            OBJECT IDENTIFIER   ::= {  sm48tat4xarpSyslog 2 }
--
-- =======================================================================================================================
-- Objects in the sm48tat4xarpSystemLog Group
-- =======================================================================================================================
--sm48tat4xarpSystemLogConf

    sm48tat4xarpSystemLogServerMode OBJECT-TYPE
               SYNTAX      AdminMode
               MAX-ACCESS  read-write
               STATUS      current
               DESCRIPTION
                   "The System log server mode admin state."
               DEFVAL  { disable }
               ::= {     sm48tat4xarpSyslogConf 1 }

    sm48tat4xarpSystemLogServerAddress OBJECT-TYPE
               SYNTAX      DisplayString
               MAX-ACCESS  read-write
               STATUS      current
               DESCRIPTION
                   "The Host address of syslog server."
               ::= {     sm48tat4xarpSyslogConf 2 }

--    sm48tat4xarpSystemLogSyslogLevel OBJECT-TYPE
--               SYNTAX      INTEGER {
--                    info(0),
--                    warning(1),
--                    error(2)
--               }
--               MAX-ACCESS  read-write
--               STATUS      current
--               DESCRIPTION
--                   "The syslog level.
--                       info(0)   : Info.
--                       warning(1): Warning.
--                       error(2)  : Error."
--               DEFVAL  { info }
--               ::= {     sm48tat4xarpSyslogConf 3 }

    sm48tat4xarpSystemLogServerPort OBJECT-TYPE
                 SYNTAX      Integer32(1..65535)
                 MAX-ACCESS  read-write
                 STATUS      current
                 DESCRIPTION
                      "syslog service port number.
                 range : 1-65535, default : 514."
               ::= {     sm48tat4xarpSyslogConf 4 }

--sm48tat4xarpSystemLogInfo
    sm48tat4xarpSystemLogInfoLevel OBJECT-TYPE
               SYNTAX      INTEGER { emergency(0), alert(1), critical(2), error(3), warning(4), notice(5), information(6), debug(7), all(8) }
               MAX-ACCESS  read-write
               STATUS      current
               DESCRIPTION
                  "The Level input field is used to filter the display system log entries.
                   0: Emergency.
                   1: Alert.
                   2: Critical.
                   3: Error.
                   4: Warning.
                   5: Notice.
                   6: Information.
                   7: Debug.
                   8: All."
               DEFVAL  { all }
               ::= {     sm48tat4xarpSysLogInfo 1 }

    sm48tat4xarpSystemLogInfoClearLevel OBJECT-TYPE
               SYNTAX      INTEGER { emergency(0), alert(1), critical(2), error(3), warning(4), notice(5), information(6), debug(7), all(8) }
               MAX-ACCESS  read-write
               STATUS      current
               DESCRIPTION
                  "The Clear Level input field is used to specify which
                  system log entries will be cleared.
                  default: 8 (All).
                   0: Emergency.
                   1: Alert.
                   2: Critical.
                   3: Error.
                   4: Warning.
                   5: Notice.
                   6: Information.
                   7: Debug.
                   8: All."
               DEFVAL  { all }
               ::= {     sm48tat4xarpSysLogInfo 2 }

    sm48tat4xarpSystemLogInfoClearCmd OBJECT-TYPE
               SYNTAX      ActivateCmd
               MAX-ACCESS  read-write
               STATUS      current
               DESCRIPTION
                  "Command to clear the syslog.
                   noAction(0) : do nothing  (read only).
                   activate(1) : Clear Syslog."
               DEFVAL  { noAction }
               ::= {     sm48tat4xarpSysLogInfo 3 }

    sm48tat4xarpSystemLogDetailedInfoTable OBJECT-TYPE
              SYNTAX      SEQUENCE OF     SM48TAT4XARPSystemLogDetailedInfoEntry
              MAX-ACCESS  not-accessible
              STATUS      current
              DESCRIPTION
                       "The system detailed Log Info table."
                   ::= {     sm48tat4xarpSysLogInfo 4 }

    sm48tat4xarpSystemLogDetailedInfoEntry OBJECT-TYPE
               SYNTAX          SM48TAT4XARPSystemLogDetailedInfoEntry
               MAX-ACCESS  not-accessible
               STATUS      current
               DESCRIPTION
                       "An entry in the system detailed Log Info table."
               INDEX    {     sm48tat4xarpSystemLogDetailedInfoID  }
               ::= {     sm48tat4xarpSystemLogDetailedInfoTable 1 }

    SM48TAT4XARPSystemLogDetailedInfoEntry             ::= SEQUENCE {
                sm48tat4xarpSystemLogDetailedSwitchIndex       Integer32,
                sm48tat4xarpSystemLogDetailedInfoID            Integer32,
                sm48tat4xarpSystemLogDetailedInfoLevel         DisplayString,
                sm48tat4xarpSystemLogDetailedInfoTime          DisplayString,
                sm48tat4xarpSystemLogDetailedInfoMessage       DisplayString
                }

    sm48tat4xarpSystemLogDetailedSwitchIndex OBJECT-TYPE
               SYNTAX      Integer32(1..16)
               MAX-ACCESS  not-accessible
               STATUS      current
               DESCRIPTION
                   "The switch index for the system detailed Log Info table."
               ::= {     sm48tat4xarpSystemLogDetailedInfoEntry 1 }

    sm48tat4xarpSystemLogDetailedInfoID OBJECT-TYPE
               SYNTAX      Integer32(1..999)
               MAX-ACCESS  not-accessible
               STATUS      current
               DESCRIPTION
                   "The index for the system detailed Log Info table."
               ::= {     sm48tat4xarpSystemLogDetailedInfoEntry 2 }

    sm48tat4xarpSystemLogDetailedInfoLevel OBJECT-TYPE
               SYNTAX      DisplayString
               MAX-ACCESS  read-only
               STATUS      current
               DESCRIPTION
                   "The Info Level."
               ::= {     sm48tat4xarpSystemLogDetailedInfoEntry 3 }

    sm48tat4xarpSystemLogDetailedInfoTime OBJECT-TYPE
               SYNTAX      DisplayString(SIZE (0..20))
               MAX-ACCESS  read-only
               STATUS      current
               DESCRIPTION
                   "The time"
               ::= {     sm48tat4xarpSystemLogDetailedInfoEntry 4 }

    sm48tat4xarpSystemLogDetailedInfoMessage OBJECT-TYPE
               SYNTAX      DisplayString
               MAX-ACCESS  read-only
               STATUS      current
               DESCRIPTION
                   "The message of this entry."
               ::= {     sm48tat4xarpSystemLogDetailedInfoEntry 5 }
-- =======================================================================================================================
sm48tat4xarpSnmp                                                OBJECT IDENTIFIER ::= { sm48tat4xarpSystem 6 }

sm48tat4xarpSnmpSystem                                            OBJECT IDENTIFIER ::= { sm48tat4xarpSnmp 1 }

sm48tat4xarpSnmpSystemMode OBJECT-TYPE
   SYNTAX       Integer32
   MAX-ACCESS   read-write
   STATUS       current
   DESCRIPTION
       "SNMP mode operation.
        default : 1, 0: disable, 1: enable. "
   ::= { sm48tat4xarpSnmpSystem 1 }

sm48tat4xarpSnmpSystemVersion OBJECT-TYPE
   SYNTAX       Integer32
   MAX-ACCESS   read-write
   STATUS       current
   DESCRIPTION
       "SNMP supported version.
       default : snmpv2c.
       1: snmpv1
       2: snmpv2c
       3: snmpv3."
   ::= { sm48tat4xarpSnmpSystem 2 }

sm48tat4xarpSnmpSystemReadCommunity OBJECT-TYPE
   SYNTAX       DisplayString
   MAX-ACCESS   read-write
   STATUS       current
   DESCRIPTION
       "Indicates the community read access string to permit access to SNMP agent.
       The allowed string length is 0 to 255.
       The field is applicable only when SNMP version is SNMPv1 or SNMPv2c."
   ::= { sm48tat4xarpSnmpSystem 3 }

sm48tat4xarpSnmpSystemWriteCommunity OBJECT-TYPE
   SYNTAX       DisplayString
   MAX-ACCESS   read-write
   STATUS       current
   DESCRIPTION
       "Indicates the community write access string to permit access to SNMP agent.
       The allowed string length is 0 to 255.
       The field is applicable only when SNMP version is SNMPv1 or SNMPv2c."
   ::= { sm48tat4xarpSnmpSystem 4 }

--sm48tat4xarpSnmpSystemEngineID OBJECT-TYPE
--   SYNTAX       DisplayString
--   MAX-ACCESS   read-write
--   STATUS       current
--   DESCRIPTION
--       "Indicates the SNMPv3 engine ID.
--        The string must contain an even number(in hexadecimal format) with number of digits between 10 and 64,
--	but all-zeros and all-'F's are not allowed.
--	Allow string length is 10 to 32.
--	Change of the Engine ID will clear all original local users."
--   ::= { sm48tat4xarpSnmpSystem 5 }

sm48tat4xarpSnmpSystemWriteCommunityMode OBJECT-TYPE
   SYNTAX       Integer32
   MAX-ACCESS   read-write
   STATUS       current
   DESCRIPTION
       "SNMP write community mode operation.
        default : 1, 0: disable, 1: enable. "
   ::= { sm48tat4xarpSnmpSystem 6 }

sm48tat4xarpSnmpSystemReadCommunityMode OBJECT-TYPE
   SYNTAX       Integer32
   MAX-ACCESS   read-write
   STATUS       current
   DESCRIPTION
       "SNMP read community mode operation.
        default : 1, 0: disable, 1: enable. "
   ::= { sm48tat4xarpSnmpSystem 7 }


--sm48tat4xarpSnmpTrapGlobalMode OBJECT-TYPE
--   SYNTAX       Integer32
--   MAX-ACCESS   read-write
--   STATUS       current
--   DESCRIPTION
--       "Indicates the trap mode operation.
--        0:Disable.
--	1:Enable."
--   ::= { sm48tat4xarpSnmp 2 }

sm48tat4xarpTrapDestinationConfTable OBJECT-TYPE
   SYNTAX      SEQUENCE OF SM48TAT4XARPTrapDestinationConfEntry
   MAX-ACCESS  not-accessible
   STATUS      current
   DESCRIPTION
       "A list of trap host entry. The numbers of entries are given by the value of TrapHostConfNumber."
   ::= { sm48tat4xarpSnmp 3 }

sm48tat4xarpTrapDestinationConfEntry OBJECT-TYPE
   SYNTAX      SM48TAT4XARPTrapDestinationConfEntry
   MAX-ACCESS  not-accessible
   STATUS      current
   DESCRIPTION
       "This is the entry information for trap host."
   INDEX    { sm48tat4xarpTrapDestinationConfIndex  }
   ::= { sm48tat4xarpTrapDestinationConfTable 1 }

SM48TAT4XARPTrapDestinationConfEntry ::= SEQUENCE {
    sm48tat4xarpTrapDestinationConfIndex                      Integer32,
    sm48tat4xarpTrapDestinationConfTrapConfigName             DisplayString,
    sm48tat4xarpTrapDestinationConfTrapMode                   Integer32,
    sm48tat4xarpTrapDestinationConfTrapVersion                Integer32,
    sm48tat4xarpTrapDestinationConfTrapCommunity              DisplayString,
    sm48tat4xarpTrapDestinationConfTrapDestinationAddres      DisplayString,
    sm48tat4xarpTrapDestinationConfTrapDestinationPort        Integer32,
--  sm48tat4xarpTrapDestinationConfTrapInformMode             Integer32,
--  sm48tat4xarpTrapDestinationConfTrapInformTimeout          Integer32,
--  sm48tat4xarpTrapDestinationConfTrapInformRetryTimes       Integer32,
--  sm48tat4xarpTrapDestinationConfTrapProbeSecurityEngineID  Integer32,
    sm48tat4xarpTrapDestinationConfTrapSecurityEngineID       DisplayString,
    sm48tat4xarpTrapDestinationConfTrapSecurityName           DisplayString,
    sm48tat4xarpTrapDestinationConfTrapRowStatus              Integer32
}

sm48tat4xarpTrapDestinationConfIndex OBJECT-TYPE
   SYNTAX       Integer32(1..65535)
   MAX-ACCESS   not-accessible
   STATUS       current
   DESCRIPTION
       "Index of tarp destination configurations."
   ::= { sm48tat4xarpTrapDestinationConfEntry 1 }

sm48tat4xarpTrapDestinationConfTrapConfigName OBJECT-TYPE
   SYNTAX       DisplayString
   MAX-ACCESS   read-write
   STATUS       current
   DESCRIPTION
       "Indicates which trap Configuration's name for configuring.
       The allowed string length is 0 to 255, and the allowed content is
       ASCII characters from 33 to 126."
   ::= { sm48tat4xarpTrapDestinationConfEntry 2 }

sm48tat4xarpTrapDestinationConfTrapMode OBJECT-TYPE
   SYNTAX       Integer32
   MAX-ACCESS   read-write
   STATUS       current
   DESCRIPTION
       "Indicates the SNMP mode operation. Possible modes are:
        2: Enable TCP SNMP mode operation.
        1: Enable UDP SNMP mode operation.
        0: Disable SNMP mode operation. "
   ::= { sm48tat4xarpTrapDestinationConfEntry 3 }

sm48tat4xarpTrapDestinationConfTrapVersion OBJECT-TYPE
   SYNTAX       Integer32
   MAX-ACCESS   read-write
   STATUS       current
   DESCRIPTION
       "0: snmpv1
        1: snmpv2c
        3: snmpv3.
        "
   ::= { sm48tat4xarpTrapDestinationConfEntry 4 }

sm48tat4xarpTrapDestinationConfTrapCommunity OBJECT-TYPE
   SYNTAX       DisplayString
   MAX-ACCESS   read-write
   STATUS       current
   DESCRIPTION
       "Indicates the community access string when sending SNMP trap packet.
       The allowed string length is 0 to 255, and the allowed content is
       ASCII characters from 33 to 126."
   ::= { sm48tat4xarpTrapDestinationConfEntry 5 }

sm48tat4xarpTrapDestinationConfTrapDestinationAddres OBJECT-TYPE
   SYNTAX       DisplayString
   MAX-ACCESS   read-write
   STATUS       current
   DESCRIPTION
       "Indicates the SNMP trap destination address.
       It allow a valid IP address in dotted decimal notation ('x.y.z.w').
    And it also allow a valid hostname.
    A valid hostname is a string drawn from the alphabet (A-Za-z), digits (0-9),
    dot (.), dash (-). Spaces are not allowed, the first character must be an alpha character,
    and the first and last characters must not be a dot or a dash.
    Indicates the SNMP trap destination IPv6 address.
    IPv6 address is in 128-bit records represented as eight fields of up to four hexadecimal digits
    with a colon separating each field (:).
    For example, 'fe80::215:c5ff:fe03:4dc7'. The symbol '::' is a special syntax
    that can be used as a shorthand way of representing multiple 16-bit groups of contiguous zeros;
    but it can appear only once.
    It can also represent a legally valid IPv4 address.
    For example, '::192.1.2.34'."
   ::= { sm48tat4xarpTrapDestinationConfEntry 6 }

sm48tat4xarpTrapDestinationConfTrapDestinationPort OBJECT-TYPE
   SYNTAX       Integer32
   MAX-ACCESS   read-write
   STATUS       current
   DESCRIPTION
       "Indicates the SNMP trap destination port.
       SNMP Agent will send SNMP message via this port,
       the port range is 1~65535."
   ::= { sm48tat4xarpTrapDestinationConfEntry 7 }

--sm48tat4xarpTrapDestinationConfTrapInformMode OBJECT-TYPE
--   SYNTAX       Integer32
--   MAX-ACCESS   read-write
--   STATUS       current
--   DESCRIPTION
--       "Indicates the SNMP trap inform mode operation. Possible modes are:
--        1: Enable SNMP trap inform mode operation.
--        0: Disable SNMP trap inform mode operation. "
--   ::= { sm48tat4xarpTrapDestinationConfEntry 8 }
--
--sm48tat4xarpTrapDestinationConfTrapInformTimeout OBJECT-TYPE
--   SYNTAX       Integer32
--   MAX-ACCESS   read-write
--   STATUS       current
--   DESCRIPTION
--       "Indicates the SNMP trap inform timeout. The allowed range is 0 to 2147."
--   ::= { sm48tat4xarpTrapDestinationConfEntry 9 }
--
--sm48tat4xarpTrapDestinationConfTrapInformRetryTimes OBJECT-TYPE
--   SYNTAX       Integer32
--   MAX-ACCESS   read-write
--   STATUS       current
--   DESCRIPTION
--       "Indicates the SNMP trap inform retry times. The allowed range is 0 to 255."
--   ::= { sm48tat4xarpTrapDestinationConfEntry 10 }
--
--sm48tat4xarpTrapDestinationConfTrapProbeSecurityEngineID OBJECT-TYPE
--   SYNTAX       Integer32
--   MAX-ACCESS   read-write
--   STATUS       current
--   DESCRIPTION
--       "Indicates the SNMP trap probe security engine ID mode of operation.
--       Possible values are:
--       1: Enable SNMP trap probe security engine ID mode of operation.
--       0: Disable SNMP trap probe security engine ID mode of operation."
--   ::= { sm48tat4xarpTrapDestinationConfEntry 11 }

sm48tat4xarpTrapDestinationConfTrapSecurityEngineID OBJECT-TYPE
   SYNTAX       DisplayString
   MAX-ACCESS   read-write
   STATUS       current
   DESCRIPTION
       "Indicates the SNMP trap security engine ID.
       SNMPv3 sends traps and informs using USM for authentication and privacy.
       A unique engine ID for these traps and informs is needed.
       When Trap Probe Security Engine ID is enabled, the ID will be probed automatically.
       Otherwise, the ID specified in this field is used.
       The string must contain an even number(in hexadecimal format) with
       number of digits between 10 and 64, but all-zeros and all-'F's are not allowed."
   ::= { sm48tat4xarpTrapDestinationConfEntry 12 }

sm48tat4xarpTrapDestinationConfTrapSecurityName OBJECT-TYPE
   SYNTAX       DisplayString
   MAX-ACCESS   read-write
   STATUS       current
   DESCRIPTION
       "Indicates the SNMP trap security name.
       SNMPv3 traps and informs using USM for authentication and privacy.
       A unique security name is needed when traps and informs are enabled.
       This name from user name of user configuration."
   ::= { sm48tat4xarpTrapDestinationConfEntry 13 }

sm48tat4xarpTrapDestinationConfTrapRowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sm48tat4xarpTrapDestinationConfEntry 14 }


sm48tat4xarpSNMPCommunityConfTable OBJECT-TYPE
   SYNTAX      SEQUENCE OF SM48TAT4XARPSNMPCommunityConfEntry
   MAX-ACCESS  not-accessible
   STATUS      current
   DESCRIPTION
       "A list of snmp community configuration entry."
   ::= { sm48tat4xarpSnmp 5 }

sm48tat4xarpSNMPCommunityConfEntry OBJECT-TYPE
   SYNTAX      SM48TAT4XARPSNMPCommunityConfEntry
   MAX-ACCESS  not-accessible
   STATUS      current
   DESCRIPTION
       "This is the entry information for snmp community configuration."
   INDEX    { sm48tat4xarpSNMPCommunityConfIndex  }
   ::= { sm48tat4xarpSNMPCommunityConfTable 1 }

SM48TAT4XARPSNMPCommunityConfEntry ::= SEQUENCE {
    sm48tat4xarpSNMPCommunityConfIndex                       Integer32,
    sm48tat4xarpSNMPCommunityConfSNMPv3Community             DisplayString,
    sm48tat4xarpSNMPCommunityConfSNMPv3SourceIP              IpAddress,
    sm48tat4xarpSNMPCommunityConfSNMPv3SourceMask            IpAddress,
    sm48tat4xarpSNMPCommunityConfSNMPv3RowStatus             Integer32
}

sm48tat4xarpSNMPCommunityConfIndex OBJECT-TYPE
   SYNTAX       Integer32(1..65535)
   MAX-ACCESS   read-write
   STATUS       current
   DESCRIPTION
       "Community configuration index."
   ::= { sm48tat4xarpSNMPCommunityConfEntry 1 }

sm48tat4xarpSNMPCommunityConfSNMPv3Community OBJECT-TYPE
   SYNTAX       DisplayString
   MAX-ACCESS   read-write
   STATUS       current
   DESCRIPTION
       "Indicates the community access string to permit access to SNMPv3 agent.
       The allowed string length is 1 to 32, and the allowed content is
       ASCII characters from 33 to 126.
       The community string will be treated as security name and map a SNMPv1
       or SNMPv2c community string."
   ::= { sm48tat4xarpSNMPCommunityConfEntry 2 }


sm48tat4xarpSNMPCommunityConfSNMPv3SourceIP OBJECT-TYPE
   SYNTAX      IpAddress
   MAX-ACCESS  read-write
   STATUS      current
   DESCRIPTION
       "Indicates the SNMP access source address.
       A particular range of source addresses can be used to restrict source subnet
       when combined with source mask."
   ::= {sm48tat4xarpSNMPCommunityConfEntry 3 }

sm48tat4xarpSNMPCommunityConfSNMPv3SourceMask OBJECT-TYPE
   SYNTAX      IpAddress
   MAX-ACCESS  read-write
   STATUS      current
   DESCRIPTION
       "Indicates the SNMP access source address mask."
   ::= {sm48tat4xarpSNMPCommunityConfEntry 4 }

sm48tat4xarpSNMPCommunityConfSNMPv3RowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sm48tat4xarpSNMPCommunityConfEntry 5 }

sm48tat4xarpSNMPv3UserConfTable OBJECT-TYPE
   SYNTAX      SEQUENCE OF SM48TAT4XARPSNMPv3UserConfEntry
   MAX-ACCESS  not-accessible
   STATUS      current
   DESCRIPTION
       "A list of snmpv3 user configuration entry."
   ::= { sm48tat4xarpSnmp 6 }

sm48tat4xarpSNMPv3UserConfEntry OBJECT-TYPE
   SYNTAX      SM48TAT4XARPSNMPv3UserConfEntry
   MAX-ACCESS  not-accessible
   STATUS      current
   DESCRIPTION
       "This is the entry information for snmpv3 user configuration."
   INDEX    { sm48tat4xarpSNMPv3UserConfIndex  }
   ::= { sm48tat4xarpSNMPv3UserConfTable 1 }

SM48TAT4XARPSNMPv3UserConfEntry ::= SEQUENCE {
    sm48tat4xarpSNMPv3UserConfIndex                     Integer32,
    sm48tat4xarpSNMPv3UserConfEngineID                  DisplayString,
    sm48tat4xarpSNMPv3UserConfUserName                  DisplayString,
    sm48tat4xarpSNMPv3UserConfSecurityLevel             Integer32,
    sm48tat4xarpSNMPv3UserConfAuthenticationProtocol    Integer32,
    sm48tat4xarpSNMPv3UserConfAuthenticationPassword    DisplayString,
    sm48tat4xarpSNMPv3UserConfPrivacyProtocol           Integer32,
    sm48tat4xarpSNMPv3UserConfPrivacyPassword           DisplayString,
    sm48tat4xarpSNMPv3UserConfRowStatus                 RowStatus
}

sm48tat4xarpSNMPv3UserConfIndex OBJECT-TYPE
   SYNTAX       Integer32(1..65535)
   MAX-ACCESS   read-write
   STATUS       current
   DESCRIPTION
       "User configuration index."
   ::= { sm48tat4xarpSNMPv3UserConfEntry 1 }

sm48tat4xarpSNMPv3UserConfEngineID OBJECT-TYPE
   SYNTAX       DisplayString
   MAX-ACCESS   read-write
   STATUS       current
   DESCRIPTION
       "An octet string identifying the engine ID that this entry should belong to.
       The string must contain an even number(in hexadecimal format) with
       number of digits between 10 and 64, but all-zeros and all-'F's are not allowed.
       The SNMPv3 architecture uses the User-based Security Model (USM)
       for message security and the View-based Access Control Model (VACM) for access control.
       For the USM entry, the usmUserEngineID and usmUserName are the entry's keys.
       In a simple agent, usmUserEngineID is always that agent's own snmpEngineID value.
       The value can also take the value of the snmpEngineID of a remote SNMP engine with
       which this user can communicate. In other words, if user engine ID equal system engine ID
       then it is local user; otherwise it's remote user. "
   ::= { sm48tat4xarpSNMPv3UserConfEntry 2 }

sm48tat4xarpSNMPv3UserConfUserName OBJECT-TYPE
   SYNTAX       DisplayString
   MAX-ACCESS   read-write
   STATUS       current
   DESCRIPTION
       "A string identifying the user name that this entry should belong to.
       The allowed string length is 1 to 32, and the allowed content is
       ASCII characters from 33 to 126."
   ::= { sm48tat4xarpSNMPv3UserConfEntry 3 }

sm48tat4xarpSNMPv3UserConfSecurityLevel OBJECT-TYPE
   SYNTAX       Integer32
   MAX-ACCESS   read-write
   STATUS       current
   DESCRIPTION
       "1:NoAuth, NoPriv
        2:Auth, NoPriv
	3:Auth, Priv"
   ::= { sm48tat4xarpSNMPv3UserConfEntry 4 }

sm48tat4xarpSNMPv3UserConfAuthenticationProtocol OBJECT-TYPE
   SYNTAX       Integer32
   MAX-ACCESS   read-write
   STATUS       current
   DESCRIPTION
       "0:None
        1:MD5
	2:SHA"
   ::= { sm48tat4xarpSNMPv3UserConfEntry 5 }

sm48tat4xarpSNMPv3UserConfAuthenticationPassword OBJECT-TYPE
   SYNTAX       DisplayString
   MAX-ACCESS   read-write
   STATUS       current
   DESCRIPTION
       "A string identifying the authentication password phrase.
       For MD5 authentication protocol, the allowed string length is 8 to 32.
       For SHA authentication protocol, the allowed string length is 8 to 40.
       The allowed content is ASCII characters from 33 to 126."
   ::= { sm48tat4xarpSNMPv3UserConfEntry 6 }

sm48tat4xarpSNMPv3UserConfPrivacyProtocol OBJECT-TYPE
   SYNTAX       Integer32
   MAX-ACCESS   read-write
   STATUS       current
   DESCRIPTION
       "0:None
        1:DES
        2:AES"
   ::= { sm48tat4xarpSNMPv3UserConfEntry 7 }

sm48tat4xarpSNMPv3UserConfPrivacyPassword OBJECT-TYPE
   SYNTAX       DisplayString
   MAX-ACCESS   read-write
   STATUS       current
   DESCRIPTION
       "A string identifying the privacy password phrase.
       The allowed string length is 8 to 32, and the allowed content is
       ASCII characters from 33 to 126."
   ::= { sm48tat4xarpSNMPv3UserConfEntry 8 }

sm48tat4xarpSNMPv3UserConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sm48tat4xarpSNMPv3UserConfEntry 9 }

sm48tat4xarpSNMPv3GroupConfTable OBJECT-TYPE
   SYNTAX      SEQUENCE OF SM48TAT4XARPSNMPv3GroupConfEntry
   MAX-ACCESS  not-accessible
   STATUS      current
   DESCRIPTION
       "A list of snmpv3 group configuration entry."
   ::= { sm48tat4xarpSnmp 7 }

sm48tat4xarpSNMPv3GroupConfEntry OBJECT-TYPE
   SYNTAX      SM48TAT4XARPSNMPv3GroupConfEntry
   MAX-ACCESS  not-accessible
   STATUS      current
   DESCRIPTION
       "This is the entry information for snmpv3 group configuration."
   INDEX    { sm48tat4xarpSNMPv3GroupConfIndex  }
   ::= { sm48tat4xarpSNMPv3GroupConfTable 1 }

SM48TAT4XARPSNMPv3GroupConfEntry ::= SEQUENCE {
    sm48tat4xarpSNMPv3GroupConfIndex                     Integer32,
    sm48tat4xarpSNMPv3GroupConfSecurityModel             Integer32,
    sm48tat4xarpSNMPv3GroupConfSecurityName          DisplayString,
    sm48tat4xarpSNMPv3GroupConfGroupName             DisplayString,
    sm48tat4xarpSNMPv3GroupConfRowStatus                 RowStatus
}

sm48tat4xarpSNMPv3GroupConfIndex OBJECT-TYPE
   SYNTAX       Integer32(1..65535)
   MAX-ACCESS   read-write
   STATUS       current
   DESCRIPTION
       "Group configuration index."
   ::= { sm48tat4xarpSNMPv3GroupConfEntry 1 }

sm48tat4xarpSNMPv3GroupConfSecurityModel OBJECT-TYPE
   SYNTAX       Integer32
   MAX-ACCESS   read-write
   STATUS       current
   DESCRIPTION
       "1:v1
        2:v2c
	3:usm"
   ::= { sm48tat4xarpSNMPv3GroupConfEntry 2 }

sm48tat4xarpSNMPv3GroupConfSecurityName OBJECT-TYPE
   SYNTAX       DisplayString
   MAX-ACCESS   read-write
   STATUS       current
   DESCRIPTION
       "A string identifying the security name that this entry should belong to.
       The allowed string length is 1 to 32, and the allowed content is
       ASCII characters from 33 to 126.
       This name is from the Community of Community configuration."
   ::= { sm48tat4xarpSNMPv3GroupConfEntry 3 }

sm48tat4xarpSNMPv3GroupConfGroupName OBJECT-TYPE
   SYNTAX       DisplayString
   MAX-ACCESS   read-write
   STATUS       current
   DESCRIPTION
       "A string identifying the group name that this entry should belong to.
       The allowed string length is 1 to 32, and the allowed content is
       ASCII characters from 33 to 126. "
   ::= { sm48tat4xarpSNMPv3GroupConfEntry 4 }


sm48tat4xarpSNMPv3GroupConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sm48tat4xarpSNMPv3GroupConfEntry 5 }

sm48tat4xarpSNMPv3ViewsConfTable OBJECT-TYPE
   SYNTAX      SEQUENCE OF SM48TAT4XARPSNMPv3ViewsConfEntry
   MAX-ACCESS  not-accessible
   STATUS      current
   DESCRIPTION
       "A list of snmpv3 view configuration entry."
   ::= { sm48tat4xarpSnmp 8 }

sm48tat4xarpSNMPv3ViewsConfEntry OBJECT-TYPE
   SYNTAX      SM48TAT4XARPSNMPv3ViewsConfEntry
   MAX-ACCESS  not-accessible
   STATUS      current
   DESCRIPTION
       "This is the entry information for snmpv3 view configuration."
   INDEX    { sm48tat4xarpSNMPv3ViewsConfIndex  }
   ::= { sm48tat4xarpSNMPv3ViewsConfTable 1 }

SM48TAT4XARPSNMPv3ViewsConfEntry ::= SEQUENCE {
    sm48tat4xarpSNMPv3ViewsConfIndex                   Integer32,
    sm48tat4xarpSNMPv3ViewsConfViewName            DisplayString,
    sm48tat4xarpSNMPv3ViewsConfViewType                Integer32,
    sm48tat4xarpSNMPv3ViewsConfOIDSubtree          DisplayString,
    sm48tat4xarpSNMPv3ViewsConfRowStatus               RowStatus
}

sm48tat4xarpSNMPv3ViewsConfIndex OBJECT-TYPE
   SYNTAX       Integer32(1..65535)
   MAX-ACCESS   read-write
   STATUS       current
   DESCRIPTION
       "view configuration index."
   ::= { sm48tat4xarpSNMPv3ViewsConfEntry 1 }

sm48tat4xarpSNMPv3ViewsConfViewName OBJECT-TYPE
   SYNTAX       DisplayString
   MAX-ACCESS   read-write
   STATUS       current
   DESCRIPTION
       "A string identifying the view name that this entry should belong to.
       The allowed string length is 1 to 32, and the allowed content is
       ASCII characters from 33 to 126. "
   ::= { sm48tat4xarpSNMPv3ViewsConfEntry 2 }

sm48tat4xarpSNMPv3ViewsConfViewType OBJECT-TYPE
   SYNTAX       Integer32
   MAX-ACCESS   read-write
   STATUS       current
   DESCRIPTION
       "0:included
       1:excluded"
   ::= { sm48tat4xarpSNMPv3ViewsConfEntry 3 }

sm48tat4xarpSNMPv3ViewsConfOIDSubtree OBJECT-TYPE
   SYNTAX       DisplayString
   MAX-ACCESS   read-write
   STATUS       current
   DESCRIPTION
       "The OID defining the root of the subtree to add to the named view.
       The allowed OID length is 1 to 128. The allowed string content is
       digital number or asterisk(*)"
   ::= { sm48tat4xarpSNMPv3ViewsConfEntry 4 }

sm48tat4xarpSNMPv3ViewsConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sm48tat4xarpSNMPv3ViewsConfEntry 5 }


sm48tat4xarpSNMPv3AccessConfTable OBJECT-TYPE
   SYNTAX      SEQUENCE OF SM48TAT4XARPSNMPv3AccessConfEntry
   MAX-ACCESS  not-accessible
   STATUS      current
   DESCRIPTION
       "A list of snmpv3 access configuration entry."
   ::= { sm48tat4xarpSnmp 9 }

sm48tat4xarpSNMPv3AccessConfEntry OBJECT-TYPE
   SYNTAX      SM48TAT4XARPSNMPv3AccessConfEntry
   MAX-ACCESS  not-accessible
   STATUS      current
   DESCRIPTION
       "This is the entry information for snmpv3 access configuration."
   INDEX    { sm48tat4xarpSNMPv3AccessConfIndex  }
   ::= { sm48tat4xarpSNMPv3AccessConfTable 1 }

SM48TAT4XARPSNMPv3AccessConfEntry ::= SEQUENCE {
    sm48tat4xarpSNMPv3AccessConfIndex                    Integer32,
    sm48tat4xarpSNMPv3AccessConfGroupName            DisplayString,
    sm48tat4xarpSNMPv3AccessConfSecurityModel            Integer32,
    sm48tat4xarpSNMPv3AccessConfSecurityLevel            Integer32,
    sm48tat4xarpSNMPv3AccessConfReadViewName         DisplayString,
    sm48tat4xarpSNMPv3AccessConfWriteViewName        DisplayString,
    sm48tat4xarpSNMPv3AccessConfRowStatus                RowStatus
}

sm48tat4xarpSNMPv3AccessConfIndex OBJECT-TYPE
   SYNTAX       Integer32(1..65535)
   MAX-ACCESS   read-write
   STATUS       current
   DESCRIPTION
       "Access configuration index"
   ::= { sm48tat4xarpSNMPv3AccessConfEntry 1 }

sm48tat4xarpSNMPv3AccessConfGroupName OBJECT-TYPE
   SYNTAX       DisplayString
   MAX-ACCESS   read-write
   STATUS       current
   DESCRIPTION
       "Group name from Group configuration."
   ::= { sm48tat4xarpSNMPv3AccessConfEntry 2 }

sm48tat4xarpSNMPv3AccessConfSecurityModel OBJECT-TYPE
   SYNTAX       Integer32
   MAX-ACCESS   read-write
   STATUS       current
   DESCRIPTION
       "0:any
        1:v1
	2:v2c
	3:usm"
   ::= { sm48tat4xarpSNMPv3AccessConfEntry 3 }

sm48tat4xarpSNMPv3AccessConfSecurityLevel OBJECT-TYPE
   SYNTAX       Integer32
   MAX-ACCESS   read-write
   STATUS       current
   DESCRIPTION
       "1:NoAuth, NoPriv
       2:Auth, NoPriv
       3:Auth, Priv"
   ::= { sm48tat4xarpSNMPv3AccessConfEntry 4 }

sm48tat4xarpSNMPv3AccessConfReadViewName OBJECT-TYPE
   SYNTAX       DisplayString
   MAX-ACCESS   read-write
   STATUS       current
   DESCRIPTION
       "Read View Name from View configuration."
   ::= { sm48tat4xarpSNMPv3AccessConfEntry 5 }

sm48tat4xarpSNMPv3AccessConfWriteViewName OBJECT-TYPE
   SYNTAX       DisplayString
   MAX-ACCESS   read-write
   STATUS       current
   DESCRIPTION
       "Write View Name from View configuration."
   ::= { sm48tat4xarpSNMPv3AccessConfEntry 6 }

sm48tat4xarpSNMPv3AccessConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sm48tat4xarpSNMPv3AccessConfEntry 7 }

-- =======================================================================================================================
sm48tat4xarpDHCPServer                                     OBJECT IDENTIFIER ::= { sm48tat4xarpSystem 9 }

sm48tat4xarpDHCPServerConfig                              OBJECT IDENTIFIER ::= { sm48tat4xarpDHCPServer 7 }

sm48tat4xarpDHCPServerConfigTable OBJECT-TYPE
   SYNTAX      SEQUENCE OF SM48TAT4XARPDHCPServerConfigEntry
   MAX-ACCESS  not-accessible
   STATUS      current
   DESCRIPTION
       " "
    ::= { sm48tat4xarpDHCPServerConfig 1 }

sm48tat4xarpDHCPServerConfigEntry OBJECT-TYPE
    SYNTAX        SM48TAT4XARPDHCPServerConfigEntry
    MAX-ACCESS    not-accessible
    STATUS        current
    DESCRIPTION
        " "
    INDEX        { sm48tat4xarpDHCPServerConfigIndex }
    ::= { sm48tat4xarpDHCPServerConfigTable 1 }


SM48TAT4XARPDHCPServerConfigEntry ::=
    SEQUENCE {
        sm48tat4xarpDHCPServerConfigIndex                    Integer32,
        sm48tat4xarpDHCPServerConfigInterfaceVLAN            Integer32,
        sm48tat4xarpDHCPServerConfigInterfaceMode            Integer32,
        sm48tat4xarpDHCPServerConfigInterfaceStartIPEndIP    DisplayString,
--      sm48tat4xarpDHCPServerConfigInterfaceEndIP           IpAddress,
        sm48tat4xarpDHCPServerConfigInterfaceLeaseTime       Integer32,
        sm48tat4xarpDHCPServerConfigInterfaceSubnetMask      IpAddress,
        sm48tat4xarpDHCPServerConfigInterfaceDefaultRouter   IpAddress,
        sm48tat4xarpDHCPServerConfigInterfaceDNSServer       IpAddress
    }

sm48tat4xarpDHCPServerConfigIndex OBJECT-TYPE
   SYNTAX      Integer32 (1..4094)
   MAX-ACCESS  not-accessible
   STATUS      current
   DESCRIPTION
       "table index."
   ::= {sm48tat4xarpDHCPServerConfigEntry 1 }

sm48tat4xarpDHCPServerConfigInterfaceVLAN OBJECT-TYPE
   SYNTAX      Integer32 (1..4094)
   MAX-ACCESS  read-only
   STATUS      current
   DESCRIPTION
       "The VLAN in which DHCP server is enabled or disabled. "
   ::= {sm48tat4xarpDHCPServerConfigEntry 2 }

sm48tat4xarpDHCPServerConfigInterfaceMode OBJECT-TYPE
   SYNTAX      Integer32 (0|1)
   MAX-ACCESS  read-write
   STATUS      current
   DESCRIPTION
       "Indicate the operation mode per VLAN.
       0:disable
       1:enable"
   ::= {sm48tat4xarpDHCPServerConfigEntry 3 }

sm48tat4xarpDHCPServerConfigInterfaceStartIPEndIP OBJECT-TYPE
   SYNTAX      DisplayString
   MAX-ACCESS  read-write
   STATUS      current
   DESCRIPTION
       "Please set SubnetMask first.
       Start IP and End IP. Format: x.x.x.x-x.x.x.x"
   ::= {sm48tat4xarpDHCPServerConfigEntry 4 }

--sm48tat4xarpDHCPServerConfigInterfaceEndIP OBJECT-TYPE
--   SYNTAX      IpAddress
--   MAX-ACCESS  read-write
--   STATUS      current
--   DESCRIPTION
--       "End IP"
--   ::= {sm48tat4xarpDHCPServerConfigEntry 5 }

sm48tat4xarpDHCPServerConfigInterfaceLeaseTime OBJECT-TYPE
   SYNTAX      Integer32
   MAX-ACCESS  read-write
   STATUS      current
   DESCRIPTION
       "The lease time in second."
   ::= {sm48tat4xarpDHCPServerConfigEntry 6 }

sm48tat4xarpDHCPServerConfigInterfaceSubnetMask OBJECT-TYPE
   SYNTAX      IpAddress
   MAX-ACCESS  read-write
   STATUS      current
   DESCRIPTION
       "Configure subnet mask of the DHCP address. "
   ::= {sm48tat4xarpDHCPServerConfigEntry 7 }

sm48tat4xarpDHCPServerConfigInterfaceDefaultRouter OBJECT-TYPE
   SYNTAX      IpAddress
   MAX-ACCESS  read-write
   STATUS      current
   DESCRIPTION
       "Configure the destination IP network or host address of the default route."
   ::= {sm48tat4xarpDHCPServerConfigEntry 8 }

sm48tat4xarpDHCPServerConfigInterfaceDNSServer OBJECT-TYPE
   SYNTAX      IpAddress
   MAX-ACCESS  read-write
   STATUS      current
   DESCRIPTION
       "Configure the default DNS server. "
   ::= {sm48tat4xarpDHCPServerConfigEntry 9 }

sm48tat4xarpDHCPServerStatus                              OBJECT IDENTIFIER ::= { sm48tat4xarpDHCPServer 8 }

sm48tat4xarpDHCPServerStatusTable OBJECT-TYPE
   SYNTAX      SEQUENCE OF SM48TAT4XARPDHCPServerStatusEntry
   MAX-ACCESS  not-accessible
   STATUS      current
   DESCRIPTION
       " "
    ::= { sm48tat4xarpDHCPServerStatus 1 }

sm48tat4xarpDHCPServerStatusEntry OBJECT-TYPE
    SYNTAX        SM48TAT4XARPDHCPServerStatusEntry
    MAX-ACCESS    not-accessible
    STATUS        current
    DESCRIPTION
        " "
    INDEX        { sm48tat4xarpDHCPServerStatusIndex }
    ::= { sm48tat4xarpDHCPServerStatusTable 1 }


SM48TAT4XARPDHCPServerStatusEntry ::=
    SEQUENCE {
        sm48tat4xarpDHCPServerStatusIndex                    Integer32,
        sm48tat4xarpDHCPServerStatusInterfaceVLAN            Integer32,
        sm48tat4xarpDHCPServerStatusInterfaceType            DisplayString,
        sm48tat4xarpDHCPServerStatusInterfaceStartIP         IpAddress,
        sm48tat4xarpDHCPServerStatusInterfaceEndIP           IpAddress,
        sm48tat4xarpDHCPServerStatusInterfaceLeaseTime       Integer32,
        sm48tat4xarpDHCPServerStatusInterfaceSubnetMask      IpAddress,
        sm48tat4xarpDHCPServerStatusInterfaceDefaultRouter   IpAddress,
        sm48tat4xarpDHCPServerStatusInterfaceDNSServer       IpAddress
    }

sm48tat4xarpDHCPServerStatusIndex OBJECT-TYPE
   SYNTAX      Integer32 (1..4094)
   MAX-ACCESS  not-accessible
   STATUS      current
   DESCRIPTION
       "table index."
   ::= {sm48tat4xarpDHCPServerStatusEntry 1 }

sm48tat4xarpDHCPServerStatusInterfaceVLAN OBJECT-TYPE
   SYNTAX      Integer32 (1..4094)
   MAX-ACCESS  read-only
   STATUS      current
   DESCRIPTION
       "The VLAN in which DHCP server is enabled or disabled. "
   ::= {sm48tat4xarpDHCPServerStatusEntry 2 }

sm48tat4xarpDHCPServerStatusInterfaceType OBJECT-TYPE
   SYNTAX      DisplayString
   MAX-ACCESS  read-only
   STATUS      current
   DESCRIPTION
       " "
   ::= {sm48tat4xarpDHCPServerStatusEntry 3 }

sm48tat4xarpDHCPServerStatusInterfaceStartIP OBJECT-TYPE
   SYNTAX      IpAddress
   MAX-ACCESS  read-only
   STATUS      current
   DESCRIPTION
       "Start IP"
   ::= {sm48tat4xarpDHCPServerStatusEntry 4 }

sm48tat4xarpDHCPServerStatusInterfaceEndIP OBJECT-TYPE
   SYNTAX      IpAddress
   MAX-ACCESS  read-only
   STATUS      current
   DESCRIPTION
       "End IP"
   ::= {sm48tat4xarpDHCPServerStatusEntry 5 }

sm48tat4xarpDHCPServerStatusInterfaceLeaseTime OBJECT-TYPE
   SYNTAX      Integer32
   MAX-ACCESS  read-only
   STATUS      current
   DESCRIPTION
       "The lease time in second."
   ::= {sm48tat4xarpDHCPServerStatusEntry 6 }

sm48tat4xarpDHCPServerStatusInterfaceSubnetMask OBJECT-TYPE
   SYNTAX      IpAddress
   MAX-ACCESS  read-only
   STATUS      current
   DESCRIPTION
       "Configure subnet mask of the DHCP address. "
   ::= {sm48tat4xarpDHCPServerStatusEntry 7 }

sm48tat4xarpDHCPServerStatusInterfaceDefaultRouter OBJECT-TYPE
   SYNTAX      IpAddress
   MAX-ACCESS  read-only
   STATUS      current
   DESCRIPTION
       "Configure the destination IP network or host address of the default route."
   ::= {sm48tat4xarpDHCPServerStatusEntry 8 }

sm48tat4xarpDHCPServerStatusInterfaceDNSServer OBJECT-TYPE
   SYNTAX      IpAddress
   MAX-ACCESS  read-only
   STATUS      current
   DESCRIPTION
       "Configure the default DNS server. "
   ::= {sm48tat4xarpDHCPServerStatusEntry 9 }

--sm48tat4xarpDHCPServerConf                                 OBJECT IDENTIFIER ::= { sm48tat4xarpDHCPServer 1 }
--
--sm48tat4xarpDHCPServerGlobalMode OBJECT-TYPE
--   SYNTAX      Integer32 (0|1)
--   MAX-ACCESS  read-write
--   STATUS      current
--   DESCRIPTION
--       "default: 0,
--        Global Mode :
--        0: Disable,
--        1: Enable.
--       "
--   ::= { sm48tat4xarpDHCPServerConf 1 }
--
--sm48tat4xarpDHCPServerVLANMode OBJECT-TYPE
--   SYNTAX      Integer32 (0|1)
--   MAX-ACCESS  read-write
--   STATUS      current
--   DESCRIPTION
--       "default: 0,
--        0: Disable,
--        1: Enable.
--       "
--   ::= { sm48tat4xarpDHCPServerConf 2 }
--
--sm48tat4xarpVLANModeTable OBJECT-TYPE
--   SYNTAX      SEQUENCE OF SM48TAT4XARPVLANModeEntry
--   MAX-ACCESS  not-accessible
--   STATUS      current
--   DESCRIPTION
--       "A table of VLAN Mode for DHCP Server."
--    ::= { sm48tat4xarpDHCPServerConf 2 }

--sm48tat4xarpVLANModeEntry OBJECT-TYPE
--    SYNTAX        SM48TAT4XARPVLANModeEntry
--    MAX-ACCESS    not-accessible
--    STATUS        current
--    DESCRIPTION
--        "An entry in the sm48tat4xarpVLANModeTable."
--    INDEX        { sm48tat4xarpVLANModeIndex }
--    ::= { sm48tat4xarpVLANModeTable 1 }
--
--SM48TAT4XARPVLANModeEntry ::=
--    SEQUENCE {
--        sm48tat4xarpVLANModeIndex                            Integer32,
--        sm48tat4xarpVLANModeRangeLow                         Integer32,
--        sm48tat4xarpVLANModeRangeHigh                        Integer32,
--        sm48tat4xarpVLANModeEnable                           Integer32,
--		sm48tat4xarpVLANModeRowStatus                        RowStatus
--    }
--
--sm48tat4xarpVLANModeIndex OBJECT-TYPE
--   SYNTAX      Integer32 (1..2048)
--   MAX-ACCESS  not-accessible
--   STATUS      current
--   DESCRIPTION
--       "VLAN Mode table index, range: 1-2048."
--   ::= {sm48tat4xarpVLANModeEntry 1 }
--
--sm48tat4xarpVLANModeRangeLow OBJECT-TYPE
--   SYNTAX      Integer32 (1..4095)
--   MAX-ACCESS  read-create
--   STATUS      current
--   DESCRIPTION
--       "VLAN Mode low range: 1-4095."
--   ::= {sm48tat4xarpVLANModeEntry 2 }
--
--sm48tat4xarpVLANModeRangeHigh OBJECT-TYPE
--   SYNTAX      Integer32 (1..4095)
--   MAX-ACCESS  read-create
--   STATUS      current
--   DESCRIPTION
--       "VLAN Mode high range: 1-4095."
--   ::= {sm48tat4xarpVLANModeEntry 3 }
--
--sm48tat4xarpVLANModeEnable OBJECT-TYPE
--   SYNTAX      Integer32 (0..1)
--   MAX-ACCESS  read-create
--   STATUS      current
--   DESCRIPTION
--       "VLAN Mode Enable, Enable:1, Disable:0."
--   ::= {sm48tat4xarpVLANModeEntry 4 }
--
--sm48tat4xarpVLANModeRowStatus OBJECT-TYPE
--   SYNTAX      RowStatus
--   MAX-ACCESS  read-create
--   STATUS      current
--   DESCRIPTION
--      "This object indicates the status of this entry, and is
--       used to create/delete entries.  Any object in an entry of
--       this table may be modified while the value of the
--       corresponding instance of this object is active(1).
--       createAndGo, notReady not supported."
--   ::= {     sm48tat4xarpVLANModeEntry 5 }
--


-- sm48tat4xarpDHCPServerBindingType OBJECT-TYPE
--   SYNTAX      Integer32 (0|1|2|3)
--   MAX-ACCESS  read-only
--   STATUS      current
--   DESCRIPTION
--       "default: None,
--        Global Mode :
--        0: None,
--        1: Automatic,
--        2: Manual,
--        3: Expired.
--       "
--   ::= { sm48tat4xarpDHCPServerConf 2 }

-- sm48tat4xarpDHCPServerBindingState OBJECT-TYPE
--   SYNTAX      Integer32 (0|1|2|3)
--   MAX-ACCESS  read-only
--   STATUS      current
--   DESCRIPTION
--       "default: None,
--        Global Mode :
--        0: None,
--        1: Allocated,
--        2: Committed,
--        3: Expired.
--       "
--   ::= { sm48tat4xarpDHCPServerConf 3 }

-- sm48tat4xarpDHCPServerBindingIP OBJECT-TYPE
--   SYNTAX      DisplayString
--   MAX-ACCESS  read-only
--   STATUS      current
--   DESCRIPTION
--       "The DHCP Server Binding IP"
--   ::= { sm48tat4xarpDHCPServerConf 4 }
--
--
--sm48tat4xarpDHCPServerExcludedIP                                 OBJECT IDENTIFIER ::= { sm48tat4xarpDHCPServer 2 }
--
--sm48tat4xarpExcludedIPTable OBJECT-TYPE
--   SYNTAX      SEQUENCE OF SM48TAT4XARPExcludedIPEntry
--   MAX-ACCESS  not-accessible
--   STATUS      current
--   DESCRIPTION
--       "A table of Excluded IP for DHCP Server."
--    ::= { sm48tat4xarpDHCPServerExcludedIP 1 }
--
--sm48tat4xarpExcludedIPEntry OBJECT-TYPE
--    SYNTAX        SM48TAT4XARPExcludedIPEntry
--    MAX-ACCESS    not-accessible
--    STATUS        current
--    DESCRIPTION
--        "An entry in the sm48tat4xarpExcludedIPTable."
--    INDEX        { sm48tat4xarpExcludedIPIndex }
--    ::= { sm48tat4xarpExcludedIPTable 1 }
--
--SM48TAT4XARPExcludedIPEntry ::=
--    SEQUENCE {
--        sm48tat4xarpExcludedIPIndex                            Integer32,
--        sm48tat4xarpExcludedIPRangeLow                         IpAddress,
--        sm48tat4xarpExcludedIPRangeHigh                        IpAddress,
--		sm48tat4xarpExcludedIPRowStatus                        RowStatus
--    }
--
--sm48tat4xarpExcludedIPIndex OBJECT-TYPE
--   SYNTAX      Integer32 (1..16)
--   MAX-ACCESS  not-accessible
--   STATUS      current
--   DESCRIPTION
--       "Excluded IP table index, range: 1-16."
--   ::= {sm48tat4xarpExcludedIPEntry 1 }
--
--sm48tat4xarpExcludedIPRangeLow OBJECT-TYPE
--   SYNTAX      IpAddress
--   MAX-ACCESS  read-create
--   STATUS      current
--   DESCRIPTION
--       "ExcludedIP low range."
--   ::= {sm48tat4xarpExcludedIPEntry 2 }
--
--sm48tat4xarpExcludedIPRangeHigh OBJECT-TYPE
--   SYNTAX      IpAddress
--   MAX-ACCESS  read-create
--   STATUS      current
--   DESCRIPTION
--       "ExcludedIP high range."
--   ::= {sm48tat4xarpExcludedIPEntry 3 }
--
--sm48tat4xarpExcludedIPRowStatus OBJECT-TYPE
--   SYNTAX      RowStatus
--   MAX-ACCESS  read-create
--   STATUS      current
--   DESCRIPTION
--      "This object indicates the status of this entry, and is
--       used to create/delete entries.  Any object in an entry of
--       this table may be modified while the value of the
--       corresponding instance of this object is active(1).
--       createAndGo, notReady not supported."
--   ::= {sm48tat4xarpExcludedIPEntry 4 }
--
--
--
--sm48tat4xarpDHCPServerPoolConf                                 OBJECT IDENTIFIER ::= { sm48tat4xarpDHCPServer 3 }
--
--sm48tat4xarpDHCPServerPoolTable OBJECT-TYPE
--   SYNTAX      SEQUENCE OF SM48TAT4XARPDHCPServerPoolEntry
--   MAX-ACCESS  not-accessible
--   STATUS      current
--   DESCRIPTION
--       "This is the entry information for DHCP Pool."
--   ::= { sm48tat4xarpDHCPServerPoolConf 1 }
--
--sm48tat4xarpDHCPServerPoolEntry OBJECT-TYPE
--   SYNTAX      SM48TAT4XARPDHCPServerPoolEntry
--   MAX-ACCESS  not-accessible
--   STATUS      current
--   DESCRIPTION
--       " "
--   INDEX    { sm48tat4xarpDHCPServerConfIndex  }
--   ::= { sm48tat4xarpDHCPServerPoolTable 1 }
--
--SM48TAT4XARPDHCPServerPoolEntry ::= SEQUENCE {
--    sm48tat4xarpDHCPServerConfIndex               Integer32,
--    sm48tat4xarpDHCPServerPoolName                DisplayString,
--    sm48tat4xarpDHCPServerPoolType                Integer32,
--    sm48tat4xarpDHCPServerIP                      IpAddress,
--    sm48tat4xarpDHCPServerSubnetMask              IpAddress,
--    sm48tat4xarpDHCPServerLeaseTimeDays           Integer32,
--    sm48tat4xarpDHCPServerLeaseTimeHours          Integer32,
--    sm48tat4xarpDHCPServerLeaseTimeMinutes        Integer32,
--    sm48tat4xarpDHCPServerDomainName              DisplayString,
--    sm48tat4xarpDHCPServerBroadcastAddress        IpAddress,
--    sm48tat4xarpDHCPServerDefRouter1              IpAddress,
--    sm48tat4xarpDHCPServerDefRouter2              IpAddress,
--    sm48tat4xarpDHCPServerDefRouter3              IpAddress,
--    sm48tat4xarpDHCPServerDefRouter4              IpAddress,
--    sm48tat4xarpDHCPServerDNSServer1              IpAddress,
--    sm48tat4xarpDHCPServerDNSServer2              IpAddress,
--    sm48tat4xarpDHCPServerDNSServer3              IpAddress,
--    sm48tat4xarpDHCPServerDNSServer4              IpAddress,
--    sm48tat4xarpDHCPServerNTPServer1              IpAddress,
--    sm48tat4xarpDHCPServerNTPServer2              IpAddress,
--    sm48tat4xarpDHCPServerNTPServer3              IpAddress,
--    sm48tat4xarpDHCPServerNTPServer4              IpAddress,
--    sm48tat4xarpDHCPServerNetbiosType             Integer32,
--    sm48tat4xarpDHCPServerNetbiosScope            DisplayString,
--    sm48tat4xarpDHCPServerNetbiosNameServer1      IpAddress,
--    sm48tat4xarpDHCPServerNetbiosNameServer2      IpAddress,
--    sm48tat4xarpDHCPServerNetbiosNameServer3      IpAddress,
--    sm48tat4xarpDHCPServerNetbiosNameServer4      IpAddress,
--    sm48tat4xarpDHCPServerNisDomainName           DisplayString,
--    sm48tat4xarpDHCPServerNisServer1              IpAddress,
--    sm48tat4xarpDHCPServerNisServer2              IpAddress,
--    sm48tat4xarpDHCPServerNisServer3              IpAddress,
--    sm48tat4xarpDHCPServerNisServer4              IpAddress,
--    sm48tat4xarpDHCPServerClientIDType            Integer32,
--    sm48tat4xarpDHCPServerClientID                DisplayString,
--    sm48tat4xarpDHCPServerHWAddr                  DisplayString,
--    sm48tat4xarpDHCPServerClientName              DisplayString,
--    sm48tat4xarpDHCPServerVendorClassID1          DisplayString,
--    sm48tat4xarpDHCPServerVendorSpecificInfo1     DisplayString,
--    sm48tat4xarpDHCPServerVendorClassID2          DisplayString,
--    sm48tat4xarpDHCPServerVendorSpecificInfo2     DisplayString,
--    sm48tat4xarpDHCPServerVendorClassID3          DisplayString,
--    sm48tat4xarpDHCPServerVendorSpecificInfo3     DisplayString,
--    sm48tat4xarpDHCPServerVendorClassID4          DisplayString,
--    sm48tat4xarpDHCPServerVendorSpecificInfo4     DisplayString,
--    sm48tat4xarpDHCPServerVendorClassID5          DisplayString,
--    sm48tat4xarpDHCPServerVendorSpecificInfo5     DisplayString,
--    sm48tat4xarpDHCPServerVendorClassID6          DisplayString,
--    sm48tat4xarpDHCPServerVendorSpecificInfo6     DisplayString,
--    sm48tat4xarpDHCPServerVendorClassID7          DisplayString,
--    sm48tat4xarpDHCPServerVendorSpecificInfo7     DisplayString,
--    sm48tat4xarpDHCPServerVendorClassID8          DisplayString,
--    sm48tat4xarpDHCPServerVendorSpecificInfo8     DisplayString,
--    sm48tat4xarpDHCPServerRowStatus               RowStatus
--}
--
--sm48tat4xarpDHCPServerConfIndex OBJECT-TYPE
--   SYNTAX      Integer32 (1..64)
--   MAX-ACCESS  not-accessible
--   STATUS      current
--   DESCRIPTION
--       " pool, range : 1 - 64. "
--   ::= { sm48tat4xarpDHCPServerPoolEntry 1 }
--
--sm48tat4xarpDHCPServerPoolName OBJECT-TYPE
--   SYNTAX      DisplayString(SIZE (1..32))
--   MAX-ACCESS  read-create
--   STATUS      current
--   DESCRIPTION
--       " DHCP pool name. "
--   ::= { sm48tat4xarpDHCPServerPoolEntry 2 }
--
--sm48tat4xarpDHCPServerPoolType OBJECT-TYPE
--   SYNTAX      Integer32(0|1|2)
--   MAX-ACCESS  read-create
--   STATUS      current
--   DESCRIPTION
--       " DHCP Server Pool Type.
--	   0:None
--	   1:Network
--	   2:Host, please set DHCP Server IP first."
--   ::= { sm48tat4xarpDHCPServerPoolEntry 3 }
--
--sm48tat4xarpDHCPServerIP OBJECT-TYPE
--   SYNTAX      IpAddress
--   MAX-ACCESS  read-create
--   STATUS      current
--   DESCRIPTION
--       " DHCP Server IP. "
--   ::= { sm48tat4xarpDHCPServerPoolEntry 4 }
--
--sm48tat4xarpDHCPServerSubnetMask OBJECT-TYPE
--   SYNTAX      IpAddress
--   MAX-ACCESS  read-create
--   STATUS      current
--   DESCRIPTION
--       " DHCP Server IPv4 Subnet Mask. "
--   ::= { sm48tat4xarpDHCPServerPoolEntry 5}
--
--sm48tat4xarpDHCPServerLeaseTimeDays OBJECT-TYPE
--   SYNTAX      Integer32(0..365)
--   MAX-ACCESS  read-create
--   STATUS      current
--   DESCRIPTION
--       " DHCP Server IPv4 Lease Time:Days. "
--   ::= { sm48tat4xarpDHCPServerPoolEntry 6 }
--
--sm48tat4xarpDHCPServerLeaseTimeHours OBJECT-TYPE
--   SYNTAX      Integer32(0..23)
--   MAX-ACCESS  read-create
--   STATUS      current
--   DESCRIPTION
--       " DHCP Server IPv4 Lease Time:Hours. "
--   ::= { sm48tat4xarpDHCPServerPoolEntry 7 }
--
--sm48tat4xarpDHCPServerLeaseTimeMinutes OBJECT-TYPE
--   SYNTAX      Integer32(0..59)
--   MAX-ACCESS  read-create
--   STATUS      current
--   DESCRIPTION
--       " DHCP Server IPv4 Lease Time:Minutes. "
--   ::= { sm48tat4xarpDHCPServerPoolEntry 8 }
--
--sm48tat4xarpDHCPServerDomainName OBJECT-TYPE
--   SYNTAX      DisplayString(SIZE (0..128))
--   MAX-ACCESS  read-create
--   STATUS      current
--   DESCRIPTION
--       " DHCP Server Domain Name. "
--   ::= { sm48tat4xarpDHCPServerPoolEntry 9 }
--
--sm48tat4xarpDHCPServerBroadcastAddress OBJECT-TYPE
--   SYNTAX      IpAddress
--   MAX-ACCESS  read-create
--   STATUS      current
--   DESCRIPTION
--       " DHCP Server IPv4 Broadcast Address. "
--   ::= { sm48tat4xarpDHCPServerPoolEntry 10 }
--
--sm48tat4xarpDHCPServerDefRouter1 OBJECT-TYPE
--   SYNTAX      IpAddress
--   MAX-ACCESS  read-create
--   STATUS      current
--   DESCRIPTION
--       " DHCP Server IPv4 Default Router 1. "
--   ::= { sm48tat4xarpDHCPServerPoolEntry 11 }
--
--sm48tat4xarpDHCPServerDefRouter2 OBJECT-TYPE
--   SYNTAX      IpAddress
--   MAX-ACCESS  read-create
--   STATUS      current
--   DESCRIPTION
--       " DHCP Server IPv4 Default Router 2. "
--   ::= { sm48tat4xarpDHCPServerPoolEntry 12 }
--
--sm48tat4xarpDHCPServerDefRouter3 OBJECT-TYPE
--   SYNTAX      IpAddress
--   MAX-ACCESS  read-create
--   STATUS      current
--   DESCRIPTION
--       " DHCP Server IPv4 Default Router 3. "
--   ::= { sm48tat4xarpDHCPServerPoolEntry 13 }
--
--sm48tat4xarpDHCPServerDefRouter4 OBJECT-TYPE
--   SYNTAX      IpAddress
--   MAX-ACCESS  read-create
--   STATUS      current
--   DESCRIPTION
--       " DHCP Server IPv4 Default Router 4. "
--   ::= { sm48tat4xarpDHCPServerPoolEntry 14 }
--
--sm48tat4xarpDHCPServerDNSServer1 OBJECT-TYPE
--   SYNTAX      IpAddress
--   MAX-ACCESS  read-create
--   STATUS      current
--   DESCRIPTION
--       " DHCP Server DNS Server 1. "
--   ::= { sm48tat4xarpDHCPServerPoolEntry 15 }
--
--sm48tat4xarpDHCPServerDNSServer2 OBJECT-TYPE
--   SYNTAX      IpAddress
--   MAX-ACCESS  read-create
--   STATUS      current
--   DESCRIPTION
--       " DHCP Server DNS Server 2. "
--   ::= { sm48tat4xarpDHCPServerPoolEntry 16 }
--
--sm48tat4xarpDHCPServerDNSServer3 OBJECT-TYPE
--   SYNTAX      IpAddress
--   MAX-ACCESS  read-create
--   STATUS      current
--   DESCRIPTION
--       " DHCP Server DNS Server 3. "
--   ::= { sm48tat4xarpDHCPServerPoolEntry 17 }
--
--sm48tat4xarpDHCPServerDNSServer4 OBJECT-TYPE
--   SYNTAX      IpAddress
--   MAX-ACCESS  read-create
--   STATUS      current
--   DESCRIPTION
--       " DHCP Server DNS Server 4. "
--   ::= { sm48tat4xarpDHCPServerPoolEntry 18 }
--
--sm48tat4xarpDHCPServerNTPServer1 OBJECT-TYPE
--   SYNTAX      IpAddress
--   MAX-ACCESS  read-create
--   STATUS      current
--   DESCRIPTION
--       " DHCP Server NTP Server 1. "
--   ::= { sm48tat4xarpDHCPServerPoolEntry 19 }
--
--sm48tat4xarpDHCPServerNTPServer2 OBJECT-TYPE
--   SYNTAX      IpAddress
--   MAX-ACCESS  read-create
--   STATUS      current
--   DESCRIPTION
--       " DHCP Server NTP Server 2. "
--   ::= { sm48tat4xarpDHCPServerPoolEntry 20 }
--
--sm48tat4xarpDHCPServerNTPServer3 OBJECT-TYPE
--   SYNTAX      IpAddress
--   MAX-ACCESS  read-create
--   STATUS      current
--   DESCRIPTION
--       " DHCP Server NTP Server 3. "
--   ::= { sm48tat4xarpDHCPServerPoolEntry 21 }
--
--sm48tat4xarpDHCPServerNTPServer4 OBJECT-TYPE
--   SYNTAX      IpAddress
--   MAX-ACCESS  read-create
--   STATUS      current
--   DESCRIPTION
--       " DHCP Server NTP Server 4. "
--   ::= { sm48tat4xarpDHCPServerPoolEntry 22 }
--
--sm48tat4xarpDHCPServerNetbiosType OBJECT-TYPE
--   SYNTAX      Integer32(1..4)
--   MAX-ACCESS  read-create
--   STATUS      current
--   DESCRIPTION
--       " DHCP Server Netbios Node Type.
--	   0:None
--	   1:B-node
--	   2:P-node
--	   3:M-node
--	   4:H-node"
--   ::= { sm48tat4xarpDHCPServerPoolEntry 23 }
--
--sm48tat4xarpDHCPServerNetbiosScope OBJECT-TYPE
--   SYNTAX      DisplayString(SIZE (0..128))
--   MAX-ACCESS  read-create
--   STATUS      current
--   DESCRIPTION
--       " DHCP Server Netbios Scope. "
--   ::= { sm48tat4xarpDHCPServerPoolEntry 24 }
--
--sm48tat4xarpDHCPServerNetbiosNameServer1 OBJECT-TYPE
--   SYNTAX      IpAddress
--   MAX-ACCESS  read-create
--   STATUS      current
--   DESCRIPTION
--       " DHCP Server Netbios Name Server 1. "
--   ::= { sm48tat4xarpDHCPServerPoolEntry 25 }
--
--sm48tat4xarpDHCPServerNetbiosNameServer2 OBJECT-TYPE
--   SYNTAX      IpAddress
--   MAX-ACCESS  read-create
--   STATUS      current
--   DESCRIPTION
--       " DHCP Server Netbios Name Server 2. "
--   ::= { sm48tat4xarpDHCPServerPoolEntry 26 }
--
--sm48tat4xarpDHCPServerNetbiosNameServer3 OBJECT-TYPE
--   SYNTAX      IpAddress
--   MAX-ACCESS  read-create
--   STATUS      current
--   DESCRIPTION
--       " DHCP Server Netbios Name Server 3. "
--   ::= { sm48tat4xarpDHCPServerPoolEntry 27 }
--
--sm48tat4xarpDHCPServerNetbiosNameServer4 OBJECT-TYPE
--   SYNTAX      IpAddress
--   MAX-ACCESS  read-create
--   STATUS      current
--   DESCRIPTION
--       " DHCP Server Netbios Name Server 4. "
--   ::= { sm48tat4xarpDHCPServerPoolEntry 28 }
--
--sm48tat4xarpDHCPServerNisDomainName OBJECT-TYPE
--   SYNTAX      DisplayString(SIZE (0..128))
--   MAX-ACCESS  read-create
--   STATUS      current
--   DESCRIPTION
--       " DHCP Server Nis Domain Name. "
--   ::= { sm48tat4xarpDHCPServerPoolEntry 29 }
--
--sm48tat4xarpDHCPServerNisServer1 OBJECT-TYPE
--   SYNTAX      IpAddress
--   MAX-ACCESS  read-create
--   STATUS      current
--   DESCRIPTION
--       " DHCP Server Nis Server 1. "
--   ::= { sm48tat4xarpDHCPServerPoolEntry 30 }
--
--sm48tat4xarpDHCPServerNisServer2 OBJECT-TYPE
--   SYNTAX      IpAddress
--   MAX-ACCESS  read-create
--   STATUS      current
--   DESCRIPTION
--       " DHCP Server Nis Server 2. "
--   ::= { sm48tat4xarpDHCPServerPoolEntry 31 }
--
--sm48tat4xarpDHCPServerNisServer3 OBJECT-TYPE
--   SYNTAX      IpAddress
--   MAX-ACCESS  read-create
--   STATUS      current
--   DESCRIPTION
--       " DHCP Server Nis Server 3. "
--   ::= { sm48tat4xarpDHCPServerPoolEntry 32 }
--
--sm48tat4xarpDHCPServerNisServer4 OBJECT-TYPE
--   SYNTAX      IpAddress
--   MAX-ACCESS  read-create
--   STATUS      current
--   DESCRIPTION
--       " DHCP Server Nis Server 4. "
--   ::= { sm48tat4xarpDHCPServerPoolEntry 33 }
--
--sm48tat4xarpDHCPServerClientIDType OBJECT-TYPE
--   SYNTAX      Integer32(0..2)
--   MAX-ACCESS  read-create
--   STATUS      current
--   DESCRIPTION
--       " DHCP Server Client ID Type.
--	   0:None
--	   1:FQDN
--	   2:MAC"
--   ::= { sm48tat4xarpDHCPServerPoolEntry 34 }
--
--sm48tat4xarpDHCPServerClientID OBJECT-TYPE
--   SYNTAX      DisplayString(SIZE (0..128))
--   MAX-ACCESS  read-create
--   STATUS      current
--   DESCRIPTION
--       " DHCP Server Pool Client ID. "
--   ::= { sm48tat4xarpDHCPServerPoolEntry 35 }
--
--sm48tat4xarpDHCPServerHWAddr OBJECT-TYPE
--   SYNTAX      DisplayString(SIZE (0..17))
--   MAX-ACCESS  read-create
--   STATUS      current
--   DESCRIPTION
--       " DHCP Server Pool Hardware Address. "
--   ::= { sm48tat4xarpDHCPServerPoolEntry 36 }
--
--sm48tat4xarpDHCPServerClientName OBJECT-TYPE
--   SYNTAX      DisplayString(SIZE (0..32))
--   MAX-ACCESS  read-create
--   STATUS      current
--   DESCRIPTION
--       " DHCP Server Pool Client Name. "
--   ::= { sm48tat4xarpDHCPServerPoolEntry 37 }
--
--sm48tat4xarpDHCPServerVendorClassID1 OBJECT-TYPE
--   SYNTAX      DisplayString(SIZE (0..64))
--   MAX-ACCESS  read-create
--   STATUS      current
--   DESCRIPTION
--       " DHCP Server Vendor Class ID 1. Please also set VendorSpecificInfo1."
--   ::= { sm48tat4xarpDHCPServerPoolEntry 38 }
--
--sm48tat4xarpDHCPServerVendorSpecificInfo1 OBJECT-TYPE
--   SYNTAX      DisplayString(SIZE (0..32))
--   MAX-ACCESS  read-create
--   STATUS      current
--   DESCRIPTION
--       " DHCP Server Vendor Specific Info 1. Please also set VendorClassID1."
--   ::= { sm48tat4xarpDHCPServerPoolEntry 39 }
--
--sm48tat4xarpDHCPServerVendorClassID2 OBJECT-TYPE
--   SYNTAX      DisplayString(SIZE (0..64))
--   MAX-ACCESS  read-create
--   STATUS      current
--   DESCRIPTION
--       " DHCP Server Vendor Class ID 2. Please also set VendorSpecificInfo2."
--   ::= { sm48tat4xarpDHCPServerPoolEntry 40 }
--
--sm48tat4xarpDHCPServerVendorSpecificInfo2 OBJECT-TYPE
--   SYNTAX      DisplayString(SIZE (0..32))
--   MAX-ACCESS  read-create
--   STATUS      current
--   DESCRIPTION
--       " DHCP Server Vendor Specific Info 2. Please also set VendorClassID2."
--   ::= { sm48tat4xarpDHCPServerPoolEntry 41 }
--
--sm48tat4xarpDHCPServerVendorClassID3 OBJECT-TYPE
--   SYNTAX      DisplayString(SIZE (0..64))
--   MAX-ACCESS  read-create
--   STATUS      current
--   DESCRIPTION
--       " DHCP Server Vendor Class ID 3. Please also set VendorSpecificInfo3."
--   ::= { sm48tat4xarpDHCPServerPoolEntry 42 }
--
--sm48tat4xarpDHCPServerVendorSpecificInfo3 OBJECT-TYPE
--   SYNTAX      DisplayString(SIZE (0..32))
--   MAX-ACCESS  read-create
--   STATUS      current
--   DESCRIPTION
--       " DHCP Server Vendor Specific Info 3. Please also set VendorClassID3."
--   ::= { sm48tat4xarpDHCPServerPoolEntry 43 }
--
--sm48tat4xarpDHCPServerVendorClassID4 OBJECT-TYPE
--   SYNTAX      DisplayString(SIZE (0..64))
--   MAX-ACCESS  read-create
--   STATUS      current
--   DESCRIPTION
--       " DHCP Server Vendor Class ID 4. Please also set VendorSpecificInfo4."
--   ::= { sm48tat4xarpDHCPServerPoolEntry 44 }
--
--sm48tat4xarpDHCPServerVendorSpecificInfo4 OBJECT-TYPE
--   SYNTAX      DisplayString(SIZE (0..32))
--   MAX-ACCESS  read-create
--   STATUS      current
--   DESCRIPTION
--       " DHCP Server Vendor Specific Info 4. Please also set VendorClassID4."
--   ::= { sm48tat4xarpDHCPServerPoolEntry 45 }
--
--sm48tat4xarpDHCPServerVendorClassID5 OBJECT-TYPE
--   SYNTAX      DisplayString(SIZE (0..64))
--   MAX-ACCESS  read-create
--   STATUS      current
--   DESCRIPTION
--       " DHCP Server Vendor Class ID 5. Please also set VendorSpecificInfo5."
--   ::= { sm48tat4xarpDHCPServerPoolEntry 46 }
--
--sm48tat4xarpDHCPServerVendorSpecificInfo5 OBJECT-TYPE
--   SYNTAX      DisplayString(SIZE (0..32))
--   MAX-ACCESS  read-create
--   STATUS      current
--   DESCRIPTION
--       " DHCP Server Vendor Specific Info 5. Please also set VendorClassID5."
--   ::= { sm48tat4xarpDHCPServerPoolEntry 47 }
--
--sm48tat4xarpDHCPServerVendorClassID6 OBJECT-TYPE
--   SYNTAX      DisplayString(SIZE (0..64))
--   MAX-ACCESS  read-create
--   STATUS      current
--   DESCRIPTION
--       " DHCP Server Vendor Class ID 6. Please also set VendorSpecificInfo6."
--   ::= { sm48tat4xarpDHCPServerPoolEntry 48 }
--
--sm48tat4xarpDHCPServerVendorSpecificInfo6 OBJECT-TYPE
--   SYNTAX      DisplayString(SIZE (0..32))
--   MAX-ACCESS  read-create
--   STATUS      current
--   DESCRIPTION
--       " DHCP Server Vendor Specific Info 6. Please also set VendorClassID6."
--   ::= { sm48tat4xarpDHCPServerPoolEntry 49 }
--
--sm48tat4xarpDHCPServerVendorClassID7 OBJECT-TYPE
--   SYNTAX      DisplayString(SIZE (0..64))
--   MAX-ACCESS  read-create
--   STATUS      current
--   DESCRIPTION
--       " DHCP Server Vendor Class ID 7. Please also set VendorSpecificInfo7."
--   ::= { sm48tat4xarpDHCPServerPoolEntry 50 }
--
--sm48tat4xarpDHCPServerVendorSpecificInfo7 OBJECT-TYPE
--   SYNTAX      DisplayString(SIZE (0..32))
--   MAX-ACCESS  read-create
--   STATUS      current
--   DESCRIPTION
--       " DHCP Server Vendor Specific Info 7. Please also set VendorClassID7."
--   ::= { sm48tat4xarpDHCPServerPoolEntry 51 }
--
--sm48tat4xarpDHCPServerVendorClassID8 OBJECT-TYPE
--   SYNTAX      DisplayString(SIZE (0..64))
--   MAX-ACCESS  read-create
--   STATUS      current
--   DESCRIPTION
--       " DHCP Server Vendor Class ID 8. Please also set VendorSpecificInfo8."
--   ::= { sm48tat4xarpDHCPServerPoolEntry 52 }
--
--sm48tat4xarpDHCPServerVendorSpecificInfo8 OBJECT-TYPE
--   SYNTAX      DisplayString(SIZE (0..32))
--   MAX-ACCESS  read-create
--   STATUS      current
--   DESCRIPTION
--       " DHCP Server Vendor Specific Info 8. Please also set VendorClassID8."
--   ::= { sm48tat4xarpDHCPServerPoolEntry 53 }
--
--sm48tat4xarpDHCPServerRowStatus OBJECT-TYPE
--   SYNTAX      RowStatus
--   MAX-ACCESS  read-create
--   STATUS      current
--   DESCRIPTION
--      "This object indicates the status of this entry, and is
--       used to create/delete entries.  Any object in an entry of
--       this table may be modified while the value of the
--       corresponding instance of this object is active(1).
--       createAndGo, notReady not supported."
--   ::= {sm48tat4xarpDHCPServerPoolEntry 54 }
--
--sm48tat4xarpDHCPServerStatistics                         OBJECT IDENTIFIER ::= { sm48tat4xarpDHCPServer 4 }
--
--sm48tat4xarpDHCPServerStatisticsDatabaseCountersPool OBJECT-TYPE
--   SYNTAX      Integer32
--   MAX-ACCESS  read-only
--   STATUS      current
--   DESCRIPTION
--       "
--       "
--   ::= { sm48tat4xarpDHCPServerStatistics 1 }
--
--sm48tat4xarpDHCPServerStatisticsDatabaseCountersExcludedIPAddress OBJECT-TYPE
--   SYNTAX      Integer32
--   MAX-ACCESS  read-only
--   STATUS      current
--   DESCRIPTION
--       "
--       "
--   ::= { sm48tat4xarpDHCPServerStatistics 2 }
--
--sm48tat4xarpDHCPServerStatisticsDatabaseCountersDeclinedIPAddress OBJECT-TYPE
--   SYNTAX      Integer32
--   MAX-ACCESS  read-only
--   STATUS      current
--   DESCRIPTION
--       "
--       "
--   ::= { sm48tat4xarpDHCPServerStatistics 3 }
--
--sm48tat4xarpDHCPServerStatisticsBindingCountersAutomaticBinding OBJECT-TYPE
--   SYNTAX      Integer32
--   MAX-ACCESS  read-only
--   STATUS      current
--   DESCRIPTION
--       "
--       "
--   ::= { sm48tat4xarpDHCPServerStatistics 4 }
--
--sm48tat4xarpDHCPServerStatisticsBindingCountersManualBinding OBJECT-TYPE
--   SYNTAX      Integer32
--   MAX-ACCESS  read-only
--   STATUS      current
--   DESCRIPTION
--       "
--       "
--   ::= { sm48tat4xarpDHCPServerStatistics 5 }
--
--sm48tat4xarpDHCPServerStatisticsBindingCountersExpiredBinding OBJECT-TYPE
--   SYNTAX      Integer32
--   MAX-ACCESS  read-only
--   STATUS      current
--   DESCRIPTION
--       "
--       "
--   ::= { sm48tat4xarpDHCPServerStatistics 6 }
--
--sm48tat4xarpDHCPServerStatisticsDHCPMessageReceivedCountersDISCOVER OBJECT-TYPE
--   SYNTAX      Integer32
--   MAX-ACCESS  read-only
--   STATUS      current
--   DESCRIPTION
--       "
--       "
--   ::= { sm48tat4xarpDHCPServerStatistics 7 }
--
--sm48tat4xarpDHCPServerStatisticsDHCPMessageReceivedCountersREQUEST OBJECT-TYPE
--   SYNTAX      Integer32
--   MAX-ACCESS  read-only
--   STATUS      current
--   DESCRIPTION
--       "
--       "
--   ::= { sm48tat4xarpDHCPServerStatistics 8 }
--
--sm48tat4xarpDHCPServerStatisticsDHCPMessageReceivedCountersDECLINE OBJECT-TYPE
--   SYNTAX      Integer32
--   MAX-ACCESS  read-only
--   STATUS      current
--   DESCRIPTION
--       "
--       "
--   ::= { sm48tat4xarpDHCPServerStatistics 9 }
--
--sm48tat4xarpDHCPServerStatisticsDHCPMessageReceivedCountersRELEASE OBJECT-TYPE
--   SYNTAX      Integer32
--   MAX-ACCESS  read-only
--   STATUS      current
--   DESCRIPTION
--       "
--       "
--   ::= { sm48tat4xarpDHCPServerStatistics 10 }
--
--sm48tat4xarpDHCPServerStatisticsDHCPMessageReceivedCountersINFORM OBJECT-TYPE
--   SYNTAX      Integer32
--   MAX-ACCESS  read-only
--   STATUS      current
--   DESCRIPTION
--       "
--       "
--   ::= { sm48tat4xarpDHCPServerStatistics 11 }
--
--sm48tat4xarpDHCPServerStatisticsDHCPMessageSentCountersOFFER OBJECT-TYPE
--   SYNTAX      Integer32
--   MAX-ACCESS  read-only
--   STATUS      current
--   DESCRIPTION
--       "
--       "
--   ::= { sm48tat4xarpDHCPServerStatistics 12 }
--
--sm48tat4xarpDHCPServerStatisticsDHCPMessageSentCountersACK OBJECT-TYPE
--   SYNTAX      Integer32
--   MAX-ACCESS  read-only
--   STATUS      current
--   DESCRIPTION
--       "
--       "
--   ::= { sm48tat4xarpDHCPServerStatistics 13 }
--
--sm48tat4xarpDHCPServerStatisticsDHCPMessageSentCountersNAK OBJECT-TYPE
--   SYNTAX      Integer32
--   MAX-ACCESS  read-only
--   STATUS      current
--   DESCRIPTION
--       "
--       "
--   ::= { sm48tat4xarpDHCPServerStatistics 14 }
--
--sm48tat4xarpDHCPServerClear OBJECT-TYPE
--   SYNTAX      Integer32
--   MAX-ACCESS  read-write
--   STATUS      current
--   DESCRIPTION
--       "
--       "
--   ::= { sm48tat4xarpDHCPServerStatistics 15 }
--
--sm48tat4xarpDHCPServerBinding                         OBJECT IDENTIFIER ::= { sm48tat4xarpDHCPServer 5 }
--
--sm48tat4xarpDHCPServerBindingTable OBJECT-TYPE
--   SYNTAX      SEQUENCE OF SM48TAT4XARPDHCPServerBindingEntry
--   MAX-ACCESS  not-accessible
--   STATUS      current
--   DESCRIPTION
--       " "
--   ::= { sm48tat4xarpDHCPServerBinding 1 }
--
--sm48tat4xarpDHCPServerBindingEntry OBJECT-TYPE
--   SYNTAX      SM48TAT4XARPDHCPServerBindingEntry
--   MAX-ACCESS  not-accessible
--   STATUS      current
--   DESCRIPTION
--       " "
--   INDEX    { sm48tat4xarpDHCPServerBindingIndex  }
--   ::= { sm48tat4xarpDHCPServerBindingTable 1 }
--
--SM48TAT4XARPDHCPServerBindingEntry ::= SEQUENCE {
--   sm48tat4xarpDHCPServerBindingIndex                 Integer32,
--   sm48tat4xarpDHCPServerBindingIP                    DisplayString,
--   sm48tat4xarpDHCPServerBindingType                  DisplayString,
--   sm48tat4xarpDHCPServerBindingState                 DisplayString,
--   sm48tat4xarpDHCPServerBindingPoolName              DisplayString,
--   sm48tat4xarpDHCPServerBindingServerID              DisplayString,
--   sm48tat4xarpDHCPServerBindingVLAN                  Integer32,
--   sm48tat4xarpDHCPServerBindingSubnetMask            DisplayString,
--   sm48tat4xarpDHCPServerBindingClientIDType          DisplayString,
--   sm48tat4xarpDHCPServerBindingClientIDValue         DisplayString,
--   sm48tat4xarpDHCPServerBindingMACAddress            DisplayString,
--   sm48tat4xarpDHCPServerBindingLeaseTime             DisplayString,
--   sm48tat4xarpDHCPServerBindingWillExpiredIn         DisplayString,
--   sm48tat4xarpDHCPServerBindingDelete                Integer32
--}
--
--sm48tat4xarpDHCPServerBindingIndex OBJECT-TYPE
--   SYNTAX      Integer32
--   MAX-ACCESS  not-accessible
--   STATUS      current
--   DESCRIPTION
--       "Index"
--   ::= { sm48tat4xarpDHCPServerBindingEntry 1 }
--
--sm48tat4xarpDHCPServerBindingIP OBJECT-TYPE
--   SYNTAX      DisplayString
--   MAX-ACCESS  read-only
--   STATUS      current
--   DESCRIPTION
--       " "
--   ::= { sm48tat4xarpDHCPServerBindingEntry 2 }
--
--sm48tat4xarpDHCPServerBindingType OBJECT-TYPE
--   SYNTAX      DisplayString
--   MAX-ACCESS  read-only
--   STATUS      current
--   DESCRIPTION
--       " "
--   ::= { sm48tat4xarpDHCPServerBindingEntry 3 }
--
--sm48tat4xarpDHCPServerBindingState OBJECT-TYPE
--   SYNTAX      DisplayString
--   MAX-ACCESS  read-only
--   STATUS      current
--   DESCRIPTION
--       " "
--   ::= { sm48tat4xarpDHCPServerBindingEntry 4 }
--
--sm48tat4xarpDHCPServerBindingPoolName OBJECT-TYPE
--   SYNTAX      DisplayString
--   MAX-ACCESS  read-only
--   STATUS      current
--   DESCRIPTION
--       " "
--   ::= { sm48tat4xarpDHCPServerBindingEntry 5 }
--
--sm48tat4xarpDHCPServerBindingServerID OBJECT-TYPE
--   SYNTAX      DisplayString
--   MAX-ACCESS  read-only
--   STATUS      current
--   DESCRIPTION
--       " "
--   ::= { sm48tat4xarpDHCPServerBindingEntry 6 }
--
--sm48tat4xarpDHCPServerBindingVLAN OBJECT-TYPE
--   SYNTAX      Integer32
--   MAX-ACCESS  read-only
--   STATUS      current
--   DESCRIPTION
--       " "
--   ::= { sm48tat4xarpDHCPServerBindingEntry 7 }
--
--sm48tat4xarpDHCPServerBindingSubnetMask OBJECT-TYPE
--   SYNTAX      DisplayString
--   MAX-ACCESS  read-only
--   STATUS      current
--   DESCRIPTION
--       " "
--   ::= { sm48tat4xarpDHCPServerBindingEntry 8 }
--
--sm48tat4xarpDHCPServerBindingClientIDType OBJECT-TYPE
--   SYNTAX      DisplayString
--   MAX-ACCESS  read-only
--   STATUS      current
--   DESCRIPTION
--       " "
--   ::= { sm48tat4xarpDHCPServerBindingEntry 9 }
--
--sm48tat4xarpDHCPServerBindingClientIDValue OBJECT-TYPE
--   SYNTAX      DisplayString
--   MAX-ACCESS  read-only
--   STATUS      current
--   DESCRIPTION
--       " "
--   ::= { sm48tat4xarpDHCPServerBindingEntry 10 }
--
--sm48tat4xarpDHCPServerBindingMACAddress OBJECT-TYPE
--   SYNTAX      DisplayString
--   MAX-ACCESS  read-only
--   STATUS      current
--   DESCRIPTION
--       " "
--   ::= { sm48tat4xarpDHCPServerBindingEntry 11 }
--
--sm48tat4xarpDHCPServerBindingLeaseTime OBJECT-TYPE
--   SYNTAX      DisplayString
--   MAX-ACCESS  read-only
--   STATUS      current
--   DESCRIPTION
--       " "
--   ::= { sm48tat4xarpDHCPServerBindingEntry 12 }
--
--sm48tat4xarpDHCPServerBindingWillExpiredIn OBJECT-TYPE
--   SYNTAX      DisplayString
--   MAX-ACCESS  read-only
--   STATUS      current
--   DESCRIPTION
--       " "
--   ::= { sm48tat4xarpDHCPServerBindingEntry 13 }
--
--sm48tat4xarpDHCPServerBindingDelete OBJECT-TYPE
--   SYNTAX      Integer32
--   MAX-ACCESS  read-write
--   STATUS      current
--   DESCRIPTION
--       " "
--   ::= { sm48tat4xarpDHCPServerBindingEntry 14 }
--
--sm48tat4xarpDHCPServerBindingClearAutomatic   OBJECT-TYPE
--   SYNTAX      Integer32
--   MAX-ACCESS  read-write
--   STATUS      current
--   DESCRIPTION
--	   "1:clear"
--   ::= { sm48tat4xarpDHCPServerBinding 2 }
--
--sm48tat4xarpDHCPServerBindingClearManual   OBJECT-TYPE
--   SYNTAX      Integer32
--   MAX-ACCESS  read-write
--   STATUS      current
--   DESCRIPTION
--	   "1:clear"
--   ::= { sm48tat4xarpDHCPServerBinding 3 }
--
--sm48tat4xarpDHCPServerBindingClearExpired   OBJECT-TYPE
--   SYNTAX      Integer32
--   MAX-ACCESS  read-write
--   STATUS      current
--   DESCRIPTION
--	   "1:clear"
--   ::= { sm48tat4xarpDHCPServerBinding 4 }
--
--sm48tat4xarpDHCPServerDeclined                         OBJECT IDENTIFIER ::= { sm48tat4xarpDHCPServer 6 }
--
--sm48tat4xarpDHCPServerDeclinedTable OBJECT-TYPE
--   SYNTAX      SEQUENCE OF SM48TAT4XARPDHCPServerDeclinedEntry
--   MAX-ACCESS  not-accessible
--   STATUS      current
--   DESCRIPTION
--       " "
--   ::= { sm48tat4xarpDHCPServerDeclined 1 }
--
--sm48tat4xarpDHCPServerDeclinedEntry OBJECT-TYPE
--   SYNTAX      SM48TAT4XARPDHCPServerDeclinedEntry
--   MAX-ACCESS  not-accessible
--   STATUS      current
--   DESCRIPTION
--       " "
--   INDEX    { sm48tat4xarpDHCPServerDeclinedIndex  }
--   ::= { sm48tat4xarpDHCPServerDeclinedTable 1 }
--
--SM48TAT4XARPDHCPServerDeclinedEntry ::= SEQUENCE {
--   sm48tat4xarpDHCPServerDeclinedIndex                 Integer32,
--   sm48tat4xarpDHCPServerDeclinedIP                    DisplayString
--}
--
--sm48tat4xarpDHCPServerDeclinedIndex OBJECT-TYPE
--   SYNTAX      Integer32
--   MAX-ACCESS  not-accessible
--   STATUS      current
--   DESCRIPTION
--       "Index"
--   ::= { sm48tat4xarpDHCPServerDeclinedEntry 1 }
--
--sm48tat4xarpDHCPServerDeclinedIP OBJECT-TYPE
--   SYNTAX      DisplayString
--   MAX-ACCESS  read-only
--   STATUS      current
--   DESCRIPTION
--       " "
--   ::= { sm48tat4xarpDHCPServerDeclinedEntry 2 }

-- =======================================================================================================================
sm48tat4xarpVLANConf                                     OBJECT IDENTIFIER ::= { sm48tat4xarpSystem 10 }

sm48tat4xarpVLAN                                     OBJECT IDENTIFIER ::= { sm48tat4xarpVLANConf 2}

sm48tat4xarpVlanStatus              OBJECT IDENTIFIER   ::= { sm48tat4xarpVLAN 6 }

--
-- =======================================================================================================================
-- Start sm48tat4xarpVlan group
-- =======================================================================================================================
    sm48tat4xarpVlanExistingVLANs  OBJECT-TYPE
               SYNTAX      DisplayString
               MAX-ACCESS  read-write
               STATUS      current
               DESCRIPTION
                   "This field shows the VLANs that are created on the switch.
                    More VLANs may be created by using a
                    list syntax where the individual elements are separated by commas.
                    Ranges are specified with a
                    dash separating the lower and upper bound.
                    The following example will create VLANs 1, 10, 11, 12
                    , 13, 200, and 300: 1,10-13,200,300.
                    default: 1."
               ::= {     sm48tat4xarpVLAN 1 }

    sm48tat4xarpVlanEthertypeforCustomSPorts  OBJECT-TYPE
               SYNTAX      DisplayString
               MAX-ACCESS  read-write
               STATUS      current
               DESCRIPTION
                   "This field specifies the ethertype/TPID (specified in hexadecimal)
                    used for Custom S-ports. The
                    setting is in force for all ports whose Port Type
                    is set to S-Custom-Port.
                    range: 0600-ffff,
                    default: 88a8."
               ::= {     sm48tat4xarpVLAN 2 }

    sm48tat4xarpVlanTable OBJECT-TYPE
               SYNTAX      SEQUENCE OF     SM48TAT4XARPVlanEntry
               MAX-ACCESS  not-accessible
               STATUS      current
               DESCRIPTION
                   "Configure Vlan ports Configuration mode.
                    INDEX for this table is ifIndex which is
                    equivalent to the panel port number."
               ::= {     sm48tat4xarpVLAN 3 }

    sm48tat4xarpVlanEntry OBJECT-TYPE
               SYNTAX          SM48TAT4XARPVlanEntry
               MAX-ACCESS  not-accessible
               STATUS      current
               DESCRIPTION
                   "The Vlan entry."
               INDEX    {     ifIndex  }
               ::= {     sm48tat4xarpVlanTable 1 }

    SM48TAT4XARPVlanEntry             ::= SEQUENCE {
                sm48tat4xarpVlanMode              INTEGER,
                sm48tat4xarpVlanPortVLAN          Integer32,
                sm48tat4xarpVlanPortType          INTEGER,
                sm48tat4xarpVlanIngressFiltering  AdminMode,
--              sm48tat4xarpVlanVLANTrunking      AdminMode,
                sm48tat4xarpVlanIngressAcceptance INTEGER,
                sm48tat4xarpVlanEgressTagging     INTEGER,
                sm48tat4xarpVlanAllowedVLANs      DisplayString,
                sm48tat4xarpVlanForbiddenVLANs    DisplayString
                }

    sm48tat4xarpVlanMode OBJECT-TYPE
               SYNTAX      INTEGER{access(0), trunk(1), hybrid(2)}
               MAX-ACCESS  read-write
               STATUS      current
               DESCRIPTION
                   "The port mode determines the fundamental
                    behavior of the port in question.
                    A port can be in one of three modes as described below.
                    0: access,
                    1: trunk,
                    2: hybrid."
               DEFVAL  { access }
               ::= {     sm48tat4xarpVlanEntry 2 }

    sm48tat4xarpVlanPortVLAN OBJECT-TYPE
               SYNTAX      Integer32(1..4094)
               MAX-ACCESS  read-write
               STATUS      current
               DESCRIPTION
                   "Determines the port's VLAN ID (a.k.a. PVID).
                    range: 1-4095,
                    default: 1."
               ::= {     sm48tat4xarpVlanEntry 3 }

    sm48tat4xarpVlanPortType OBJECT-TYPE
               SYNTAX      INTEGER { unaware(0), cPort(1), sPort(2), sCustomPort(3) }
               MAX-ACCESS  read-write
               STATUS      current
               DESCRIPTION
                   "Ports in hybrid mode allow for changing the port type,
                    that is, whether a frame's VLAN tag is
                    used to classify the frame on ingress to a particular VLAN,
                    and if so, which TPID it reacts on.
                    Likewise, on egress, the Port Type determines the
                    TPID of the tag, if a tag is required.
                    0: unaware,
                    1: c-Port,
                    2: s-Port,
                    3: s-Custom-Port."
                DEFVAL  { cPort }
               ::= {     sm48tat4xarpVlanEntry 4 }

    sm48tat4xarpVlanIngressFiltering OBJECT-TYPE
               SYNTAX      AdminMode
               MAX-ACCESS  read-write
               STATUS      current
               DESCRIPTION
                   "Hybrid ports allow for changing ingress filtering.
                    Access and Trunk ports always have ingress
                    filtering enabled.If ingress filtering is enabled,
                    frames classified to
                    a VLAN that the port is not a member of get discarded."
               ::= {     sm48tat4xarpVlanEntry 5 }

--    sm48tat4xarpVlanVLANTrunking OBJECT-TYPE
--               SYNTAX      AdminMode
--               MAX-ACCESS  read-write
--               STATUS      current
--               DESCRIPTION
--                   "Trunk and Hybrid ports allow for enabling VLAN trunking.
--                    When VLAN trunking is enabled, frames
--                    classified to unknown VLANs are accepted on the port
--                    whether ingress filtering is enabled or not."
--               DEFVAL  { disable }
--               ::= {     sm48tat4xarpVlanEntry 6 }

    sm48tat4xarpVlanIngressAcceptance OBJECT-TYPE
               SYNTAX      INTEGER  { taggedAndUntagged  ( 0 ),
                                      taggedOnly ( 1 ),
                                      untaggedOnly ( 2 )
                                    }
               MAX-ACCESS  read-write
               STATUS      current
               DESCRIPTION
                   "Hybrid ports allow for changing the type of frames that are
                    accepted on ingress.
                    0: Tagged and Untagged,
                    1: Tagged Only,
                    2: Untagged Only."
               ::= {     sm48tat4xarpVlanEntry 7 }

    sm48tat4xarpVlanEgressTagging OBJECT-TYPE
               SYNTAX      INTEGER  { untagPortVlan  ( 0 ),
                                      tagAll ( 1 ),
                                      untagAll ( 2 )
                                    }
               MAX-ACCESS  read-write
               STATUS      current
               DESCRIPTION
                   "Ports in Trunk and Hybrid mode may control the
                    tagging of frames on egress.
                    0: Untag Port VLAN,
                    1: Tag All,
                    2: Untag All."
               ::= {     sm48tat4xarpVlanEntry 8 }

    sm48tat4xarpVlanAllowedVLANs OBJECT-TYPE
               SYNTAX      DisplayString
               MAX-ACCESS  read-write
               STATUS      current
               DESCRIPTION
                   "Ports in Trunk and Hybrid mode may control which
                    VLANs they are allowed to become members of.
                    Access ports can only be member of one VLAN, the Access VLAN.
                    range: 1~4095.
                    '-': Allowed VLANs is empty."
               ::= {     sm48tat4xarpVlanEntry 9 }

    sm48tat4xarpVlanForbiddenVLANs OBJECT-TYPE
               SYNTAX      DisplayString
               MAX-ACCESS  read-write
               STATUS      current
               DESCRIPTION
                   "A port may be configured to never be member of one or
                    more VLANs. This is particularly useful
                    when dynamic VLAN protocols like MVRP and GVRP
                    must be prevented from dynamically adding ports
                    to VLANs.
                    range: 1~4095.
                    '-': Forbidden VLANs is empty."
               ::= {     sm48tat4xarpVlanEntry 10 }

--sm48tat4xarpVLANMembershipStatusTable

    sm48tat4xarpVLANMembershipStatusTable OBJECT-TYPE
               SYNTAX      SEQUENCE OF     SM48TAT4XARPVLANMembershipStatusEntry
               MAX-ACCESS  not-accessible
               STATUS      current
               DESCRIPTION
                   "Vlan membership Status table.
                    INDEX for this table is ifIndex which is
                    equivalent to the panel port number."
               ::= {     sm48tat4xarpVlanStatus 1 }

    sm48tat4xarpVLANMembershipStatusEntry OBJECT-TYPE
               SYNTAX          SM48TAT4XARPVLANMembershipStatusEntry
               MAX-ACCESS  not-accessible
               STATUS      current
               DESCRIPTION
                   "Vlan membership Status entry."
               INDEX    {     ifIndex, sm48tat4xarpVLANMembershipVlanID    }
               ::= {     sm48tat4xarpVLANMembershipStatusTable 1 }

    SM48TAT4XARPVLANMembershipStatusEntry             ::= SEQUENCE {
                sm48tat4xarpVLANMembershipVlanID      Integer32,
                sm48tat4xarpVLANMembershipStatus      INTEGER
                }

    sm48tat4xarpVLANMembershipVlanID OBJECT-TYPE
               SYNTAX      Integer32(1..4095)
               MAX-ACCESS  not-accessible
               STATUS      current
               DESCRIPTION
                   "VLAN ID for which the Port members are displayed."
               ::= {     sm48tat4xarpVLANMembershipStatusEntry 2 }

    sm48tat4xarpVLANMembershipStatus OBJECT-TYPE
               SYNTAX      INTEGER  { portIsNotInVlan  ( 0 ),
                                      portIncludedInVlan ( 1 ),
                                      portInForbiddenPortList( 2 ),
                                      portInForbiddenPortListAndVlan( 3 )
                                    }
               MAX-ACCESS  read-only
               STATUS      current
               DESCRIPTION
                   "portIsNotInVlan(0): A port is nothing in a VLAN.
                    portIncludedInVlan(1): A port is included in a VLAN.
                    portInForbiddenPortList(2): A port is in the forbidden port list.
                    portInForbiddenPortListAndVlan(3):
                     A port is in the forbidden port list and at the same
                     time attempted included in the VLAN."
               ::= {     sm48tat4xarpVLANMembershipStatusEntry 3 }

--sm48tat4xarpVLANPortStatusTable
    sm48tat4xarpVLANPortStatusTable OBJECT-TYPE
               SYNTAX      SEQUENCE OF     SM48TAT4XARPVLANPortStatusEntry
               MAX-ACCESS  not-accessible
               STATUS      current
               DESCRIPTION
                   "The vlan port status table.
                    INDEX for this table is ifIndex which is
                    equivalent to the panel port number."
               ::= {     sm48tat4xarpVlanStatus 2 }

    sm48tat4xarpVLANPortStatusEntry OBJECT-TYPE
               SYNTAX          SM48TAT4XARPVLANPortStatusEntry
               MAX-ACCESS  not-accessible
               STATUS      current
               DESCRIPTION
                   "The vlan port status entry."
               INDEX    {     ifIndex }
               ::= {     sm48tat4xarpVLANPortStatusTable 1 }

    SM48TAT4XARPVLANPortStatusEntry             ::= SEQUENCE {
                sm48tat4xarpVLANPortStatusPortType          DisplayString,
                sm48tat4xarpVLANPortStatusIngressFiltering  AdminMode,
                sm48tat4xarpVLANPortStatusFrameType         DisplayString,
                sm48tat4xarpVLANPortStatusPortVLANID        Integer32,
                sm48tat4xarpVLANPortStatusTxTag             DisplayString,
                sm48tat4xarpVLANPortStatusUntaggedVLANID    Integer32,
                sm48tat4xarpVLANPortStatusConflicts         DisplayString
                }

    sm48tat4xarpVLANPortStatusPortType OBJECT-TYPE
               SYNTAX      DisplayString
               MAX-ACCESS  read-only
               STATUS      current
               DESCRIPTION
                   "Shows the port type (Unaware, C-Port, S-Port,
                    S-Custom-Port.) that a given user wants to configure on
                    the port.The field is empty if not overridden by the selected user."
               ::= {     sm48tat4xarpVLANPortStatusEntry 2 }

    sm48tat4xarpVLANPortStatusIngressFiltering OBJECT-TYPE
               SYNTAX      AdminMode
               MAX-ACCESS  read-only
               STATUS      current
               DESCRIPTION
                   "Shows whether a given user wants ingress filtering enabled or not."
               ::= {     sm48tat4xarpVLANPortStatusEntry 3 }

    sm48tat4xarpVLANPortStatusFrameType OBJECT-TYPE
               SYNTAX      DisplayString
               MAX-ACCESS  read-only
               STATUS      current
               DESCRIPTION
                   "Shows the acceptable frame types (All, Taged,
                    Untagged) that a given user wants to configure on the port.
                    The field is empty if not overridden by the selected user."
               ::= {     sm48tat4xarpVLANPortStatusEntry 4 }

    sm48tat4xarpVLANPortStatusPortVLANID OBJECT-TYPE
               SYNTAX      Integer32 (1..4095)
               MAX-ACCESS  read-only
               STATUS      current
               DESCRIPTION
                   "Shows the Port VLAN ID (PVID) that a given user
                    wants the port to have.
                    The field is 0 if not overridden by the selected user."
               ::= {     sm48tat4xarpVLANPortStatusEntry 5 }

    sm48tat4xarpVLANPortStatusTxTag OBJECT-TYPE
               SYNTAX      DisplayString
               MAX-ACCESS  read-only
               STATUS      current
               DESCRIPTION
                   "Shows the Tx Tag requirements (Tag All, Tag PVID,
                    Tag UVID, Untag All, Untag PVID, Untag UVID)
                    that a given user has on a port.The field is empty
                    if not overridden by the selected user."
               ::= {     sm48tat4xarpVLANPortStatusEntry 6 }

    sm48tat4xarpVLANPortStatusUntaggedVLANID OBJECT-TYPE
               SYNTAX      Integer32(1..4095)
               MAX-ACCESS  read-only
               STATUS      current
               DESCRIPTION
                   "If Tx Tag is overridden by the selected user and is
                    set to Tag or Untag UVID, then this field will show
                    the VLAN ID the user wants to tag or untag on egress.
                    The field is 0 if not overridden by the selected
                    user."
               ::= {     sm48tat4xarpVLANPortStatusEntry 7 }

    sm48tat4xarpVLANPortStatusConflicts OBJECT-TYPE
               SYNTAX      DisplayString
               MAX-ACCESS  read-only
               STATUS      current
               DESCRIPTION
                   "Two users may have conflicting requirements to a port's
                    configuration. For instance, one user may require
                    all frames to be tagged on egress while another requires
                    all frames to be untagged on egress.Since both
                    users cannot win, this gives rise to a conflict,
                    which is solved in a prioritized way. The Administrator
                    has the least priority. Other software modules are
                    prioritized according to their position in the drop-down
                    list: The higher in the list, the higher priority.
                    If conflicts exist, it will be displayed as 'Yes'."
               ::= {     sm48tat4xarpVLANPortStatusEntry 8 }

sm48tat4xarpMacBaesdVlanMembershipConfig     OBJECT IDENTIFIER   ::= { sm48tat4xarpVLAN 7 }

sm48tat4xarpMacBaesdVlanMembershipConfigTable  OBJECT-TYPE
   SYNTAX      SEQUENCE OF SM48TAT4XARPMacBaesdVlanMembershipConfigEntry
   MAX-ACCESS  not-accessible
   STATUS      current
   DESCRIPTION
       "Mac-Based VLAN Membership table"
 ::= { sm48tat4xarpMacBaesdVlanMembershipConfig 1 }

sm48tat4xarpMacBaesdVlanMembershipConfigEntry OBJECT-TYPE
    SYNTAX        SM48TAT4XARPMacBaesdVlanMembershipConfigEntry
    MAX-ACCESS    not-accessible
    STATUS        current
    DESCRIPTION
        "Mac-Based VLAN Membership table."
    INDEX        { sm48tat4xarpMacBaesdVlanMembershipConfigIndex }
    ::= { sm48tat4xarpMacBaesdVlanMembershipConfigTable 1 }

SM48TAT4XARPMacBaesdVlanMembershipConfigEntry ::=
    SEQUENCE {
        sm48tat4xarpMacBaesdVlanMembershipConfigIndex        Integer32,
        sm48tat4xarpMacBaesdVlanMembershipConfigMACAddress   DisplayString,
        sm48tat4xarpMacBaesdVlanMembershipConfigVLANID       Integer32,
        sm48tat4xarpMacBaesdVlanMembershipConfigPortMembers  DisplayString,
        sm48tat4xarpMacBaesdVlanMembershipConfigRowStatus    RowStatus
    }

sm48tat4xarpMacBaesdVlanMembershipConfigIndex OBJECT-TYPE
   SYNTAX      Integer32(1..65535)
   MAX-ACCESS  not-accessible
   STATUS      current
   DESCRIPTION
       "Mac-Based VLAN membership index."
   ::= {sm48tat4xarpMacBaesdVlanMembershipConfigEntry 1 }

sm48tat4xarpMacBaesdVlanMembershipConfigMACAddress OBJECT-TYPE
   SYNTAX      DisplayString
   MAX-ACCESS  read-create
   STATUS      current
   DESCRIPTION
       "MAC address: xx-xx-xx-xx-xx-xx."
   ::= {sm48tat4xarpMacBaesdVlanMembershipConfigEntry 2 }

sm48tat4xarpMacBaesdVlanMembershipConfigVLANID OBJECT-TYPE
   SYNTAX      Integer32
   MAX-ACCESS  read-create
   STATUS      current
   DESCRIPTION
       "VLAN ID"
   ::= {sm48tat4xarpMacBaesdVlanMembershipConfigEntry 3 }

sm48tat4xarpMacBaesdVlanMembershipConfigPortMembers OBJECT-TYPE
   SYNTAX      DisplayString
   MAX-ACCESS  read-create
   STATUS      current
   DESCRIPTION
       "0:remove or exclude the port from the mapping
        1:include a port in the mapping"
   ::= {sm48tat4xarpMacBaesdVlanMembershipConfigEntry 4 }

sm48tat4xarpMacBaesdVlanMembershipConfigRowStatus OBJECT-TYPE
   SYNTAX      RowStatus
   MAX-ACCESS  read-create
   STATUS      current
   DESCRIPTION
       "Row Status."
   ::= {sm48tat4xarpMacBaesdVlanMembershipConfigEntry 5 }

sm48tat4xarpMacBaesdVlanMembershipStatusUser   OBJECT-TYPE
       SYNTAX      Integer32
       MAX-ACCESS  read-write
       STATUS      current
       DESCRIPTION
           "MAC-based VLAN Membership Status User"
       ::= { sm48tat4xarpVLAN 8 }

sm48tat4xarpMacBaesdVlanMembershipStatus     OBJECT IDENTIFIER   ::= { sm48tat4xarpVLAN 9 }

sm48tat4xarpMacBaesdVlanMembershipStatusTable  OBJECT-TYPE
   SYNTAX      SEQUENCE OF SM48TAT4XARPMacBaesdVlanMembershipStatusEntry
   MAX-ACCESS  not-accessible
   STATUS      current
   DESCRIPTION
       "Mac-Based VLAN Membership table"
 ::= { sm48tat4xarpMacBaesdVlanMembershipStatus 1 }

sm48tat4xarpMacBaesdVlanMembershipStatusEntry OBJECT-TYPE
    SYNTAX        SM48TAT4XARPMacBaesdVlanMembershipStatusEntry
    MAX-ACCESS    not-accessible
    STATUS        current
    DESCRIPTION
        "Mac-Based VLAN Membership table."
    INDEX        { sm48tat4xarpMacBaesdVlanMembershipStatusIndex }
    ::= { sm48tat4xarpMacBaesdVlanMembershipStatusTable 1 }

SM48TAT4XARPMacBaesdVlanMembershipStatusEntry ::=
    SEQUENCE {
        sm48tat4xarpMacBaesdVlanMembershipStatusIndex        Integer32,
        sm48tat4xarpMacBaesdVlanMembershipStatusMACAddress   DisplayString,
        sm48tat4xarpMacBaesdVlanMembershipStatusVLANID       Integer32,
        sm48tat4xarpMacBaesdVlanMembershipStatusPortMembers  DisplayString
    }

sm48tat4xarpMacBaesdVlanMembershipStatusIndex OBJECT-TYPE
   SYNTAX      Integer32(1..65535)
   MAX-ACCESS  not-accessible
   STATUS      current
   DESCRIPTION
       "Mac-Based VLAN membership index."
   ::= {sm48tat4xarpMacBaesdVlanMembershipStatusEntry 1 }

sm48tat4xarpMacBaesdVlanMembershipStatusMACAddress OBJECT-TYPE
   SYNTAX      DisplayString
   MAX-ACCESS  read-only
   STATUS      current
   DESCRIPTION
       "MAC address: xx-xx-xx-xx-xx-xx."
   ::= {sm48tat4xarpMacBaesdVlanMembershipStatusEntry 2 }

sm48tat4xarpMacBaesdVlanMembershipStatusVLANID OBJECT-TYPE
   SYNTAX      Integer32
   MAX-ACCESS  read-only
   STATUS      current
   DESCRIPTION
       "VLAN ID"
   ::= {sm48tat4xarpMacBaesdVlanMembershipStatusEntry 3 }

sm48tat4xarpMacBaesdVlanMembershipStatusPortMembers OBJECT-TYPE
   SYNTAX      DisplayString
   MAX-ACCESS  read-only
   STATUS      current
   DESCRIPTION
       "0:remove or exclude the port from the mapping
        1:include a port in the mapping"
   ::= {sm48tat4xarpMacBaesdVlanMembershipStatusEntry 4 }

sm48tat4xarpProtocolbasedVLANConfig     OBJECT IDENTIFIER   ::= { sm48tat4xarpVLAN 10 }

sm48tat4xarpProtocolbasedVLANConfigTable  OBJECT-TYPE
   SYNTAX      SEQUENCE OF SM48TAT4XARPProtocolbasedVLANConfigEntry
   MAX-ACCESS  not-accessible
   STATUS      current
   DESCRIPTION
       "Protocol-based VLAN Config table"
 ::= { sm48tat4xarpProtocolbasedVLANConfig 1 }

sm48tat4xarpProtocolbasedVLANConfigEntry OBJECT-TYPE
    SYNTAX        SM48TAT4XARPProtocolbasedVLANConfigEntry
    MAX-ACCESS    not-accessible
    STATUS        current
    DESCRIPTION
        "Protocol-based VLAN Config table"
    INDEX        { sm48tat4xarpProtocolbasedVLANConfigIndex }
    ::= { sm48tat4xarpProtocolbasedVLANConfigTable 1 }

SM48TAT4XARPProtocolbasedVLANConfigEntry ::=
    SEQUENCE {
        sm48tat4xarpProtocolbasedVLANConfigIndex               Integer32,
        sm48tat4xarpProtocolbasedVLANConfigFrameType           Integer32,
        sm48tat4xarpProtocolbasedVLANConfigValueEthernetEtype  DisplayString,
        sm48tat4xarpProtocolbasedVLANConfigValueSNAPOUI        DisplayString,
        sm48tat4xarpProtocolbasedVLANConfigValueSNAPPID        DisplayString,
        sm48tat4xarpProtocolbasedVLANConfigValueLLCDSAP        DisplayString,
        sm48tat4xarpProtocolbasedVLANConfigValueLLCSSAP        DisplayString,
        sm48tat4xarpProtocolbasedVLANConfigGroupName           DisplayString,
        sm48tat4xarpProtocolbasedVLANConfigRowStatus           RowStatus
    }

sm48tat4xarpProtocolbasedVLANConfigIndex OBJECT-TYPE
   SYNTAX      Integer32(1..65535)
   MAX-ACCESS  not-accessible
   STATUS      current
   DESCRIPTION
       "Protocol-based VLAN Config index."
   ::= {sm48tat4xarpProtocolbasedVLANConfigEntry 1 }

sm48tat4xarpProtocolbasedVLANConfigFrameType OBJECT-TYPE
   SYNTAX      Integer32
   MAX-ACCESS  read-create
   STATUS      current
   DESCRIPTION
       "Frame Type.
       1:Ethernet
       2:LLC
       3:SNAP"
   ::= {sm48tat4xarpProtocolbasedVLANConfigEntry 2 }


sm48tat4xarpProtocolbasedVLANConfigValueEthernetEtype OBJECT-TYPE
   SYNTAX      DisplayString
   MAX-ACCESS  read-create
   STATUS      current
   DESCRIPTION
       "Ethernet Etype.
       Valid values for etype range between 0x0600 and 0xffff "
   ::= {sm48tat4xarpProtocolbasedVLANConfigEntry 3 }

sm48tat4xarpProtocolbasedVLANConfigValueSNAPOUI OBJECT-TYPE
   SYNTAX      DisplayString
   MAX-ACCESS  read-create
   STATUS      current
   DESCRIPTION
       "SNAP OUI.
       Format:xx-xx-xx"
   ::= {sm48tat4xarpProtocolbasedVLANConfigEntry 4 }

sm48tat4xarpProtocolbasedVLANConfigValueSNAPPID OBJECT-TYPE
   SYNTAX      DisplayString
   MAX-ACCESS  read-create
   STATUS      current
   DESCRIPTION
       "SNAP PID
       Ranging between 0x00 and 0xff."
   ::= {sm48tat4xarpProtocolbasedVLANConfigEntry 5 }

sm48tat4xarpProtocolbasedVLANConfigValueLLCDSAP OBJECT-TYPE
   SYNTAX      DisplayString
   MAX-ACCESS  read-create
   STATUS      current
   DESCRIPTION
       "LLC DSAP.
       Range: 0x00-0xff"
   ::= {sm48tat4xarpProtocolbasedVLANConfigEntry 6 }

sm48tat4xarpProtocolbasedVLANConfigValueLLCSSAP OBJECT-TYPE
   SYNTAX      DisplayString
   MAX-ACCESS  read-create
   STATUS      current
   DESCRIPTION
       "LLC SSAP.
       Range: 0x00-0xff"
   ::= {sm48tat4xarpProtocolbasedVLANConfigEntry 7 }

sm48tat4xarpProtocolbasedVLANConfigGroupName OBJECT-TYPE
   SYNTAX      DisplayString
   MAX-ACCESS  read-create
   STATUS      current
   DESCRIPTION
       "Group Name
        16-character long string, unique for every entry, which consists of a combination of alphabets (a-z or A-Z) and integers(0-9)."
   ::= {sm48tat4xarpProtocolbasedVLANConfigEntry 8 }

sm48tat4xarpProtocolbasedVLANConfigRowStatus OBJECT-TYPE
   SYNTAX      RowStatus
   MAX-ACCESS  read-create
   STATUS      current
   DESCRIPTION
       "Row Status."
   ::= {sm48tat4xarpProtocolbasedVLANConfigEntry 9 }



sm48tat4xarpGroupNameToVLANMappingConfigTable  OBJECT-TYPE
   SYNTAX      SEQUENCE OF SM48TAT4XARPGroupNameToVLANMappingConfigEntry
   MAX-ACCESS  not-accessible
   STATUS      current
   DESCRIPTION
       "Group Name To VLAN Mapping Config table"
 ::= { sm48tat4xarpProtocolbasedVLANConfig 2 }

sm48tat4xarpGroupNameToVLANMappingConfigEntry OBJECT-TYPE
    SYNTAX        SM48TAT4XARPGroupNameToVLANMappingConfigEntry
    MAX-ACCESS    not-accessible
    STATUS        current
    DESCRIPTION
        "Group Name To VLAN Mapping Config table."
    INDEX        { sm48tat4xarpGroupNameToVLANMappingConfigIndex }
    ::= { sm48tat4xarpGroupNameToVLANMappingConfigTable 1 }

SM48TAT4XARPGroupNameToVLANMappingConfigEntry ::=
    SEQUENCE {
        sm48tat4xarpGroupNameToVLANMappingConfigIndex        Integer32,
        sm48tat4xarpGroupNameToVLANMappingConfigGroupName    DisplayString,
        sm48tat4xarpGroupNameToVLANMappingConfigVLANID       Integer32,
        sm48tat4xarpGroupNameToVLANMappingConfigPortMembers  DisplayString,
        sm48tat4xarpGroupNameToVLANMappingConfigRowStatus    RowStatus
    }

sm48tat4xarpGroupNameToVLANMappingConfigIndex OBJECT-TYPE
   SYNTAX      Integer32(1..65535)
   MAX-ACCESS  not-accessible
   STATUS      current
   DESCRIPTION
       "Group Name To VLAN Mapping Config index."
   ::= {sm48tat4xarpGroupNameToVLANMappingConfigEntry 1 }

sm48tat4xarpGroupNameToVLANMappingConfigGroupName OBJECT-TYPE
   SYNTAX      DisplayString
   MAX-ACCESS  read-create
   STATUS      current
   DESCRIPTION
       "Group Name
        16-character long string, unique for every entry, which consists of a combination of alphabets (a-z or A-Z) and integers(0-9)."
   ::= {sm48tat4xarpGroupNameToVLANMappingConfigEntry 2 }

sm48tat4xarpGroupNameToVLANMappingConfigVLANID OBJECT-TYPE
   SYNTAX      Integer32
   MAX-ACCESS  read-create
   STATUS      current
   DESCRIPTION
       "VLAN ID"
   ::= {sm48tat4xarpGroupNameToVLANMappingConfigEntry 3 }

sm48tat4xarpGroupNameToVLANMappingConfigPortMembers OBJECT-TYPE
   SYNTAX      DisplayString
   MAX-ACCESS  read-create
   STATUS      current
   DESCRIPTION
       "0:remove or exclude the port from the mapping
        1:include a port in the mapping"
   ::= {sm48tat4xarpGroupNameToVLANMappingConfigEntry 4 }

sm48tat4xarpGroupNameToVLANMappingConfigRowStatus OBJECT-TYPE
   SYNTAX      RowStatus
   MAX-ACCESS  read-create
   STATUS      current
   DESCRIPTION
       "Row Status."
   ::= {sm48tat4xarpGroupNameToVLANMappingConfigEntry 5 }

sm48tat4xarpIPSubnetBasedVLANConfig     OBJECT IDENTIFIER   ::= { sm48tat4xarpVLAN 11 }

sm48tat4xarpIPSubnetBasedVLANConfigTable  OBJECT-TYPE
   SYNTAX      SEQUENCE OF SM48TAT4XARPIPSubnetBasedVLANConfigEntry
   MAX-ACCESS  not-accessible
   STATUS      current
   DESCRIPTION
       "IP Subnet Based VLAN Config table"
 ::= { sm48tat4xarpIPSubnetBasedVLANConfig 1 }

sm48tat4xarpIPSubnetBasedVLANConfigEntry OBJECT-TYPE
    SYNTAX        SM48TAT4XARPIPSubnetBasedVLANConfigEntry
    MAX-ACCESS    not-accessible
    STATUS        current
    DESCRIPTION
        "IP Subnet Based VLAN Config table."
    INDEX        { sm48tat4xarpIPSubnetBasedVLANConfigIndex }
    ::= { sm48tat4xarpIPSubnetBasedVLANConfigTable 1 }

SM48TAT4XARPIPSubnetBasedVLANConfigEntry ::=
    SEQUENCE {
        sm48tat4xarpIPSubnetBasedVLANConfigIndex        Integer32,
        sm48tat4xarpIPSubnetBasedVLANConfigIPAddress    IpAddress,
        sm48tat4xarpIPSubnetBasedVLANConfigMaskLength   Integer32,
        sm48tat4xarpIPSubnetBasedVLANConfigVLANID       Integer32,
        sm48tat4xarpIPSubnetBasedVLANConfigPortMembers  DisplayString,
        sm48tat4xarpIPSubnetBasedVLANConfigRowStatus    RowStatus
    }

sm48tat4xarpIPSubnetBasedVLANConfigIndex OBJECT-TYPE
   SYNTAX      Integer32(1..65535)
   MAX-ACCESS  not-accessible
   STATUS      current
   DESCRIPTION
       "IP Subnet Based VLAN Config index."
   ::= {sm48tat4xarpIPSubnetBasedVLANConfigEntry 1 }

sm48tat4xarpIPSubnetBasedVLANConfigIPAddress OBJECT-TYPE
   SYNTAX      IpAddress
   MAX-ACCESS  read-create
   STATUS      current
   DESCRIPTION
       "The subnet's IP address"
   ::= {sm48tat4xarpIPSubnetBasedVLANConfigEntry 2 }

sm48tat4xarpIPSubnetBasedVLANConfigMaskLength OBJECT-TYPE
   SYNTAX      Integer32
   MAX-ACCESS  read-create
   STATUS      current
   DESCRIPTION
       "The subnet's mask length. "
   ::= {sm48tat4xarpIPSubnetBasedVLANConfigEntry 3 }

sm48tat4xarpIPSubnetBasedVLANConfigVLANID OBJECT-TYPE
   SYNTAX      Integer32
   MAX-ACCESS  read-create
   STATUS      current
   DESCRIPTION
       "VLAN ID"
   ::= {sm48tat4xarpIPSubnetBasedVLANConfigEntry 4 }

sm48tat4xarpIPSubnetBasedVLANConfigPortMembers OBJECT-TYPE
   SYNTAX      DisplayString
   MAX-ACCESS  read-create
   STATUS      current
   DESCRIPTION
       "0:remove or exclude the port from the mapping
        1:include a port in the mapping"
   ::= {sm48tat4xarpIPSubnetBasedVLANConfigEntry 5 }

sm48tat4xarpIPSubnetBasedVLANConfigRowStatus OBJECT-TYPE
   SYNTAX      RowStatus
   MAX-ACCESS  read-create
   STATUS      current
   DESCRIPTION
       "Row Status."
   ::= {sm48tat4xarpIPSubnetBasedVLANConfigEntry 6 }

sm48tat4xarpVLANNameConfig     OBJECT IDENTIFIER   ::= { sm48tat4xarpVLAN 12 }

sm48tat4xarpVLANNameConfigTable  OBJECT-TYPE
   SYNTAX      SEQUENCE OF SM48TAT4XARPVLANNameConfigEntry
   MAX-ACCESS  not-accessible
   STATUS      current
   DESCRIPTION
       "VLAN Name Config table"
 ::= { sm48tat4xarpVLANNameConfig 1 }

sm48tat4xarpVLANNameConfigEntry OBJECT-TYPE
    SYNTAX        SM48TAT4XARPVLANNameConfigEntry
    MAX-ACCESS    not-accessible
    STATUS        current
    DESCRIPTION
        "VLAN Name Config table."
    INDEX        { sm48tat4xarpVLANNameConfigIndex }
    ::= { sm48tat4xarpVLANNameConfigTable 1 }

SM48TAT4XARPVLANNameConfigEntry ::=
    SEQUENCE {
        sm48tat4xarpVLANNameConfigIndex        Integer32,
        sm48tat4xarpVLANNameConfigVLANName     DisplayString
    }

sm48tat4xarpVLANNameConfigIndex OBJECT-TYPE
   SYNTAX      Integer32(1..65535)
   MAX-ACCESS  not-accessible
   STATUS      current
   DESCRIPTION
       "VLAN Name Config index."
   ::= {sm48tat4xarpVLANNameConfigEntry 1 }

sm48tat4xarpVLANNameConfigVLANName OBJECT-TYPE
   SYNTAX      DisplayString
   MAX-ACCESS  read-write
   STATUS      current
   DESCRIPTION
       "VLAN Name."
   ::= {sm48tat4xarpVLANNameConfigEntry 2 }


sm48tat4xarpNTPConf   OBJECT IDENTIFIER ::= { sm48tat4xarpSystem 12 }

sm48tat4xarpNTPConfigMode OBJECT-TYPE
           SYNTAX       INTEGER {useLocal(0),useNTP(1)}
           MAX-ACCESS   read-write
           STATUS       current
           DESCRIPTION
               "The system NTP Mode.
                useLocal(0) : Use Local Settings,
                useNTP(1)   : Use NTP Server."
           DEFVAL  { useLocal }
           ::= {     sm48tat4xarpNTPConf 1 }

--sm48tat4xarpNTPConfigAutomatic   OBJECT-TYPE
--               SYNTAX      Integer32 (0|1)
--               MAX-ACCESS  read-write
--               STATUS      current
--               DESCRIPTION
--                   "Indicates the Automatic mode operation. Possible modes are:
--                   0:Disable, NTP servers available from the config.
--                   1:Enable, NTP servers available from the DHCP."
--               ::= { sm48tat4xarpNTPConf 2 }

sm48tat4xarpNTPConfigTimeSyncInterval   OBJECT-TYPE
               SYNTAX      Integer32 (5|10|15|30|60|120)
               MAX-ACCESS  read-write
               STATUS      current
               DESCRIPTION
                   "Time-Sync Interval.
                   Valid values are restricted to 5,10,15,30,60,120 minutes. "
               ::= { sm48tat4xarpNTPConf 3 }

sm48tat4xarpNTPConfigServerAddress1   OBJECT-TYPE
               SYNTAX      DisplayString
               MAX-ACCESS  read-write
               STATUS      current
               DESCRIPTION
                   "Provide the IPv4 or IPv6 address of a NTP server."
               ::= { sm48tat4xarpNTPConf 4 }

sm48tat4xarpNTPConfigServerAddress2   OBJECT-TYPE
               SYNTAX      DisplayString
               MAX-ACCESS  read-write
               STATUS      current
               DESCRIPTION
                   "Provide the IPv4 or IPv6 address of a NTP server."
               ::= { sm48tat4xarpNTPConf 5 }

sm48tat4xarpNTPConfigServerAddress3   OBJECT-TYPE
               SYNTAX      DisplayString
               MAX-ACCESS  read-write
               STATUS      current
               DESCRIPTION
                   "Provide the IPv4 or IPv6 address of a NTP server."
               ::= { sm48tat4xarpNTPConf 6 }

sm48tat4xarpNTPConfigServerAddress4   OBJECT-TYPE
               SYNTAX      DisplayString
               MAX-ACCESS  read-write
               STATUS      current
               DESCRIPTION
                   "Provide the IPv4 or IPv6 address of a NTP server."
               ::= { sm48tat4xarpNTPConf 7 }

sm48tat4xarpNTPConfigServerAddress5   OBJECT-TYPE
               SYNTAX      DisplayString
               MAX-ACCESS  read-write
               STATUS      current
               DESCRIPTION
                   "Provide the IPv4 or IPv6 address of a NTP server."
               ::= { sm48tat4xarpNTPConf 8 }


sm48tat4xarpTemperature   OBJECT IDENTIFIER ::= { sm48tat4xarpSystem 13 }

sm48tat4xarpTemperature1   OBJECT IDENTIFIER ::= { sm48tat4xarpTemperature 1 }

sm48tat4xarpTemperature1Celsius   OBJECT-TYPE
               SYNTAX      DisplayString
               MAX-ACCESS  read-only
               STATUS      current
               DESCRIPTION
                   "Value of Celsius"
               ::= { sm48tat4xarpTemperature1 1 }

sm48tat4xarpTemperature1Fahrenheit   OBJECT-TYPE
               SYNTAX      DisplayString
               MAX-ACCESS  read-only
               STATUS      current
               DESCRIPTION
                   "Value of Fahrenheit"
               ::= { sm48tat4xarpTemperature1 2 }

sm48tat4xarpTemperature2   OBJECT IDENTIFIER ::= { sm48tat4xarpTemperature 2 }

sm48tat4xarpTemperature2Celsius   OBJECT-TYPE
               SYNTAX      DisplayString
               MAX-ACCESS  read-only
               STATUS      current
               DESCRIPTION
                   "Value of Celsius"
               ::= { sm48tat4xarpTemperature2 1 }

sm48tat4xarpTemperature2Fahrenheit   OBJECT-TYPE
               SYNTAX      DisplayString
               MAX-ACCESS  read-only
               STATUS      current
               DESCRIPTION
                   "Value of Fahrenheit"
               ::= { sm48tat4xarpTemperature2 2 }

-- =======================================================================================================================
sm48tat4xarpConfiguration                                         OBJECT IDENTIFIER ::= { sm48tat4xarpProductId 2 }

sm48tat4xarpPort                                                  OBJECT IDENTIFIER ::= { sm48tat4xarpConfiguration 1 }

sm48tat4xarpPortConfigurationTable OBJECT-TYPE
   SYNTAX      SEQUENCE OF SM48TAT4XARPPortConfigurationEntry
   MAX-ACCESS  not-accessible
   STATUS      current
   DESCRIPTION
       " Show port configurations. "
   ::= { sm48tat4xarpPort 1 }

sm48tat4xarpPortConfigurationEntry OBJECT-TYPE
   SYNTAX      SM48TAT4XARPPortConfigurationEntry
   MAX-ACCESS  not-accessible
   STATUS      current
   DESCRIPTION
       " "
   INDEX    { sm48tat4xarpPortConfPort  }
   ::= { sm48tat4xarpPortConfigurationTable 1 }

SM48TAT4XARPPortConfigurationEntry ::= SEQUENCE {
   sm48tat4xarpPortConfPort                     Integer32,
   sm48tat4xarpPortConfDescription              DisplayString,
   sm48tat4xarpPortConfLink                     DisplayString,
   sm48tat4xarpPortConfSpeedStatus              DisplayString,
   sm48tat4xarpPortConfSpeedMode                Integer32,
   sm48tat4xarpPortConfFlowControlRxStatus      Integer32,
   sm48tat4xarpPortConfFlowControlTxStatus      Integer32,
   sm48tat4xarpPortConfFlowControlMode          Integer32,
   sm48tat4xarpPortConfMaximumFrameSize         Integer32
-- sm48tat4xarpPortConfExcessiveCollisionMode   Integer32,
-- sm48tat4xarpPortConfPowerControl             Integer32,
-- sm48tat4xarpPortConfPortMedia                DisplayString
}

sm48tat4xarpPortConfPort OBJECT-TYPE
   SYNTAX      Integer32 (1..4095)
   MAX-ACCESS  not-accessible
   STATUS      current
   DESCRIPTION
       " port, range : 1 - port number. "
   ::= { sm48tat4xarpPortConfigurationEntry 1 }

sm48tat4xarpPortConfDescription OBJECT-TYPE
   SYNTAX      DisplayString
   MAX-ACCESS  read-write
   STATUS      current
   DESCRIPTION
       " Interface specific description.
         Up to 16 characters describing this interface. "
   ::= { sm48tat4xarpPortConfigurationEntry 2 }

sm48tat4xarpPortConfLink OBJECT-TYPE
   SYNTAX      DisplayString(SIZE (2..4))
   MAX-ACCESS  read-only
   STATUS      current
   DESCRIPTION
       " The current link state. "
   ::= { sm48tat4xarpPortConfigurationEntry 3 }

sm48tat4xarpPortConfSpeedStatus OBJECT-TYPE
   SYNTAX      DisplayString(SIZE (6..12))
   MAX-ACCESS  read-only
   STATUS      current
   DESCRIPTION
       " The current link speed of the port. "
   ::= { sm48tat4xarpPortConfigurationEntry 4 }

sm48tat4xarpPortConfSpeedMode OBJECT-TYPE
   SYNTAX      Integer32 (0..9)
   MAX-ACCESS  read-write
   STATUS      current
   DESCRIPTION
       "default: 1,
        0: disable state,
        1: auto,
        2: 10 Half,
        3: 10 Full,
        4: 100 Half,
        5: 100 Full,
        6: 1G full,
        7: 10G Full,
        8: 100-FX,
        9: 1000-X. "
   ::= { sm48tat4xarpPortConfigurationEntry 5 }

sm48tat4xarpPortConfFlowControlRxStatus OBJECT-TYPE
   SYNTAX      Integer32 (0|1)
   MAX-ACCESS  read-only
   STATUS      current
   DESCRIPTION
       "0: disable
        1: enable
        2: not support.  "
   ::= { sm48tat4xarpPortConfigurationEntry 6 }

sm48tat4xarpPortConfFlowControlTxStatus OBJECT-TYPE
   SYNTAX      Integer32 (0|1)
   MAX-ACCESS  read-only
   STATUS      current
   DESCRIPTION
       "0: disable
        1: enable
        2: not support.  "
   ::= { sm48tat4xarpPortConfigurationEntry 7 }

sm48tat4xarpPortConfFlowControlMode OBJECT-TYPE
   SYNTAX      Integer32 (0|1)
   MAX-ACCESS  read-write
   STATUS      current
   DESCRIPTION
       "default: 0,
        0: disable
        1: enable
        2: not support. "
   ::= { sm48tat4xarpPortConfigurationEntry 8 }

sm48tat4xarpPortConfMaximumFrameSize OBJECT-TYPE
   SYNTAX      Integer32 (1518..10240)
   MAX-ACCESS  read-write
   STATUS      current
   DESCRIPTION
       "default: 10240 , range : 1518 - 10240 "
   ::= { sm48tat4xarpPortConfigurationEntry 9 }

--sm48tat4xarpPortConfExcessiveCollisionMode OBJECT-TYPE
--   SYNTAX      Integer32 (0|1)
--   MAX-ACCESS  read-write
--   STATUS      current
--   DESCRIPTION
--       "default: 0,
--        Excessive Collision Mode :
--        0: Discard,
--        1: Restart,
--        2: not support.
--       "
--   ::= { sm48tat4xarpPortConfigurationEntry 10 }

--sm48tat4xarpPortConfPowerControl OBJECT-TYPE
--   SYNTAX      Integer32 (0..3)
--   MAX-ACCESS  read-write
--   STATUS      current
--   DESCRIPTION
--       "default: 0,
--        PowerControl :
--        0: disable,
--        1: Actiphy,
--        2: Dynamic (perfectReach),
--        3: Enable,
--        4: not support.
--       "
--   ::= { sm48tat4xarpPortConfigurationEntry 11 }

--sm48tat4xarpPortConfPortMedia OBJECT-TYPE
--   SYNTAX      DisplayString(SIZE (1..4))
--   MAX-ACCESS  read-only
--   STATUS      current
--   DESCRIPTION
--       " Show port media. "
--   ::= { sm48tat4xarpPortConfigurationEntry 12 }


sm48tat4xarpPortTrafficStatisticsTable OBJECT-TYPE
   SYNTAX      SEQUENCE OF SM48TAT4XARPPortTrafficStatisticsEntry
   MAX-ACCESS  not-accessible
   STATUS      current
   DESCRIPTION
       " "
   ::= { sm48tat4xarpPort 2 }

sm48tat4xarpPortTrafficStatisticsEntry OBJECT-TYPE
   SYNTAX      SM48TAT4XARPPortTrafficStatisticsEntry
   MAX-ACCESS  not-accessible
   STATUS      current
   DESCRIPTION
       " "
   INDEX    { sm48tat4xarpPortTrafficStatisticsPort  }
   ::= { sm48tat4xarpPortTrafficStatisticsTable 1 }

SM48TAT4XARPPortTrafficStatisticsEntry ::= SEQUENCE {
   sm48tat4xarpPortTrafficStatisticsPort          Integer32,
   sm48tat4xarpPortTrafficStatisticsClear         Integer32,
   sm48tat4xarpPortTrafficRxPackets               Counter64,
   sm48tat4xarpPortTrafficRxOctets                Counter64,
   sm48tat4xarpPortTrafficRxUnicast               Counter64,
   sm48tat4xarpPortTrafficRxMulticast             Counter64,
   sm48tat4xarpPortTrafficRxBroadcast             Counter64,
   sm48tat4xarpPortTrafficRxPause                 Counter64,
   sm48tat4xarpPortTrafficRx64Bytes               Counter64,
   sm48tat4xarpPortTrafficRx65to127Bytes          Counter64,
   sm48tat4xarpPortTrafficRx128to255Bytes         Counter64,
   sm48tat4xarpPortTrafficRx256to511Bytes         Counter64,
   sm48tat4xarpPortTrafficRx512to1023Bytes        Counter64,
   sm48tat4xarpPortTrafficRx1024to1526Bytes       Counter64,
   sm48tat4xarpPortTrafficRxExceecd1527Bytes      Counter64,
   sm48tat4xarpPortTrafficRxQ0                    Counter64,
   sm48tat4xarpPortTrafficRxQ1                    Counter64,
   sm48tat4xarpPortTrafficRxQ2                    Counter64,
   sm48tat4xarpPortTrafficRxQ3                    Counter64,
   sm48tat4xarpPortTrafficRxQ4                    Counter64,
   sm48tat4xarpPortTrafficRxQ5                    Counter64,
   sm48tat4xarpPortTrafficRxQ6                    Counter64,
   sm48tat4xarpPortTrafficRxQ7                    Counter64,
   sm48tat4xarpPortTrafficRxDrops                 Counter64,
   sm48tat4xarpPortTrafficRxCRCorAlignment        Counter64,
   sm48tat4xarpPortTrafficRxUndersize             Counter64,
   sm48tat4xarpPortTrafficRxOversize              Counter64,
   sm48tat4xarpPortTrafficRxFragments             Counter64,
   sm48tat4xarpPortTrafficRxJabber                Counter64,
   sm48tat4xarpPortTrafficRxFiltered              Counter64,
   sm48tat4xarpPortTrafficTxPackets               Counter64,
   sm48tat4xarpPortTrafficTxOctets                Counter64,
   sm48tat4xarpPortTrafficTxUnicast               Counter64,
   sm48tat4xarpPortTrafficTxMulticast             Counter64,
   sm48tat4xarpPortTrafficTxBroadcast             Counter64,
   sm48tat4xarpPortTrafficTxPause                 Counter64,
   sm48tat4xarpPortTrafficTx64Bytes               Counter64,
   sm48tat4xarpPortTrafficTx65to127Bytes          Counter64,
   sm48tat4xarpPortTrafficTx128to255Bytes         Counter64,
   sm48tat4xarpPortTrafficTx256to511Bytes         Counter64,
   sm48tat4xarpPortTrafficTx512to1023Bytes        Counter64,
   sm48tat4xarpPortTrafficTx1024to1526Bytes       Counter64,
   sm48tat4xarpPortTrafficTxExceecd1527Bytes      Counter64,
   sm48tat4xarpPortTrafficTxQ0                    Counter64,
   sm48tat4xarpPortTrafficTxQ1                    Counter64,
   sm48tat4xarpPortTrafficTxQ2                    Counter64,
   sm48tat4xarpPortTrafficTxQ3                    Counter64,
   sm48tat4xarpPortTrafficTxQ4                    Counter64,
   sm48tat4xarpPortTrafficTxQ5                    Counter64,
   sm48tat4xarpPortTrafficTxQ6                    Counter64,
   sm48tat4xarpPortTrafficTxQ7                    Counter64,
   sm48tat4xarpPortTrafficTxDrops                 Counter64,
   sm48tat4xarpPortTrafficTxLateOrExcColl         Counter64
}

sm48tat4xarpPortTrafficStatisticsPort OBJECT-TYPE
   SYNTAX      Integer32 (1..4095)
   MAX-ACCESS  not-accessible
   STATUS      current
   DESCRIPTION
       " "
   ::= { sm48tat4xarpPortTrafficStatisticsEntry 1 }

sm48tat4xarpPortTrafficStatisticsClear OBJECT-TYPE
   SYNTAX      Integer32(0|1)
   MAX-ACCESS  read-write
   STATUS      current
   DESCRIPTION
       " "
   ::= { sm48tat4xarpPortTrafficStatisticsEntry 2 }

sm48tat4xarpPortTrafficRxPackets OBJECT-TYPE
   SYNTAX      Counter64
   MAX-ACCESS  read-only
   STATUS      current
   DESCRIPTION
       " "
   ::= { sm48tat4xarpPortTrafficStatisticsEntry 3 }

sm48tat4xarpPortTrafficRxOctets OBJECT-TYPE
   SYNTAX      Counter64
   MAX-ACCESS  read-only
   STATUS      current
   DESCRIPTION
       " "
   ::= { sm48tat4xarpPortTrafficStatisticsEntry 4 }

sm48tat4xarpPortTrafficRxUnicast OBJECT-TYPE
   SYNTAX      Counter64
   MAX-ACCESS  read-only
   STATUS      current
   DESCRIPTION
       " "
   ::= { sm48tat4xarpPortTrafficStatisticsEntry 5 }

sm48tat4xarpPortTrafficRxMulticast OBJECT-TYPE
   SYNTAX      Counter64
   MAX-ACCESS  read-only
   STATUS      current
   DESCRIPTION
       " "
   ::= { sm48tat4xarpPortTrafficStatisticsEntry 6 }

sm48tat4xarpPortTrafficRxBroadcast OBJECT-TYPE
   SYNTAX      Counter64
   MAX-ACCESS  read-only
   STATUS      current
   DESCRIPTION
       " "
   ::= { sm48tat4xarpPortTrafficStatisticsEntry 7 }

sm48tat4xarpPortTrafficRxPause OBJECT-TYPE
   SYNTAX      Counter64
   MAX-ACCESS  read-only
   STATUS      current
   DESCRIPTION
       " "
   ::= { sm48tat4xarpPortTrafficStatisticsEntry 8 }

sm48tat4xarpPortTrafficRx64Bytes OBJECT-TYPE
   SYNTAX      Counter64
   MAX-ACCESS  read-only
   STATUS      current
   DESCRIPTION
       " "
   ::= { sm48tat4xarpPortTrafficStatisticsEntry 9 }

sm48tat4xarpPortTrafficRx65to127Bytes OBJECT-TYPE
   SYNTAX      Counter64
   MAX-ACCESS  read-only
   STATUS      current
   DESCRIPTION
       " "
   ::= { sm48tat4xarpPortTrafficStatisticsEntry 10 }

sm48tat4xarpPortTrafficRx128to255Bytes OBJECT-TYPE
   SYNTAX      Counter64
   MAX-ACCESS  read-only
   STATUS      current
   DESCRIPTION
       " "
   ::= { sm48tat4xarpPortTrafficStatisticsEntry 11 }

sm48tat4xarpPortTrafficRx256to511Bytes OBJECT-TYPE
   SYNTAX      Counter64
   MAX-ACCESS  read-only
   STATUS      current
   DESCRIPTION
       " "
   ::= { sm48tat4xarpPortTrafficStatisticsEntry 12 }

sm48tat4xarpPortTrafficRx512to1023Bytes OBJECT-TYPE
   SYNTAX      Counter64
   MAX-ACCESS  read-only
   STATUS      current
   DESCRIPTION
       " "
   ::= { sm48tat4xarpPortTrafficStatisticsEntry 13 }

sm48tat4xarpPortTrafficRx1024to1526Bytes OBJECT-TYPE
   SYNTAX      Counter64
   MAX-ACCESS  read-only
   STATUS      current
   DESCRIPTION
       " "
   ::= { sm48tat4xarpPortTrafficStatisticsEntry 14 }

sm48tat4xarpPortTrafficRxExceecd1527Bytes OBJECT-TYPE
   SYNTAX      Counter64
   MAX-ACCESS  read-only
   STATUS      current
   DESCRIPTION
       " "
   ::= { sm48tat4xarpPortTrafficStatisticsEntry 15 }

sm48tat4xarpPortTrafficRxQ0 OBJECT-TYPE
   SYNTAX      Counter64
   MAX-ACCESS  read-only
   STATUS      current
   DESCRIPTION
       " "
   ::= { sm48tat4xarpPortTrafficStatisticsEntry 16 }

sm48tat4xarpPortTrafficRxQ1 OBJECT-TYPE
   SYNTAX      Counter64
   MAX-ACCESS  read-only
   STATUS      current
   DESCRIPTION
       " "
   ::= { sm48tat4xarpPortTrafficStatisticsEntry 17 }

sm48tat4xarpPortTrafficRxQ2 OBJECT-TYPE
   SYNTAX      Counter64
   MAX-ACCESS  read-only
   STATUS      current
   DESCRIPTION
       " "
   ::= { sm48tat4xarpPortTrafficStatisticsEntry 18 }

sm48tat4xarpPortTrafficRxQ3 OBJECT-TYPE
   SYNTAX      Counter64
   MAX-ACCESS  read-only
   STATUS      current
   DESCRIPTION
       " "
   ::= { sm48tat4xarpPortTrafficStatisticsEntry 19 }

sm48tat4xarpPortTrafficRxQ4 OBJECT-TYPE
   SYNTAX      Counter64
   MAX-ACCESS  read-only
   STATUS      current
   DESCRIPTION
       " "
   ::= { sm48tat4xarpPortTrafficStatisticsEntry 20 }

sm48tat4xarpPortTrafficRxQ5 OBJECT-TYPE
   SYNTAX      Counter64
   MAX-ACCESS  read-only
   STATUS      current
   DESCRIPTION
       " "
   ::= { sm48tat4xarpPortTrafficStatisticsEntry 21 }

sm48tat4xarpPortTrafficRxQ6 OBJECT-TYPE
   SYNTAX      Counter64
   MAX-ACCESS  read-only
   STATUS      current
   DESCRIPTION
       " "
   ::= { sm48tat4xarpPortTrafficStatisticsEntry 22 }

sm48tat4xarpPortTrafficRxQ7 OBJECT-TYPE
   SYNTAX      Counter64
   MAX-ACCESS  read-only
   STATUS      current
   DESCRIPTION
       " "
   ::= { sm48tat4xarpPortTrafficStatisticsEntry 23 }

sm48tat4xarpPortTrafficRxDrops OBJECT-TYPE
   SYNTAX      Counter64
   MAX-ACCESS  read-only
   STATUS      current
   DESCRIPTION
       " "
   ::= { sm48tat4xarpPortTrafficStatisticsEntry 24 }

sm48tat4xarpPortTrafficRxCRCorAlignment OBJECT-TYPE
   SYNTAX      Counter64
   MAX-ACCESS  read-only
   STATUS      current
   DESCRIPTION
       " "
   ::= { sm48tat4xarpPortTrafficStatisticsEntry 25 }

sm48tat4xarpPortTrafficRxUndersize OBJECT-TYPE
   SYNTAX      Counter64
   MAX-ACCESS  read-only
   STATUS      current
   DESCRIPTION
       " "
   ::= { sm48tat4xarpPortTrafficStatisticsEntry 26 }

sm48tat4xarpPortTrafficRxOversize OBJECT-TYPE
   SYNTAX      Counter64
   MAX-ACCESS  read-only
   STATUS      current
   DESCRIPTION
       " "
   ::= { sm48tat4xarpPortTrafficStatisticsEntry 27 }

sm48tat4xarpPortTrafficRxFragments OBJECT-TYPE
   SYNTAX      Counter64
   MAX-ACCESS  read-only
   STATUS      current
   DESCRIPTION
       " "
   ::= { sm48tat4xarpPortTrafficStatisticsEntry 28 }

sm48tat4xarpPortTrafficRxJabber OBJECT-TYPE
   SYNTAX      Counter64
   MAX-ACCESS  read-only
   STATUS      current
   DESCRIPTION
       " "
   ::= { sm48tat4xarpPortTrafficStatisticsEntry 29 }

sm48tat4xarpPortTrafficRxFiltered OBJECT-TYPE
   SYNTAX      Counter64
   MAX-ACCESS  read-only
   STATUS      current
   DESCRIPTION
       " "
   ::= { sm48tat4xarpPortTrafficStatisticsEntry 30 }

sm48tat4xarpPortTrafficTxPackets OBJECT-TYPE
   SYNTAX      Counter64
   MAX-ACCESS  read-only
   STATUS      current
   DESCRIPTION
       " "
   ::= { sm48tat4xarpPortTrafficStatisticsEntry 31 }

sm48tat4xarpPortTrafficTxOctets OBJECT-TYPE
   SYNTAX      Counter64
   MAX-ACCESS  read-only
   STATUS      current
   DESCRIPTION
       " "
   ::= { sm48tat4xarpPortTrafficStatisticsEntry 32 }

sm48tat4xarpPortTrafficTxUnicast OBJECT-TYPE
   SYNTAX      Counter64
   MAX-ACCESS  read-only
   STATUS      current
   DESCRIPTION
       " "
   ::= { sm48tat4xarpPortTrafficStatisticsEntry 33 }

sm48tat4xarpPortTrafficTxMulticast OBJECT-TYPE
   SYNTAX      Counter64
   MAX-ACCESS  read-only
   STATUS      current
   DESCRIPTION
       " "
   ::= { sm48tat4xarpPortTrafficStatisticsEntry 34 }

sm48tat4xarpPortTrafficTxBroadcast OBJECT-TYPE
   SYNTAX      Counter64
   MAX-ACCESS  read-only
   STATUS      current
   DESCRIPTION
       " "
   ::= { sm48tat4xarpPortTrafficStatisticsEntry 35 }

sm48tat4xarpPortTrafficTxPause OBJECT-TYPE
   SYNTAX      Counter64
   MAX-ACCESS  read-only
   STATUS      current
   DESCRIPTION
       " "
   ::= { sm48tat4xarpPortTrafficStatisticsEntry 36 }

sm48tat4xarpPortTrafficTx64Bytes OBJECT-TYPE
   SYNTAX      Counter64
   MAX-ACCESS  read-only
   STATUS      current
   DESCRIPTION
       " "
   ::= { sm48tat4xarpPortTrafficStatisticsEntry 37 }

sm48tat4xarpPortTrafficTx65to127Bytes OBJECT-TYPE
   SYNTAX      Counter64
   MAX-ACCESS  read-only
   STATUS      current
   DESCRIPTION
       " "
   ::= { sm48tat4xarpPortTrafficStatisticsEntry 38 }

sm48tat4xarpPortTrafficTx128to255Bytes OBJECT-TYPE
   SYNTAX      Counter64
   MAX-ACCESS  read-only
   STATUS      current
   DESCRIPTION
       " "
   ::= { sm48tat4xarpPortTrafficStatisticsEntry 39 }

sm48tat4xarpPortTrafficTx256to511Bytes OBJECT-TYPE
   SYNTAX      Counter64
   MAX-ACCESS  read-only
   STATUS      current
   DESCRIPTION
       " "
   ::= { sm48tat4xarpPortTrafficStatisticsEntry 40 }

sm48tat4xarpPortTrafficTx512to1023Bytes OBJECT-TYPE
   SYNTAX      Counter64
   MAX-ACCESS  read-only
   STATUS      current
   DESCRIPTION
       " "
   ::= { sm48tat4xarpPortTrafficStatisticsEntry 41 }

sm48tat4xarpPortTrafficTx1024to1526Bytes OBJECT-TYPE
   SYNTAX      Counter64
   MAX-ACCESS  read-only
   STATUS      current
   DESCRIPTION
       " "
   ::= { sm48tat4xarpPortTrafficStatisticsEntry 42 }

sm48tat4xarpPortTrafficTxExceecd1527Bytes OBJECT-TYPE
   SYNTAX      Counter64
   MAX-ACCESS  read-only
   STATUS      current
   DESCRIPTION
       " "
   ::= { sm48tat4xarpPortTrafficStatisticsEntry 43 }

sm48tat4xarpPortTrafficTxQ0 OBJECT-TYPE
   SYNTAX      Counter64
   MAX-ACCESS  read-only
   STATUS      current
   DESCRIPTION
       " "
   ::= { sm48tat4xarpPortTrafficStatisticsEntry 44 }

sm48tat4xarpPortTrafficTxQ1 OBJECT-TYPE
   SYNTAX      Counter64
   MAX-ACCESS  read-only
   STATUS      current
   DESCRIPTION
       " "
   ::= { sm48tat4xarpPortTrafficStatisticsEntry 45 }

sm48tat4xarpPortTrafficTxQ2 OBJECT-TYPE
   SYNTAX      Counter64
   MAX-ACCESS  read-only
   STATUS      current
   DESCRIPTION
       " "
   ::= { sm48tat4xarpPortTrafficStatisticsEntry 46 }

sm48tat4xarpPortTrafficTxQ3 OBJECT-TYPE
   SYNTAX      Counter64
   MAX-ACCESS  read-only
   STATUS      current
   DESCRIPTION
       " "
   ::= { sm48tat4xarpPortTrafficStatisticsEntry 47 }

sm48tat4xarpPortTrafficTxQ4 OBJECT-TYPE
   SYNTAX      Counter64
   MAX-ACCESS  read-only
   STATUS      current
   DESCRIPTION
       " "
   ::= { sm48tat4xarpPortTrafficStatisticsEntry 48 }

sm48tat4xarpPortTrafficTxQ5 OBJECT-TYPE
   SYNTAX      Counter64
   MAX-ACCESS  read-only
   STATUS      current
   DESCRIPTION
       " "
   ::= { sm48tat4xarpPortTrafficStatisticsEntry 49 }

sm48tat4xarpPortTrafficTxQ6 OBJECT-TYPE
   SYNTAX      Counter64
   MAX-ACCESS  read-only
   STATUS      current
   DESCRIPTION
       " "
   ::= { sm48tat4xarpPortTrafficStatisticsEntry 50 }


sm48tat4xarpPortTrafficTxQ7 OBJECT-TYPE
   SYNTAX      Counter64
   MAX-ACCESS  read-only
   STATUS      current
   DESCRIPTION
       " "
   ::= { sm48tat4xarpPortTrafficStatisticsEntry 51 }

sm48tat4xarpPortTrafficTxDrops OBJECT-TYPE
   SYNTAX      Counter64
   MAX-ACCESS  read-only
   STATUS      current
   DESCRIPTION
       " "
   ::= { sm48tat4xarpPortTrafficStatisticsEntry 52 }

sm48tat4xarpPortTrafficTxLateOrExcColl OBJECT-TYPE
   SYNTAX      Counter64
   MAX-ACCESS  read-only
   STATUS      current
   DESCRIPTION
       " "
   ::= { sm48tat4xarpPortTrafficStatisticsEntry 53 }


sm48tat4xarpPortQoSStatistics                                     OBJECT IDENTIFIER ::= { sm48tat4xarpPort 3 }

sm48tat4xarpPortQoSStatisticsClear OBJECT-TYPE
   SYNTAX      Integer32(0|1)
   MAX-ACCESS  read-only
   STATUS      current
   DESCRIPTION
       "default: 0
       0: none
       1: clear "
   ::= { sm48tat4xarpPortQoSStatistics 1 }

sm48tat4xarpPortQoSStatisticsTable OBJECT-TYPE
   SYNTAX      SEQUENCE OF SM48TAT4XARPPortQoSStatisticsEntry
   MAX-ACCESS  not-accessible
   STATUS      current
   DESCRIPTION
       " "
   ::= { sm48tat4xarpPortQoSStatistics 2 }

sm48tat4xarpPortQoSStatisticsEntry OBJECT-TYPE
   SYNTAX      SM48TAT4XARPPortQoSStatisticsEntry
   MAX-ACCESS  not-accessible
   STATUS      current
   DESCRIPTION
       " "
   INDEX    { sm48tat4xarpPortQoSStatisticsPort  }
   ::= { sm48tat4xarpPortQoSStatisticsTable 1 }

SM48TAT4XARPPortQoSStatisticsEntry ::= SEQUENCE {
   sm48tat4xarpPortQoSStatisticsPort      Integer32,
   sm48tat4xarpPortQoSQ0Rx                Counter64,
   sm48tat4xarpPortQoSQ0Tx                Counter64,
   sm48tat4xarpPortQoSQ1Rx                Counter64,
   sm48tat4xarpPortQoSQ1Tx                Counter64,
   sm48tat4xarpPortQoSQ2Rx                Counter64,
   sm48tat4xarpPortQoSQ2Tx                Counter64,
   sm48tat4xarpPortQoSQ3Rx                Counter64,
   sm48tat4xarpPortQoSQ3Tx                Counter64,
   sm48tat4xarpPortQoSQ4Rx                Counter64,
   sm48tat4xarpPortQoSQ4Tx                Counter64,
   sm48tat4xarpPortQoSQ5Rx                Counter64,
   sm48tat4xarpPortQoSQ5Tx                Counter64,
   sm48tat4xarpPortQoSQ6Rx                Counter64,
   sm48tat4xarpPortQoSQ6Tx                Counter64,
   sm48tat4xarpPortQoSQ7Rx                Counter64,
   sm48tat4xarpPortQoSQ7Tx                Counter64
}

sm48tat4xarpPortQoSStatisticsPort OBJECT-TYPE
   SYNTAX      Integer32 (1..4095)
   MAX-ACCESS  not-accessible
   STATUS      current
   DESCRIPTION
       " "
   ::= { sm48tat4xarpPortQoSStatisticsEntry 1 }

sm48tat4xarpPortQoSQ0Rx OBJECT-TYPE
   SYNTAX      Counter64
   MAX-ACCESS  read-only
   STATUS      current
   DESCRIPTION
       " "
   ::= { sm48tat4xarpPortQoSStatisticsEntry 2 }

sm48tat4xarpPortQoSQ0Tx OBJECT-TYPE
   SYNTAX      Counter64
   MAX-ACCESS  read-only
   STATUS      current
   DESCRIPTION
       " "
   ::= { sm48tat4xarpPortQoSStatisticsEntry 3 }

sm48tat4xarpPortQoSQ1Rx OBJECT-TYPE
   SYNTAX      Counter64
   MAX-ACCESS  read-only
   STATUS      current
   DESCRIPTION
       " "
   ::= { sm48tat4xarpPortQoSStatisticsEntry 4 }

sm48tat4xarpPortQoSQ1Tx OBJECT-TYPE
   SYNTAX      Counter64
   MAX-ACCESS  read-only
   STATUS      current
   DESCRIPTION
       " "
   ::= { sm48tat4xarpPortQoSStatisticsEntry 5 }

sm48tat4xarpPortQoSQ2Rx OBJECT-TYPE
   SYNTAX      Counter64
   MAX-ACCESS  read-only
   STATUS      current
   DESCRIPTION
       " "
   ::= { sm48tat4xarpPortQoSStatisticsEntry 6 }

sm48tat4xarpPortQoSQ2Tx OBJECT-TYPE
   SYNTAX      Counter64
   MAX-ACCESS  read-only
   STATUS      current
   DESCRIPTION
       " "
   ::= { sm48tat4xarpPortQoSStatisticsEntry 7 }

sm48tat4xarpPortQoSQ3Rx OBJECT-TYPE
   SYNTAX      Counter64
   MAX-ACCESS  read-only
   STATUS      current
   DESCRIPTION
       " "
   ::= { sm48tat4xarpPortQoSStatisticsEntry 8 }

sm48tat4xarpPortQoSQ3Tx OBJECT-TYPE
   SYNTAX      Counter64
   MAX-ACCESS  read-only
   STATUS      current
   DESCRIPTION
       " "
   ::= { sm48tat4xarpPortQoSStatisticsEntry 9 }

sm48tat4xarpPortQoSQ4Rx OBJECT-TYPE
   SYNTAX      Counter64
   MAX-ACCESS  read-only
   STATUS      current
   DESCRIPTION
       " "
   ::= { sm48tat4xarpPortQoSStatisticsEntry 10 }

sm48tat4xarpPortQoSQ4Tx OBJECT-TYPE
   SYNTAX      Counter64
   MAX-ACCESS  read-only
   STATUS      current
   DESCRIPTION
       " "
   ::= { sm48tat4xarpPortQoSStatisticsEntry 11 }

sm48tat4xarpPortQoSQ5Rx OBJECT-TYPE
   SYNTAX      Counter64
   MAX-ACCESS  read-only
   STATUS      current
   DESCRIPTION
       " "
   ::= { sm48tat4xarpPortQoSStatisticsEntry 12 }

sm48tat4xarpPortQoSQ5Tx OBJECT-TYPE
   SYNTAX      Counter64
   MAX-ACCESS  read-only
   STATUS      current
   DESCRIPTION
       " "
   ::= { sm48tat4xarpPortQoSStatisticsEntry 13 }

sm48tat4xarpPortQoSQ6Rx OBJECT-TYPE
   SYNTAX      Counter64
   MAX-ACCESS  read-only
   STATUS      current
   DESCRIPTION
       " "
   ::= { sm48tat4xarpPortQoSStatisticsEntry 14 }

sm48tat4xarpPortQoSQ6Tx OBJECT-TYPE
   SYNTAX      Counter64
   MAX-ACCESS  read-only
   STATUS      current
   DESCRIPTION
       " "
   ::= { sm48tat4xarpPortQoSStatisticsEntry 15 }

sm48tat4xarpPortQoSQ7Rx OBJECT-TYPE
   SYNTAX      Counter64
   MAX-ACCESS  read-only
   STATUS      current
   DESCRIPTION
       " "
   ::= { sm48tat4xarpPortQoSStatisticsEntry 16 }

sm48tat4xarpPortQoSQ7Tx OBJECT-TYPE
   SYNTAX      Counter64
   MAX-ACCESS  read-only
   STATUS      current
   DESCRIPTION
       " "
   ::= { sm48tat4xarpPortQoSStatisticsEntry 17 }

sm48tat4xarpSFPInfoTable OBJECT-TYPE
   SYNTAX      SEQUENCE OF SM48TAT4XARPSFPInfoEntry
   MAX-ACCESS  not-accessible
   STATUS      current
   DESCRIPTION
       " "
   ::= { sm48tat4xarpPort 4 }

sm48tat4xarpSFPInfoEntry OBJECT-TYPE
   SYNTAX      SM48TAT4XARPSFPInfoEntry
   MAX-ACCESS  not-accessible
   STATUS      current
   DESCRIPTION
       " "
   INDEX    { sm48tat4xarpSFPInfoIndex }
   ::= { sm48tat4xarpSFPInfoTable 1 }

SM48TAT4XARPSFPInfoEntry ::= SEQUENCE {
   sm48tat4xarpSFPInfoIndex               Integer32,
   sm48tat4xarpSFPInfoPort                DisplayString,
   sm48tat4xarpSFPConnectorType           DisplayString,
   sm48tat4xarpSFPFiberType               DisplayString,
   sm48tat4xarpSFPTxCentralWavelength     DisplayString,
   sm48tat4xarpSFPBaudRate                DisplayString,
   sm48tat4xarpSFPVendorOUI               DisplayString,
   sm48tat4xarpSFPVendorName              DisplayString,
   sm48tat4xarpSFPVendorPN                DisplayString,
   sm48tat4xarpSFPVendorRev               DisplayString,
   sm48tat4xarpSFPVendorSN                DisplayString,
   sm48tat4xarpSFPDateCode                DisplayString,
   sm48tat4xarpSFPTemperature             DisplayString,
   sm48tat4xarpSFPVcc                     DisplayString,
   sm48tat4xarpSFPMon1Bias                DisplayString,
   sm48tat4xarpSFPMon2TxPWR               DisplayString,
   sm48tat4xarpSFPMon3RxPWR               DisplayString
}

sm48tat4xarpSFPInfoIndex OBJECT-TYPE
   SYNTAX      Integer32 (1..4095)
   MAX-ACCESS  not-accessible
   STATUS      current
   DESCRIPTION
       " "
   ::= { sm48tat4xarpSFPInfoEntry 1 }

sm48tat4xarpSFPInfoPort OBJECT-TYPE
   SYNTAX      DisplayString
   MAX-ACCESS  read-only
   STATUS      current
   DESCRIPTION
       " "
   ::= { sm48tat4xarpSFPInfoEntry 2 }

sm48tat4xarpSFPConnectorType OBJECT-TYPE
   SYNTAX      DisplayString
   MAX-ACCESS  read-only
   STATUS      current
   DESCRIPTION
       " "
   ::= { sm48tat4xarpSFPInfoEntry 3 }

sm48tat4xarpSFPFiberType OBJECT-TYPE
   SYNTAX      DisplayString
   MAX-ACCESS  read-only
   STATUS      current
   DESCRIPTION
       " "
   ::= { sm48tat4xarpSFPInfoEntry 4 }

sm48tat4xarpSFPTxCentralWavelength OBJECT-TYPE
   SYNTAX      DisplayString
   MAX-ACCESS  read-only
   STATUS      current
   DESCRIPTION
       " "
   ::= { sm48tat4xarpSFPInfoEntry 5 }

sm48tat4xarpSFPBaudRate OBJECT-TYPE
   SYNTAX      DisplayString
   MAX-ACCESS  read-only
   STATUS      current
   DESCRIPTION
       " "
   ::= { sm48tat4xarpSFPInfoEntry 6 }

sm48tat4xarpSFPVendorOUI OBJECT-TYPE
   SYNTAX      DisplayString
   MAX-ACCESS  read-only
   STATUS      current
   DESCRIPTION
       " "
   ::= { sm48tat4xarpSFPInfoEntry 7 }

sm48tat4xarpSFPVendorName OBJECT-TYPE
   SYNTAX      DisplayString
   MAX-ACCESS  read-only
   STATUS      current
   DESCRIPTION
       " "
   ::= { sm48tat4xarpSFPInfoEntry 8 }

sm48tat4xarpSFPVendorPN OBJECT-TYPE
   SYNTAX      DisplayString
   MAX-ACCESS  read-only
   STATUS      current
   DESCRIPTION
       " "
   ::= { sm48tat4xarpSFPInfoEntry 9 }

sm48tat4xarpSFPVendorRev OBJECT-TYPE
   SYNTAX      DisplayString
   MAX-ACCESS  read-only
   STATUS      current
   DESCRIPTION
       " "
   ::= { sm48tat4xarpSFPInfoEntry 10 }

sm48tat4xarpSFPVendorSN OBJECT-TYPE
   SYNTAX      DisplayString
   MAX-ACCESS  read-only
   STATUS      current
   DESCRIPTION
       " "
   ::= { sm48tat4xarpSFPInfoEntry 11 }

sm48tat4xarpSFPDateCode OBJECT-TYPE
   SYNTAX      DisplayString
   MAX-ACCESS  read-only
   STATUS      current
   DESCRIPTION
       " "
   ::= { sm48tat4xarpSFPInfoEntry 12 }

sm48tat4xarpSFPTemperature OBJECT-TYPE
   SYNTAX      DisplayString
   MAX-ACCESS  read-only
   STATUS      current
   DESCRIPTION
       "Value of Celsius"
   ::= { sm48tat4xarpSFPInfoEntry 13 }

sm48tat4xarpSFPVcc OBJECT-TYPE
   SYNTAX      DisplayString
   MAX-ACCESS  read-only
   STATUS      current
   DESCRIPTION
       "Value of V"
   ::= { sm48tat4xarpSFPInfoEntry 14 }

sm48tat4xarpSFPMon1Bias OBJECT-TYPE
   SYNTAX      DisplayString
   MAX-ACCESS  read-only
   STATUS      current
   DESCRIPTION
       "Value of mA"
   ::= { sm48tat4xarpSFPInfoEntry 15 }

sm48tat4xarpSFPMon2TxPWR OBJECT-TYPE
   SYNTAX      DisplayString
   MAX-ACCESS  read-only
   STATUS      current
   DESCRIPTION
       "Value of dBm"
   ::= { sm48tat4xarpSFPInfoEntry 16 }

sm48tat4xarpSFPMon3RxPWR OBJECT-TYPE
   SYNTAX      DisplayString
   MAX-ACCESS  read-only
   STATUS      current
   DESCRIPTION
       "Value of dBm"
   ::= { sm48tat4xarpSFPInfoEntry 17 }


sm48tat4xarpVoiceVLAN                                             OBJECT IDENTIFIER ::= { sm48tat4xarpConfiguration 2 }

sm48tat4xarpVoiceVLANConf                                         OBJECT IDENTIFIER ::= { sm48tat4xarpVoiceVLAN 1 }

sm48tat4xarpVoiceVLANMode OBJECT-TYPE
   SYNTAX      Integer32 (0|1)
   MAX-ACCESS  read-write
   STATUS      current
   DESCRIPTION
       " Voice VLAN mode operation.
       default: 0,
       0: disable
       1: enable"
   ::= { sm48tat4xarpVoiceVLANConf 1 }

sm48tat4xarpVoiceVLANVLANId OBJECT-TYPE
   SYNTAX      Integer32 (1..4094)
   MAX-ACCESS  read-write
   STATUS      current
   DESCRIPTION
       "Voice VLAN ID.
        default: 1000,
        range : 1-4094. "
   ::= { sm48tat4xarpVoiceVLANConf 2 }

sm48tat4xarpVoiceVLANAgingTime OBJECT-TYPE
   SYNTAX      Integer32 (10..10000000)
   MAX-ACCESS  read-write
   STATUS      current
   DESCRIPTION
       " Voice VLAN secure learning aging time.
         default: 86400,
         range : 10 - 10000000. "
   ::= { sm48tat4xarpVoiceVLANConf 3 }

sm48tat4xarpVoiceVLANTrafficClass OBJECT-TYPE
   SYNTAX      Integer32 (0..7)
   MAX-ACCESS  read-write
   STATUS      current
   DESCRIPTION
       " Voice VLAN traffic class, all traffic on the Voice VLAN
         will apply this class, available value is from 0(Low)
         to 7(High).
         default: 7. "
   ::= { sm48tat4xarpVoiceVLANConf 4 }


sm48tat4xarpVoiceVLANPortTable OBJECT-TYPE
   SYNTAX      SEQUENCE OF SM48TAT4XARPVoiceVLANPortEntry
   MAX-ACCESS  not-accessible
   STATUS      current
   DESCRIPTION
       " Show Voice Vlan configuration. "
   ::= { sm48tat4xarpVoiceVLANConf 5 }

sm48tat4xarpVoiceVLANPortEntry OBJECT-TYPE
   SYNTAX      SM48TAT4XARPVoiceVLANPortEntry
   MAX-ACCESS  not-accessible
   STATUS      current
   DESCRIPTION
       " "
   INDEX    { sm48tat4xarpVoiceVLANPort  }
   ::= { sm48tat4xarpVoiceVLANPortTable 1 }

SM48TAT4XARPVoiceVLANPortEntry ::= SEQUENCE {
   sm48tat4xarpVoiceVLANPort                    Integer32,
   sm48tat4xarpVoiceVLANPortMode                Integer32,
   sm48tat4xarpVoiceVLANPortSecurity            Integer32,
   sm48tat4xarpVoiceVLANPortDiscoveryProtocol   Integer32
}

sm48tat4xarpVoiceVLANPort OBJECT-TYPE
   SYNTAX      Integer32 (1..4095)
   MAX-ACCESS  not-accessible
   STATUS      current
   DESCRIPTION
       " port, range : 1 - port number. "
   ::= { sm48tat4xarpVoiceVLANPortEntry 1 }

sm48tat4xarpVoiceVLANPortMode OBJECT-TYPE
   SYNTAX      Integer32 (0..2)
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { sm48tat4xarpVoiceVLANPortEntry 2 }

sm48tat4xarpVoiceVLANPortSecurity OBJECT-TYPE
   SYNTAX      Integer32 (0|1)
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { sm48tat4xarpVoiceVLANPortEntry 3 }

sm48tat4xarpVoiceVLANPortDiscoveryProtocol OBJECT-TYPE
   SYNTAX      Integer32 (0..2)
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { sm48tat4xarpVoiceVLANPortEntry 4 }


sm48tat4xarpVoiceVLANOUI                                          OBJECT IDENTIFIER ::= { sm48tat4xarpVoiceVLAN 2 }

sm48tat4xarpVoiceVLANOUICreate OBJECT-TYPE
   SYNTAX       Integer32(0|1)
   MAX-ACCESS   read-write
   STATUS       current
   DESCRIPTION
       "default: 0
        0 : None  (read only)
        1 : Create an OUI entry"
   ::= { sm48tat4xarpVoiceVLANOUI 1 }

sm48tat4xarpVoiceVLANOUITable OBJECT-TYPE
   SYNTAX      SEQUENCE OF SM48TAT4XARPVoiceVLANOUIEntry
   MAX-ACCESS  not-accessible
   STATUS      current
   DESCRIPTION
       " Create Voice VLAN OUI entry. Modify OUI table will
         restart auto detect OUI process. "
   ::= { sm48tat4xarpVoiceVLANOUI 2 }

sm48tat4xarpVoiceVLANOUIEntry OBJECT-TYPE
   SYNTAX      SM48TAT4XARPVoiceVLANOUIEntry
   MAX-ACCESS  not-accessible
   STATUS      current
   DESCRIPTION
       " "
   INDEX    { sm48tat4xarpVoiceVLANOUIIndex  }
   ::= { sm48tat4xarpVoiceVLANOUITable 1 }

SM48TAT4XARPVoiceVLANOUIEntry ::= SEQUENCE {
   sm48tat4xarpVoiceVLANOUIIndex         Integer32,
   sm48tat4xarpVoiceVLANTelephonyOUI     DisplayString,
   sm48tat4xarpVoiceVLANDescription      DisplayString,
   sm48tat4xarpVoiceVLANOUIRowStatus     RowStatus
}

sm48tat4xarpVoiceVLANOUIIndex OBJECT-TYPE
   SYNTAX      Integer32 (1..16)
   MAX-ACCESS  not-accessible
   STATUS      current
   DESCRIPTION
       " "
   ::= { sm48tat4xarpVoiceVLANOUIEntry 1 }

sm48tat4xarpVoiceVLANTelephonyOUI OBJECT-TYPE
   SYNTAX      DisplayString (SIZE (1..32))
   MAX-ACCESS  read-create
   STATUS      current
   DESCRIPTION
       "OUI address, format : 0a 1b 2c "
   ::= { sm48tat4xarpVoiceVLANOUIEntry 2 }

sm48tat4xarpVoiceVLANDescription OBJECT-TYPE
   SYNTAX      DisplayString (SIZE (1..32))
   MAX-ACCESS  read-create
   STATUS      current
   DESCRIPTION
       " Up to 32 characters describing OUI address. "
   ::= { sm48tat4xarpVoiceVLANOUIEntry 3 }

sm48tat4xarpVoiceVLANOUIRowStatus OBJECT-TYPE
   SYNTAX      RowStatus
   MAX-ACCESS  read-create
   STATUS      current
   DESCRIPTION
	   "This object indicates the status of this entry, and is used
	   to create/delete entries.  Any object in an entry of this table
	   may be modified while the value of the corresponding instance
	   of this object is active(1).
	   createAndGo, notReady not supported."
   ::= { sm48tat4xarpVoiceVLANOUIEntry 4 }

--sm48tat4xarpGARP                                                   OBJECT IDENTIFIER ::= { sm48tat4xarpConfiguration 3 }

--sm48tat4xarpGARPConfTable OBJECT-TYPE
--   SYNTAX      SEQUENCE OF SM48TAT4XARPGARPConfEntry
--   MAX-ACCESS  not-accessible
--   STATUS      current
--   DESCRIPTION
--       " "
--   ::= { sm48tat4xarpGARP 1 }

--sm48tat4xarpGARPConfEntry OBJECT-TYPE
--   SYNTAX      SM48TAT4XARPGARPConfEntry
--   MAX-ACCESS  not-accessible
--   STATUS      current
--   DESCRIPTION
--       " "
--   INDEX    { sm48tat4xarpGARPConfPort  }
--   ::= { sm48tat4xarpGARPConfTable 1 }

--SM48TAT4XARPGARPConfEntry ::= SEQUENCE {
--   sm48tat4xarpGARPConfPort           Integer32,
--   sm48tat4xarpGARPJoinTimer          Integer32,
--   sm48tat4xarpGARPLeaveTimer         Integer32,
--   sm48tat4xarpGARPLeaveAllTimer      Integer32,
--   sm48tat4xarpGARPApplicantion       Integer32,
--   sm48tat4xarpGARPAttributeType      Integer32,
--   sm48tat4xarpGARPApplicant          Integer32
--}

--sm48tat4xarpGARPConfPort OBJECT-TYPE
--   SYNTAX      Integer32 (1..4095)
--   MAX-ACCESS  not-accessible
--   STATUS      current
--   DESCRIPTION
--       " "
--   ::= { sm48tat4xarpGARPConfEntry 1 }

--sm48tat4xarpGARPJoinTimer OBJECT-TYPE
--   SYNTAX      Integer32 (200..1000)
--   MAX-ACCESS  read-write
--   STATUS      current
--   DESCRIPTION
--       "default: 200, range : 200 - 1000 "
--   ::= { sm48tat4xarpGARPConfEntry 2 }

--sm48tat4xarpGARPLeaveTimer OBJECT-TYPE
--   SYNTAX      Integer32 (600..3000)
--   MAX-ACCESS  read-write
--   STATUS      current
--   DESCRIPTION
--       "default: 600 , range : 600 - 3000"
--   ::= { sm48tat4xarpGARPConfEntry 3 }

--sm48tat4xarpGARPLeaveAllTimer OBJECT-TYPE
--   SYNTAX      Integer32 (10000..50000)
--   MAX-ACCESS  read-write
--   STATUS      current
--   DESCRIPTION
--       "default: 10000, range : 10000 - 50000 "
--   ::= { sm48tat4xarpGARPConfEntry 4 }

--sm48tat4xarpGARPApplicantion OBJECT-TYPE
--   SYNTAX      Integer32(1)
--   MAX-ACCESS  read-write
--   STATUS      current
--   DESCRIPTION
--       "default: 1
--       1: GVRP"
--   ::= { sm48tat4xarpGARPConfEntry 5 }

--sm48tat4xarpGARPAttributeType OBJECT-TYPE
--   SYNTAX      Integer32(1)
--   MAX-ACCESS  read-write
--   STATUS      current
--   DESCRIPTION
--       "default: 1
--       1: VLAN"
--   ::= { sm48tat4xarpGARPConfEntry 6 }

--sm48tat4xarpGARPApplicant OBJECT-TYPE
--   SYNTAX      Integer32(0|1)
--   MAX-ACCESS  read-write
--   STATUS      current
--   DESCRIPTION
--       "default: 0
--       0: normal-participant
--       1: non-participant"
--   ::= { sm48tat4xarpGARPConfEntry 7 }

--sm48tat4xarpGARPStatisticsTable OBJECT-TYPE
--   SYNTAX      SEQUENCE OF SM48TAT4XARPGARPStatisticsEntry
--   MAX-ACCESS  not-accessible
--   STATUS      current
--   DESCRIPTION
--       " Show the basic GARP port statistics. "
--   ::= { sm48tat4xarpGARP 2 }

--sm48tat4xarpGARPStatisticsEntry OBJECT-TYPE
--   SYNTAX      SM48TAT4XARPGARPStatisticsEntry
--   MAX-ACCESS  not-accessible
--   STATUS      current
--   DESCRIPTION
--       " "
--   INDEX    { sm48tat4xarpGARPStatisticsPort  }
--   ::= { sm48tat4xarpGARPStatisticsTable 1 }

--SM48TAT4XARPGARPStatisticsEntry ::= SEQUENCE {
--   sm48tat4xarpGARPStatisticsPort             Integer32,
--   sm48tat4xarpGARPStatisticsPeerMAC          DisplayString,
--   sm48tat4xarpGARPStatisticsFailedCount      Counter32
--}

--sm48tat4xarpGARPStatisticsPort OBJECT-TYPE
--   SYNTAX      Integer32 (1..4095)
--   MAX-ACCESS  not-accessible
--   STATUS      current
--   DESCRIPTION
--       " port, range : 1 - port number. "
--   ::= { sm48tat4xarpGARPStatisticsEntry 1 }

--sm48tat4xarpGARPStatisticsPeerMAC OBJECT-TYPE
--   SYNTAX      DisplayString
--   MAX-ACCESS  read-only
--   STATUS      current
--   DESCRIPTION
--       " Peer MAC is MAC address of the neighbour Switch from with GARP frame is received.  "
--   ::= { sm48tat4xarpGARPStatisticsEntry 2 }

--sm48tat4xarpGARPStatisticsFailedCount OBJECT-TYPE
--   SYNTAX      Counter32
--   MAX-ACCESS  read-only
--   STATUS      current
--   DESCRIPTION
--       " explain Failed count here. "
--   ::= { sm48tat4xarpGARPStatisticsEntry 3 }

sm48tat4xarpGVRP                                                   OBJECT IDENTIFIER ::= { sm48tat4xarpConfiguration 4 }

sm48tat4xarpGVRPConf                                                   OBJECT IDENTIFIER ::= { sm48tat4xarpGVRP 1 }

sm48tat4xarpGVRPMode OBJECT-TYPE
   SYNTAX      Integer32(0|1)
   MAX-ACCESS  read-write
   STATUS      current
   DESCRIPTION
       "default: 0,
        0: disable,
        1: enable. "
   ::= { sm48tat4xarpGVRPConf 1 }

sm48tat4xarpGVRPMaxVlan OBJECT-TYPE
   SYNTAX      Integer32(1..4095)
   MAX-ACCESS  read-write
   STATUS      current
   DESCRIPTION
       "Number of simultaniously VLANs that GVRP can control. "
   ::= { sm48tat4xarpGVRPConf 2 }

sm48tat4xarpGVRPJoinTime OBJECT-TYPE
   SYNTAX      Integer32(1..20)
   MAX-ACCESS  read-write
   STATUS      current
   DESCRIPTION
       "join-time in units of centi seconds. Range is 1-20. Default is 20. "
   ::= { sm48tat4xarpGVRPConf 3 }

sm48tat4xarpGVRPLeaveTime OBJECT-TYPE
   SYNTAX      Integer32(60..300)
   MAX-ACCESS  read-write
   STATUS      current
   DESCRIPTION
       "leave-time in units of centi seconds. Range is 60-300. Default is 60. "
   ::= { sm48tat4xarpGVRPConf 4 }

sm48tat4xarpGVRPLeaveAllTime OBJECT-TYPE
   SYNTAX      Integer32(1000..5000)
   MAX-ACCESS  read-write
   STATUS      current
   DESCRIPTION
       "leave-all-time in units of centi seconds Range is 1000-5000. Default is 1000"
   ::= { sm48tat4xarpGVRPConf 5 }

sm48tat4xarpGVRPConfTable OBJECT-TYPE
   SYNTAX      SEQUENCE OF SM48TAT4XARPGVRPConfEntry
   MAX-ACCESS  not-accessible
   STATUS      current
   DESCRIPTION
       " "
   ::= { sm48tat4xarpGVRPConf 6 }

sm48tat4xarpGVRPConfEntry OBJECT-TYPE
   SYNTAX      SM48TAT4XARPGVRPConfEntry
   MAX-ACCESS  not-accessible
   STATUS      current
   DESCRIPTION
       " "
   INDEX    { sm48tat4xarpGVRPConfPort  }
   ::= { sm48tat4xarpGVRPConfTable 1 }

SM48TAT4XARPGVRPConfEntry ::= SEQUENCE {
   sm48tat4xarpGVRPConfPort           Integer32,
   sm48tat4xarpGVRPConfPortMode       Integer32
-- sm48tat4xarpGVRPConfPortRRole      Integer32
}

sm48tat4xarpGVRPConfPort OBJECT-TYPE
   SYNTAX      Integer32 (1..4095)
   MAX-ACCESS  not-accessible
   STATUS      current
   DESCRIPTION
       " "
   ::= { sm48tat4xarpGVRPConfEntry 1 }

sm48tat4xarpGVRPConfPortMode OBJECT-TYPE
   SYNTAX      Integer32(0|1)
   MAX-ACCESS  read-write
   STATUS      current
   DESCRIPTION
       "default: 0
       1: enable
       0: disable"
   ::= { sm48tat4xarpGVRPConfEntry 2 }

--sm48tat4xarpGVRPConfPortRRole OBJECT-TYPE
--   SYNTAX      Integer32(0|1)
--   MAX-ACCESS  read-write
--   STATUS      current
--   DESCRIPTION
--       "default: 0
--       1: enable
--       0: disable"
--   ::= { sm48tat4xarpGVRPConfEntry 3 }

--sm48tat4xarpGVRPStatisticsTable OBJECT-TYPE
--   SYNTAX      SEQUENCE OF SM48TAT4XARPGVRPStatisticsEntry
--   MAX-ACCESS  not-accessible
--   STATUS      current
--   DESCRIPTION
--       " "
--   ::= { sm48tat4xarpGVRP 2 }

--sm48tat4xarpGVRPStatisticsEntry OBJECT-TYPE
--   SYNTAX      SM48TAT4XARPGVRPStatisticsEntry
--   MAX-ACCESS  not-accessible
--   STATUS      current
--   DESCRIPTION
--       " "
--   INDEX    { sm48tat4xarpGVRPStatisticsPort  }
--   ::= { sm48tat4xarpGVRPStatisticsTable 1 }

--SM48TAT4XARPGVRPStatisticsEntry ::= SEQUENCE {
--   sm48tat4xarpGVRPStatisticsPort         Integer32,
--   sm48tat4xarpGVRPStatisticsJoinTxCnt    Counter32,
--   sm48tat4xarpGVRPStatisticsLeaveTxCnt   Counter32
--}

--sm48tat4xarpGVRPStatisticsPort OBJECT-TYPE
--   SYNTAX      Integer32 (1..4095)
--   MAX-ACCESS  not-accessible
--   STATUS      current
--   DESCRIPTION
--       " "
--   ::= { sm48tat4xarpGVRPStatisticsEntry 1 }

--sm48tat4xarpGVRPStatisticsJoinTxCnt OBJECT-TYPE
--   SYNTAX      Counter32
--   MAX-ACCESS  read-only
--   STATUS      current
--   DESCRIPTION
--       " "
--   ::= { sm48tat4xarpGVRPStatisticsEntry 2 }

--sm48tat4xarpGVRPStatisticsLeaveTxCnt OBJECT-TYPE
--   SYNTAX      Counter32
--   MAX-ACCESS  read-only
--   STATUS      current
--   DESCRIPTION
--       " "
--   ::= { sm48tat4xarpGVRPStatisticsEntry 3 }


sm48tat4xarpMirroring                                             OBJECT IDENTIFIER ::= { sm48tat4xarpConfiguration 6 }

sm48tat4xarpMonitorSession OBJECT-TYPE
   SYNTAX      Integer32(1..5)
   MAX-ACCESS  read-write
   STATUS      current
   DESCRIPTION
       "Monitor session."
   ::= { sm48tat4xarpMirroring 1 }

sm48tat4xarpPortToMirrorOn OBJECT-TYPE
   SYNTAX      Integer32
   MAX-ACCESS  read-write
   STATUS      current
   DESCRIPTION
       "default: 0
        0: disable,
        range : 1 - port number. "
   ::= { sm48tat4xarpMirroring 2 }

sm48tat4xarpMirrorTable OBJECT-TYPE
   SYNTAX      SEQUENCE OF SM48TAT4XARPMirrorEntry
   MAX-ACCESS  not-accessible
   STATUS      current
   DESCRIPTION
       " "
   ::= { sm48tat4xarpMirroring 3 }

sm48tat4xarpMirrorEntry OBJECT-TYPE
   SYNTAX      SM48TAT4XARPMirrorEntry
   MAX-ACCESS  not-accessible
   STATUS      current
   DESCRIPTION
       " "
   INDEX    { sm48tat4xarpMirrorPort  }
   ::= { sm48tat4xarpMirrorTable 1 }

SM48TAT4XARPMirrorEntry ::= SEQUENCE {
   sm48tat4xarpMirrorPort		Integer32,
   sm48tat4xarpMirrorMode		Integer32
}

sm48tat4xarpMirrorPort OBJECT-TYPE
   SYNTAX      Integer32 (1..4095)
   MAX-ACCESS  not-accessible
   STATUS      current
   DESCRIPTION
       " "
   ::= { sm48tat4xarpMirrorEntry 1 }

sm48tat4xarpMirrorMode OBJECT-TYPE
   SYNTAX      Integer32(0..3)
   MAX-ACCESS  read-write
   STATUS      current
   DESCRIPTION
       "default: 0
       0: disable
       1: rx only
       2: tx only
       3: enable
       Setting Tx mirroring for analyzer port has no effect. Tx mirroring ignored"
   ::= { sm48tat4xarpMirrorEntry 2 }

sm48tat4xarpTrapEventSeverity                                             OBJECT IDENTIFIER ::= { sm48tat4xarpConfiguration 7 }

sm48tat4xarpTrapEventSeverityTable OBJECT-TYPE
   SYNTAX      SEQUENCE OF SM48TAT4XARPTrapEventSeverityEntry
   MAX-ACCESS  not-accessible
   STATUS      current
   DESCRIPTION
       " "
   ::= { sm48tat4xarpTrapEventSeverity 1 }

sm48tat4xarpTrapEventSeverityEntry OBJECT-TYPE
   SYNTAX      SM48TAT4XARPTrapEventSeverityEntry
   MAX-ACCESS  not-accessible
   STATUS      current
   DESCRIPTION
       " "
   INDEX    { sm48tat4xarpTrapEventSeverityIndex }
   ::= { sm48tat4xarpTrapEventSeverityTable 1 }

SM48TAT4XARPTrapEventSeverityEntry ::= SEQUENCE {
   sm48tat4xarpTrapEventSeverityIndex        Integer32,
   sm48tat4xarpTrapEventSeverityGroupName    DisplayString,
   sm48tat4xarpTrapEventSeverityLevel        Integer32,
   sm48tat4xarpTrapEventSeveritySyslog       Integer32,
   sm48tat4xarpTrapEventSeverityTrap         Integer32,
   sm48tat4xarpTrapEventSeveritySMTP         Integer32
}

sm48tat4xarpTrapEventSeverityIndex OBJECT-TYPE
   SYNTAX      Integer32(1..65535)
   MAX-ACCESS  not-accessible
   STATUS      current
   DESCRIPTION
       " "
   ::= { sm48tat4xarpTrapEventSeverityEntry 1 }

sm48tat4xarpTrapEventSeverityGroupName OBJECT-TYPE
   SYNTAX      DisplayString
   MAX-ACCESS  read-only
   STATUS      current
   DESCRIPTION
       "Group Name"
   ::= { sm48tat4xarpTrapEventSeverityEntry 2 }

sm48tat4xarpTrapEventSeverityLevel OBJECT-TYPE
   SYNTAX      Integer32
   MAX-ACCESS  not-accessible
   STATUS      current
   DESCRIPTION
       "0:Emergency
       1:Alert
       2:Critical
       3:Error
       4:Warning
       5:Notice
       6:Information
       7:Debug"
   ::= { sm48tat4xarpTrapEventSeverityEntry 3 }

sm48tat4xarpTrapEventSeveritySyslog OBJECT-TYPE
   SYNTAX      Integer32
   MAX-ACCESS  not-accessible
   STATUS      current
   DESCRIPTION
       "0:disable
       1:enable"
   ::= { sm48tat4xarpTrapEventSeverityEntry 4 }

sm48tat4xarpTrapEventSeverityTrap OBJECT-TYPE
   SYNTAX      Integer32
   MAX-ACCESS  not-accessible
   STATUS      current
   DESCRIPTION
       "0:disable
       1:enable"
   ::= { sm48tat4xarpTrapEventSeverityEntry 5 }

sm48tat4xarpTrapEventSeveritySMTP OBJECT-TYPE
   SYNTAX      Integer32
   MAX-ACCESS  not-accessible
   STATUS      current
   DESCRIPTION
       "0:disable
       1:enable"
   ::= { sm48tat4xarpTrapEventSeverityEntry 6 }

-- =======================================================================================================================
sm48tat4xarpSMTP                                             OBJECT IDENTIFIER ::= { sm48tat4xarpConfiguration 8 }

sm48tat4xarpSMTPMailServer OBJECT-TYPE
   SYNTAX      DisplayString
   MAX-ACCESS  read-write
   STATUS      current
   DESCRIPTION
       " Up to 47 characters describing email server. "
   ::= { sm48tat4xarpSMTP 1 }

sm48tat4xarpSMTPUserName OBJECT-TYPE
   SYNTAX      DisplayString
   MAX-ACCESS  read-write
   STATUS      current
   DESCRIPTION
       " Up to 47 characters describing user name. "
   ::= { sm48tat4xarpSMTP 2 }

sm48tat4xarpSMTPPassword OBJECT-TYPE
   SYNTAX      DisplayString
   MAX-ACCESS  read-write
   STATUS      current
   DESCRIPTION
       " Up to 47 characters describing password. "
   ::= { sm48tat4xarpSMTP 3 }

sm48tat4xarpSMTPSender OBJECT-TYPE
   SYNTAX      DisplayString
   MAX-ACCESS  read-write
   STATUS      current
   DESCRIPTION
       " Up to 47 characters describing sender. "
   ::= { sm48tat4xarpSMTP 5 }

sm48tat4xarpSMTPReturnPath OBJECT-TYPE
   SYNTAX      DisplayString
   MAX-ACCESS  read-write
   STATUS      current
   DESCRIPTION
       " Up to 47 characters describing return path. "
   ::= { sm48tat4xarpSMTP 6 }

sm48tat4xarpSMTPEmailAddress1 OBJECT-TYPE
   SYNTAX      DisplayString
   MAX-ACCESS  read-write
   STATUS      current
   DESCRIPTION
       " Up to 47 characters describing mail address. "
   ::= { sm48tat4xarpSMTP 7 }

sm48tat4xarpSMTPEmailAddress2 OBJECT-TYPE
   SYNTAX      DisplayString
   MAX-ACCESS  read-write
   STATUS      current
   DESCRIPTION
       " Up to 47 characters describing mail address. "
   ::= { sm48tat4xarpSMTP 8 }

sm48tat4xarpSMTPEmailAddress3 OBJECT-TYPE
   SYNTAX      DisplayString
   MAX-ACCESS  read-write
   STATUS      current
   DESCRIPTION
       " Up to 47 characters describing mail address. "
   ::= { sm48tat4xarpSMTP 9 }

sm48tat4xarpSMTPEmailAddress4 OBJECT-TYPE
   SYNTAX      DisplayString
   MAX-ACCESS  read-write
   STATUS      current
   DESCRIPTION
       " Up to 47 characters describing mail address. "
   ::= { sm48tat4xarpSMTP 10 }

sm48tat4xarpSMTPEmailAddress5 OBJECT-TYPE
   SYNTAX      DisplayString
   MAX-ACCESS  read-write
   STATUS      current
   DESCRIPTION
       " Up to 47 characters describing mail address. "
   ::= { sm48tat4xarpSMTP 11 }

sm48tat4xarpSMTPEmailAddress6 OBJECT-TYPE
   SYNTAX      DisplayString
   MAX-ACCESS  read-write
   STATUS      current
   DESCRIPTION
       " Up to 47 characters describing mail address. "
   ::= { sm48tat4xarpSMTP 12 }

-- =======================================================================================================================
sm48tat4xarpACLConf                                              OBJECT IDENTIFIER ::= { sm48tat4xarpConfiguration 9 }

-- RowStatus Info:  createAndGo, notReady not supported.
-- =======================================================================================================================
-- Textual Conventions for the sm48tat4xarp Acl Mib
-- =======================================================================================================================
--
    sm48tat4xarpACL                     OBJECT IDENTIFIER  ::= { sm48tat4xarpACLConf 1 }
    sm48tat4xarpACLACE                  OBJECT IDENTIFIER  ::= { sm48tat4xarpACLConf 3 }

--
-- =======================================================================================================================
-- Start sm48tat4xarpACLPortConf group
-- =======================================================================================================================
--sm48tat4xarpACLPortConfTable

    sm48tat4xarpACLPortConfTable OBJECT-TYPE
               SYNTAX      SEQUENCE OF     SM48TAT4XARPACLPortConfEntry
               MAX-ACCESS  not-accessible
               STATUS      current
               DESCRIPTION
                   "The ACL Port Conf Table.
                    INDEX for this table is ifIndex which is
                    equivalent to the panel port number."
               ::= {     sm48tat4xarpACL 1 }

    sm48tat4xarpACLPortConfEntry OBJECT-TYPE
               SYNTAX          SM48TAT4XARPACLPortConfEntry
               MAX-ACCESS  not-accessible
               STATUS      current
               DESCRIPTION
                   "The ACL Port Conf Entry. "
               INDEX    {     ifIndex  }
               ::= {     sm48tat4xarpACLPortConfTable 1 }

    SM48TAT4XARPACLPortConfEntry             ::=
            SEQUENCE {
                 sm48tat4xarpACLPortConfPolicyID        Integer32,
                 sm48tat4xarpACLPortConfAction          INTEGER,
                 sm48tat4xarpACLPortConfRateLimiterID   Integer32,
                 sm48tat4xarpACLPortConfPortRedirect    Integer32,
                 sm48tat4xarpACLPortConfMirror          AdminMode,
                 sm48tat4xarpACLPortConfLogging         AdminMode,
                 sm48tat4xarpACLPortConfShutdown        AdminMode,
                 sm48tat4xarpACLPortConfState           AdminMode,
                 sm48tat4xarpACLPortConfCounter         Counter32
                 }

    sm48tat4xarpACLPortConfPolicyID OBJECT-TYPE
               SYNTAX       Integer32 (0..127)
               MAX-ACCESS   read-write
               STATUS       current
               DESCRIPTION
                   "The policy to apply to this port.
                    default: 0, range : 0 - 127. "
               ::= {     sm48tat4xarpACLPortConfEntry 2 }

    sm48tat4xarpACLPortConfAction OBJECT-TYPE
               SYNTAX      INTEGER { deny(0), permit(1) }
               MAX-ACCESS  read-write
               STATUS      current
               DESCRIPTION
                   "Whether forwarding is permitted ('Permit') or denied ('Deny').
                    default: 1,
                    0: Deny,
                    1: Permit."
               ::= {     sm48tat4xarpACLPortConfEntry 3 }

    sm48tat4xarpACLPortConfRateLimiterID OBJECT-TYPE
               SYNTAX      Integer32 (0..16)
               MAX-ACCESS  read-write
               STATUS      current
               DESCRIPTION
                   "The rate limiter to apply on this port.
                    0: Disable,
                    range : 0 - 16. "
               ::= {     sm48tat4xarpACLPortConfEntry 4 }

    sm48tat4xarpACLPortConfPortRedirect OBJECT-TYPE
               SYNTAX      Integer32 (0..4095)
               MAX-ACCESS  read-write
               STATUS      current
               DESCRIPTION
                   "Port frames are redirected on.
                    0: Disable,
                    range : 0 - end port number. "
               ::= {     sm48tat4xarpACLPortConfEntry 5 }

    sm48tat4xarpACLPortConfMirror OBJECT-TYPE
               SYNTAX      AdminMode
               MAX-ACCESS  read-write
               STATUS      current
               DESCRIPTION
                   "The mirror operation of this port."
               ::= {     sm48tat4xarpACLPortConfEntry 6 }

    sm48tat4xarpACLPortConfLogging OBJECT-TYPE
               SYNTAX      AdminMode
               MAX-ACCESS  read-write
               STATUS      current
               DESCRIPTION
                   "Specify the logging operation of this port."
               ::= {     sm48tat4xarpACLPortConfEntry 7 }

    sm48tat4xarpACLPortConfShutdown OBJECT-TYPE
               SYNTAX      AdminMode
               MAX-ACCESS  read-write
               STATUS      current
               DESCRIPTION
                   "Specify the port shut down operation of this port."
               DEFVAL  { disable }
               ::= {     sm48tat4xarpACLPortConfEntry 8 }

    sm48tat4xarpACLPortConfState OBJECT-TYPE
               SYNTAX      AdminMode
               MAX-ACCESS  read-write
               STATUS      current
               DESCRIPTION
                   "Specify the port state of this port."
               DEFVAL  { enable }
               ::= {     sm48tat4xarpACLPortConfEntry 9 }

    sm48tat4xarpACLPortConfCounter OBJECT-TYPE
               SYNTAX      Counter32
               MAX-ACCESS  read-only
               STATUS      current
               DESCRIPTION
                   "Counts the number of frames that match this ACE. "
               ::= {     sm48tat4xarpACLPortConfEntry 10 }

--
-- =======================================================================================================================
-- Start sm48tat4xarpACLRateLimiter group
-- =======================================================================================================================
--sm48tat4xarpACLRateLimiterTable

    sm48tat4xarpACLRateLimiterTable OBJECT-TYPE
               SYNTAX      SEQUENCE OF     SM48TAT4XARPACLRateLimiterEntry
               MAX-ACCESS  not-accessible
               STATUS      current
               DESCRIPTION
                   "The ACL Rate Limiter Table."
               ::= {     sm48tat4xarpACL 2 }

    sm48tat4xarpACLRateLimiterEntry OBJECT-TYPE
               SYNTAX          SM48TAT4XARPACLRateLimiterEntry
               MAX-ACCESS  not-accessible
               STATUS      current
               DESCRIPTION
                   "The ACL Rate Limiter Entry. "
               INDEX    {     sm48tat4xarpACLRateLimiterID  }
               ::= {     sm48tat4xarpACLRateLimiterTable 1 }

    SM48TAT4XARPACLRateLimiterEntry             ::= SEQUENCE {
                 sm48tat4xarpACLRateLimiterID       Integer32,
                 sm48tat4xarpACLRateLimiterRate     Integer32,
                 sm48tat4xarpACLRateLimiterUnit     Integer32
                 }

    sm48tat4xarpACLRateLimiterID OBJECT-TYPE
               SYNTAX      Integer32 (1..16)
               MAX-ACCESS  not-accessible
               STATUS      current
               DESCRIPTION
                   "Rate Limiter ID.
                    range : 1-16 "
               ::= {     sm48tat4xarpACLRateLimiterEntry 1 }

    sm48tat4xarpACLRateLimiterRate OBJECT-TYPE
               SYNTAX      Integer32(0..500000)
               MAX-ACCESS  read-write
               STATUS      current
               DESCRIPTION
                   "default: 1,
                    range :
                    <0-500000> 10pps,The valid rate is 0, 10, 20, 30,
                    ..., 5000000 in pps.
                    <0-400000> 25kbps,The valid rate is 0, 25, 50, 75,...,
                    10000000 in kbps."
               ::= {     sm48tat4xarpACLRateLimiterEntry 2 }

    sm48tat4xarpACLRateLimiterUnit OBJECT-TYPE
               SYNTAX      Integer32(0|1)
               MAX-ACCESS  read-write
               STATUS      current
               DESCRIPTION
                   "Specify the rate unit.
                    0: 10pps, 1: 25kbps.
                   "
               ::= {     sm48tat4xarpACLRateLimiterEntry 3 }

--
-- =======================================================================================================================
-- Start sm48tat4xarpACLACE group
-- =======================================================================================================================
--sm48tat4xarpACLACEClear

    sm48tat4xarpACLACEClear OBJECT-TYPE
               SYNTAX      ActivateCmd
               MAX-ACCESS  read-write
               STATUS      current
               DESCRIPTION
                   "Clear all ACE counters."
               ::= {     sm48tat4xarpACLACE 1 }

--sm48tat4xarpACLACETable

    sm48tat4xarpACLACETable OBJECT-TYPE
               SYNTAX      SEQUENCE OF     SM48TAT4XARPACLACEEntry
               MAX-ACCESS  not-accessible
               STATUS      current
               DESCRIPTION
                   "Create ACL ACE entry. "
               ::= {     sm48tat4xarpACLACE 2 }

    sm48tat4xarpACLACEEntry OBJECT-TYPE
               SYNTAX          SM48TAT4XARPACLACEEntry
               MAX-ACCESS  not-accessible
               STATUS      current
               DESCRIPTION
                   "The ACLACE Table."
               INDEX    {     sm48tat4xarpACLACEIndex  }
               ::= {     sm48tat4xarpACLACETable 1 }

    SM48TAT4XARPACLACEEntry             ::= SEQUENCE {
                 sm48tat4xarpACLACEIndex                Integer32,
                 sm48tat4xarpACLACEID                   Integer32,
                 sm48tat4xarpACLACENextID               Integer32,
--               sm48tat4xarpACLACELoopUp               AdminMode,
                 sm48tat4xarpACLACEIngressPort          DisplayString,
                 sm48tat4xarpACLACEPortPolicyNumber     Integer32,
                 sm48tat4xarpACLACEPortPolicyBitmask    Integer32,
                 sm48tat4xarpACLACEFrameType            INTEGER,
                 sm48tat4xarpACLACEAction               INTEGER,
                 sm48tat4xarpACLACEFilterPort           DisplayString,
                 sm48tat4xarpACLACEDenyPortRedirect     DisplayString,
                 sm48tat4xarpACLACERateLimiter          Integer32,
                 sm48tat4xarpACLACEMirror               AdminMode,
                 sm48tat4xarpACLACELogging              AdminMode,
                 sm48tat4xarpACLACEShutdown             AdminMode,
                 sm48tat4xarpACLACECounter              Counter32,
                 sm48tat4xarpACLACEVLAN8021QTagged      INTEGER,
                 sm48tat4xarpACLACEVLANVID              Integer32,
                 sm48tat4xarpACLACEVLANTagPriority      Integer32,
                 sm48tat4xarpACLACESMAC                 DisplayString,
                 sm48tat4xarpACLACEDMACType             INTEGER,
                 sm48tat4xarpACLACEDMAC                 DisplayString,
                 sm48tat4xarpACLACEEtherType            Integer32,
                 sm48tat4xarpACLACEArpOpCode            INTEGER,
                 sm48tat4xarpACLACEArpFlagsRequestReply INTEGER,
                 sm48tat4xarpACLACEArpFlagsArpSMac      INTEGER,
                 sm48tat4xarpACLACEArpFlagsRarpDmac     INTEGER,
                 sm48tat4xarpACLACEArpFlagsLength       INTEGER,
                 sm48tat4xarpACLACEArpFlagsIp           INTEGER,
                 sm48tat4xarpACLACEArpFlagsEthernet     INTEGER,
                 sm48tat4xarpACLACESIPType              INTEGER,
                 sm48tat4xarpACLACESIPIPAddress         IpAddress,
                 sm48tat4xarpACLACESIPIPMask            IpAddress,
                 sm48tat4xarpACLACEDIPType              INTEGER,
                 sm48tat4xarpACLACEDIPIPAddress         IpAddress,
                 sm48tat4xarpACLACEDIPIPMask            IpAddress,
                 sm48tat4xarpACLACEIPProtocol           INTEGER,
                 sm48tat4xarpACLACEIPProtocolValue      Integer32,
                 sm48tat4xarpACLACEIPFlagsTTL           INTEGER,
                 sm48tat4xarpACLACEIPFlagsFragment      INTEGER,
                 sm48tat4xarpACLACEIPFlagsOptions       INTEGER,
                 sm48tat4xarpACLACEICMPType             Integer32,
                 sm48tat4xarpACLACEICMPCode             Integer32,
                 sm48tat4xarpACLACESourcePort           DisplayString,
                 sm48tat4xarpACLACEDestPort             DisplayString,
                 sm48tat4xarpACLACETCPFlagsFin          INTEGER,
                 sm48tat4xarpACLACETCPFlagsSyn          INTEGER,
                 sm48tat4xarpACLACETCPFlagsRst          INTEGER,
                 sm48tat4xarpACLACETCPFlagsPsh          INTEGER,
                 sm48tat4xarpACLACETCPFlagsAck          INTEGER,
                 sm48tat4xarpACLACETCPFlagsUrg          INTEGER,
                 sm48tat4xarpACLACEIPv6SIPAddress       DisplayString,
                 sm48tat4xarpACLACEIPv6SIPBitmask       DisplayString,
                 sm48tat4xarpACLACEIPv6HopLimit         INTEGER,
                 sm48tat4xarpACLACESMACMask             DisplayString,
                 sm48tat4xarpACLACEDMACMask             DisplayString,
                 sm48tat4xarpACLACERowStatus            RowStatus
                 }

    sm48tat4xarpACLACEIndex OBJECT-TYPE
               SYNTAX      Integer32(1..256)
               MAX-ACCESS  not-accessible
               STATUS      current
               DESCRIPTION
                   "The index. "
               ::= {     sm48tat4xarpACLACEEntry 1 }

    sm48tat4xarpACLACEID OBJECT-TYPE
               SYNTAX      Integer32(1..256)
               MAX-ACCESS  read-create
               STATUS      current
               DESCRIPTION
                   "If the ACE ID is specified and an entry with this ACE ID
                    already exists, the ACE will be modified. Otherwise, a
                    new ACE will be added.
                    range : 1 - 256. "
               ::= {     sm48tat4xarpACLACEEntry 2 }

    sm48tat4xarpACLACENextID OBJECT-TYPE
               SYNTAX      Integer32 (0..256)
               MAX-ACCESS  read-create
               STATUS      current
               DESCRIPTION
                   "If the next ACE ID is non zero, the ACE will be placed
                    before this ACE in the list. If the next ACE ID is zero,
                    the ACE will be placed last in the list.
                    range : 0 - 256. "
               ::= {     sm48tat4xarpACLACEEntry 3 }

--    sm48tat4xarpACLACELoopUp OBJECT-TYPE
--               SYNTAX      AdminMode
--               MAX-ACCESS  read-create
--               STATUS      current
--               DESCRIPTION
--                   "Specify the second lookup operation of the ACE."
--               ::= {     sm48tat4xarpACLACEEntry 4 }
--
    sm48tat4xarpACLACEIngressPort OBJECT-TYPE
               SYNTAX      DisplayString
               MAX-ACCESS  read-create
               STATUS      current
               DESCRIPTION
                   "Indicates the ingress port of the ACE. Possible values are:
                    0: All,The ACE will match all ingress port.
                    Port n: The ACE will match a specific ingress port."
               ::= {     sm48tat4xarpACLACEEntry 5 }

    sm48tat4xarpACLACEPortPolicyNumber OBJECT-TYPE
               SYNTAX      Integer32(0..127)
               MAX-ACCESS  read-create
               STATUS      current
               DESCRIPTION
                   "policy value.
                    range : 0 - 127.
                    0: Any."
               ::= {     sm48tat4xarpACLACEEntry 6 }

    sm48tat4xarpACLACEPortPolicyBitmask OBJECT-TYPE
               SYNTAX      Integer32(0..127)
               MAX-ACCESS  read-create
               STATUS      current
               DESCRIPTION
                   "When 'Specific' is selected for the policy filter,
                    you can enter a specific policy bitmask.
                    range : 0 - 127, 0: no data."
               ::= {     sm48tat4xarpACLACEEntry 7 }

    sm48tat4xarpACLACEFrameType OBJECT-TYPE
               SYNTAX      INTEGER {   any(0), etype(1), arp(2),
                                       ipv4(3), ipv6(4) }
               MAX-ACCESS  read-create
               STATUS      current
               DESCRIPTION
                   "Select the frame type for this ACE.
                    When change the type Related oid will set default.
                    0: any,
                    1: etype,
                    2: arp,
                    3: ipv4,
                    4: ipv6."
               ::= {     sm48tat4xarpACLACEEntry 8 }

    sm48tat4xarpACLACEAction OBJECT-TYPE
               SYNTAX      INTEGER { deny(0), permit(1), filter(2) }
               MAX-ACCESS  read-create
               STATUS      current
               DESCRIPTION
                   "0: Deny
				    1: Permit
					2: Filter"
               ::= {     sm48tat4xarpACLACEEntry 9 }

    sm48tat4xarpACLACEFilterPort OBJECT-TYPE
               SYNTAX      DisplayString
               MAX-ACCESS  read-create
               STATUS      current
               DESCRIPTION
                   "When 'Action' is 'Filter' can set.
                    0: Disable,
                    Port n: The ACE applies to this port number, where n is
                    the number of the switch port.
                    range: 0 - Port number.
                   "
               ::= {     sm48tat4xarpACLACEEntry 10 }

    sm48tat4xarpACLACEDenyPortRedirect OBJECT-TYPE
               SYNTAX      DisplayString
               MAX-ACCESS  read-create
               STATUS      current
               DESCRIPTION
                   "Frames that hit the ACE are redirected to the port
                    number specified here.Disabled,indicates that the port
                    redirect operation is disabled.
                    When 'Action' is 'Deny' can set.
                    0: disabled,
                    Port no: The ACE applies to this port number, where n is
                    the number of the switch port."
               ::= {     sm48tat4xarpACLACEEntry 11 }

    sm48tat4xarpACLACERateLimiter OBJECT-TYPE
               SYNTAX      Integer32(0..16)
               MAX-ACCESS  read-create
               STATUS      current
               DESCRIPTION
                   "default: 0,
                    0: Disable
                    range : 0 - 16 "
               ::= {     sm48tat4xarpACLACEEntry 12 }

    sm48tat4xarpACLACEMirror OBJECT-TYPE
               SYNTAX      AdminMode
               MAX-ACCESS  read-create
               STATUS      current
               DESCRIPTION
                   "default: 0,
                    0: disable - Frames matching the ACE are not mirrored.
                    1: enable - Frames matching the ACE are mirrored.
                   "
               ::= {     sm48tat4xarpACLACEEntry 13 }

    sm48tat4xarpACLACELogging OBJECT-TYPE
               SYNTAX      AdminMode
               MAX-ACCESS  read-create
               STATUS      current
               DESCRIPTION
                   "default: 0,
                    0: disable - Frames matching the ACE are not logged.
                    1: enable - Frames matching the ACE are stored in the
                   system log."
               ::= {     sm48tat4xarpACLACEEntry 14 }

    sm48tat4xarpACLACEShutdown OBJECT-TYPE
               SYNTAX      AdminMode
               MAX-ACCESS  read-create
               STATUS      current
               DESCRIPTION
                   "default: 0,
                    0: disable - Port shut down is disabled for the AC.
                    1: enable - If a frame matches the ACE, the ingress port
                    will be disabled."
               ::= {     sm48tat4xarpACLACEEntry 15 }

    sm48tat4xarpACLACECounter OBJECT-TYPE
               SYNTAX      Counter32
               MAX-ACCESS  read-only
               STATUS      current
               DESCRIPTION
                   "The counter indicates the number of times the ACE was
                    hit by a frame. "
               ::= {     sm48tat4xarpACLACEEntry 16 }

    sm48tat4xarpACLACEVLAN8021QTagged OBJECT-TYPE
               SYNTAX      INTEGER { disable(0), enable(1), any(2) }
               MAX-ACCESS  read-create
               STATUS      current
               DESCRIPTION
                   "Specify whether frames can hit the action according to
                    the 802.1Q tagged.
                    default: 2,
                    0: disable - Untagged frame only.
                    1: enable - Tagged frame only.
                    2: Any - Any value is allowed.
                    "
               ::= {     sm48tat4xarpACLACEEntry 17 }

    sm48tat4xarpACLACEVLANVID OBJECT-TYPE
               SYNTAX      Integer32(0..4095)
               MAX-ACCESS  read-create
               STATUS      current
               DESCRIPTION
                   "Specify the VLAN ID filter for this ACE.
                    The vid can't be set when 802.1Q Tagged is disabled.
                    default: 0,
                    0: Any - No VLAN ID filter is specified.
                    range : 0 - 4095 "
               ::= {     sm48tat4xarpACLACEEntry 18 }

    sm48tat4xarpACLACEVLANTagPriority OBJECT-TYPE
               SYNTAX      Integer32(0..14)
               MAX-ACCESS  read-create
               STATUS      current
               DESCRIPTION
                   "Specify the tag priority for this ACE.
                    The tag priority can't be set when 802.1Q Tagged is disabled.
                    range: 0-14
					0:0
					1:1
					2:2
					3:3
					4:4
					5:5
					6:6
					7:7
					8:0-1
					9:2-3
					10:4-5
					11:6-7
					12:0-3
					13:4-7
					14:Any
					"
               ::= {     sm48tat4xarpACLACEEntry 19 }

    sm48tat4xarpACLACESMAC OBJECT-TYPE
               SYNTAX      DisplayString
               MAX-ACCESS  read-create
               STATUS      current
               DESCRIPTION
                   "Configure source MAC address for this ACE.
                    <mac-address>: A frame that hits this ACE matches this
                    source MAC address value. xx-xx-xx-xx-xx-xx.
                    Any: Don't care."
               ::= {    sm48tat4xarpACLACEEntry 20 }

    sm48tat4xarpACLACEDMACType OBJECT-TYPE
               SYNTAX      INTEGER { any(0), mc(1), bc(2), uc(3) ,
                                     macAddress(4) , noData(5) }
               MAX-ACCESS  read-create
               STATUS      current
               DESCRIPTION
                   "DMAC Type.
                    default: 0,
                    0: Any - Don't care.
                    1: Multicast - Frame must be multicast.
                    2: Broadcast - Frame must be broadcast.
                    3: Unicast - Frame must be unicast.
                    4: mac address.
                    5: no data."
               DEFVAL  { any }
               ::= {    sm48tat4xarpACLACEEntry 21 }

    sm48tat4xarpACLACEDMAC OBJECT-TYPE
               SYNTAX      DisplayString
               MAX-ACCESS  read-create
               STATUS      current
               DESCRIPTION
                   "Configure destination MAC address for this ACE.
                    <mac-address>: A frame that hits this ACE matches this
                    destination MAC address value. xx-xx-xx-xx-xx-xx."
               ::= {     sm48tat4xarpACLACEEntry 22 }

    sm48tat4xarpACLACEEtherType OBJECT-TYPE
               SYNTAX      Integer32(-1..65535)
               MAX-ACCESS  read-create
               STATUS      current
               DESCRIPTION
                   "0: Any
				   range : 0, or 1536(0x0600) - 65535(0xffff) but excluding 0x0800(IPv4) 0x0806(ARP) and
                    0x86DD(IPv6).
                    -1: No data. "
               ::= {     sm48tat4xarpACLACEEntry 23 }

    sm48tat4xarpACLACEArpOpCode OBJECT-TYPE
               SYNTAX      INTEGER { any(0), arp(1), rarp(2),
                                     other(3), noData(4) }
               MAX-ACCESS  read-create
               STATUS      current
               DESCRIPTION
                   "Configure ARP opcode for this ACE.
                    default: 0,
                    0: Any - Don't care.
                    1: arp.
                    2: rarp.
                    3: other.
                    4: No data."
               DEFVAL  { any }
               ::= {     sm48tat4xarpACLACEEntry 24 }

    sm48tat4xarpACLACEArpFlagsRequestReply OBJECT-TYPE
               SYNTAX      INTEGER { reply(0), request(1), any(2), noData(3)}
               MAX-ACCESS  read-create
               STATUS      current
               DESCRIPTION
                   "Specify the available ARP/RARP opcode (OP) flag for this ACE.
                    default: 2,
                    0: Frame must have ARP Reply or RARP Reply OP flag.
                    1: Frame must have ARP Request or RARP Request OP flag set.
                    2: Any - Don't care.
                    3: No data."
               DEFVAL  { any }
               ::= {     sm48tat4xarpACLACEEntry 25 }

    sm48tat4xarpACLACEArpFlagsArpSMac OBJECT-TYPE
               SYNTAX      INTEGER { notEqualSMAC(0), equalSMAC(1),
                                     any(2), noData(3)}
               MAX-ACCESS  read-create
               STATUS      current
               DESCRIPTION
                   "Specify whether frames can hit the action according to their
                    sender hardware address field (SHA) settings.
                    default: 2,
                    0: ARP frames where SHA is not equal to the SMAC address.
                    1: ARP frames where SHA is equal to the SMAC address.
                    2: Any - Don't care.
                    3: No data."
               DEFVAL  { any }
               ::= {     sm48tat4xarpACLACEEntry 26 }

    sm48tat4xarpACLACEArpFlagsRarpDmac OBJECT-TYPE
               SYNTAX      INTEGER { notEqualDMAC(0), equalDMAC(1),
                                     any(2), noData(3)}
               MAX-ACCESS  read-create
               STATUS      current
               DESCRIPTION
                   "Specify whether frames can hit the action according to
                    their target hardware address field (THA) settings.
                    default: 2,
                    0: RARP frames where THA is not equal to the DMAC address.
                    1: RARP frames where THA is equal to the DMAC address.
                    2: Any - Don't care.
                    3: No data."
               DEFVAL  { any }
               ::= {     sm48tat4xarpACLACEEntry 27 }

    sm48tat4xarpACLACEArpFlagsLength OBJECT-TYPE
               SYNTAX      INTEGER { notEqualEthIpV4 (0), equalEthIpV4(1),
                                     any(2), noData(3)}
               MAX-ACCESS  read-create
               STATUS      current
               DESCRIPTION
                   "Specify whether frames can hit the action according to
                    their ARP/RARP hardware address length (HLN) and protocol
                    address length (PLN) settings.
                    default: 2,
                    0: ARP/RARP frames where the HLN is not equal to
                    Ethernet(0x06) or the (PLN) is not equal to IPv4(0x04).
                    1: ARP/RARP frames where the HLN is equal to Ethernet (0x06)
                    and the (PLN) is equal to IPv4(0x04).
                    2: Any - Don't care.
                    3: No data."
                DEFVAL  { any }
                ::= {     sm48tat4xarpACLACEEntry 28 }

    sm48tat4xarpACLACEArpFlagsIp OBJECT-TYPE
               SYNTAX      INTEGER { notEqualEth(0), equalEth(1),
                                     any(2), noData(3)}
               MAX-ACCESS  read-create
               STATUS      current
               DESCRIPTION
                   "Specify whether frames can hit the action according to
                    their ARP/RARP hardware address space (HRD) settings.
                    default: 2,
                    0: ARP/RARP frames where the HLD is not equal to Ethernet(1).
                    1: ARP/RARP frames where the HLD is equal to Ethernet(1).
                    2: Any - Don't care.
                    3: No data."
               DEFVAL  { any }
               ::= {     sm48tat4xarpACLACEEntry 29 }

    sm48tat4xarpACLACEArpFlagsEthernet OBJECT-TYPE
               SYNTAX      INTEGER { notEqualIp(0), equalIp(1),
                                     any(2), noData(3)}
               MAX-ACCESS  read-create
               STATUS      current
               DESCRIPTION
                   "Specify whether frames can hit the action
                    according to their ARP/RARP protocol address space (PRO) settings.
                    default: 2,
                    0: ARP/RARP frames where the PRO is not equal to IP\n(0x800).
                    1: ARP/RARP frames where the PRO is equal to IP(0x800).
                    2: Any - Don't care.
                    3: No data."
               DEFVAL  { any }
               ::= {     sm48tat4xarpACLACEEntry 30 }

    sm48tat4xarpACLACESIPType OBJECT-TYPE
               SYNTAX      INTEGER { any(0), ip(1), network(2), noData(3) }
               MAX-ACCESS  read-create
               STATUS      current
               DESCRIPTION
                   "Configure source IP address for this ACE.
                    default: 0,
                    0: Any - Don't care.
                    1: IP Address.
                    2: Network.
                    3: No data."
               DEFVAL  { any }
               ::= {     sm48tat4xarpACLACEEntry 31 }

    sm48tat4xarpACLACESIPIPAddress OBJECT-TYPE
               SYNTAX      IpAddress
               MAX-ACCESS  read-create
               STATUS      current
               DESCRIPTION
                   "A frame that hits this ACE matches this source IP address
                    value."
               ::= {     sm48tat4xarpACLACEEntry 32 }

    sm48tat4xarpACLACESIPIPMask OBJECT-TYPE
               SYNTAX      IpAddress
               MAX-ACCESS  read-create
               STATUS      current
               DESCRIPTION
                   "Specific sender IP mask in dotted decimal notation."
               ::= {     sm48tat4xarpACLACEEntry 33 }

    sm48tat4xarpACLACEDIPType OBJECT-TYPE
               SYNTAX      INTEGER { any(0), ip(1), network(2), noData(3) }
               MAX-ACCESS  read-create
               STATUS      current
               DESCRIPTION
                   "Configure destination IP address for this ACE.
                    default: 0,
                    0: Any - Don't care.
                    1: IP Address.
                    2: Network.
                    3: No data."
               DEFVAL  { any }
               ::= {     sm48tat4xarpACLACEEntry 34 }

    sm48tat4xarpACLACEDIPIPAddress OBJECT-TYPE
               SYNTAX      IpAddress
               MAX-ACCESS  read-create
               STATUS      current
               DESCRIPTION
                   "A frame that hits this ACE matches this destination IP
                    address value."
               ::= {     sm48tat4xarpACLACEEntry 35 }

    sm48tat4xarpACLACEDIPIPMask OBJECT-TYPE
               SYNTAX      IpAddress
               MAX-ACCESS  read-create
               STATUS      current
               DESCRIPTION
                   "Specific sender IP mask in dotted decimal notation."
               ::= {     sm48tat4xarpACLACEEntry 36 }

    sm48tat4xarpACLACEIPProtocol OBJECT-TYPE
               SYNTAX      INTEGER{ any(0), icmp(1), udp(2), tcp(3),
                                    other(4), noData(5)}
               MAX-ACCESS  read-create
               STATUS      current
               DESCRIPTION
                   "Specify the IP protocol filter for this ACE.
                    default: 0,
                    0: Any,
                    1: ICMP,
                    2: UDP,
                    3: TCP,
                    4: Other,
                    5: no data."
               DEFVAL  { any }
               ::= {     sm48tat4xarpACLACEEntry 37 }

    sm48tat4xarpACLACEIPProtocolValue OBJECT-TYPE
               SYNTAX      Integer32(0..256)
               MAX-ACCESS  read-create
               STATUS      current
               DESCRIPTION
                   "Configure IP protocol value for this ACE when IP Protocol
                    is 'other'.
                    default: 256,
                    256: No data.
                    range : 0 - 256"
               ::= {     sm48tat4xarpACLACEEntry 38 }

    sm48tat4xarpACLACEIPFlagsTTL OBJECT-TYPE
               SYNTAX      INTEGER { nonZero(0), zero(1), any(2), noData(3) }
               MAX-ACCESS  read-create
               STATUS      current
               DESCRIPTION
                   "Specify the Time-to-Live settings for this ACE.
                    default: 0,
                    0: zero,
                    1: Non-Zero
                    2: Any,,
                    3: No data."
               DEFVAL  { nonZero }
               ::= {     sm48tat4xarpACLACEEntry 39 }

    sm48tat4xarpACLACEIPFlagsFragment OBJECT-TYPE
               SYNTAX      INTEGER{yes(0), no(1), any(2), noData(3)}
               MAX-ACCESS  read-create
               STATUS      current
               DESCRIPTION
                   "Specify the fragment offset settings for this ACE.
                    default: 2,
                    0: No,
                    1: Yes,
                    2: Any,
                    3: No data."
               DEFVAL  { any }
               ::= {     sm48tat4xarpACLACEEntry 40 }

    sm48tat4xarpACLACEIPFlagsOptions OBJECT-TYPE
               SYNTAX      INTEGER{yes(0), no(1), any(2),  noData(3)}
               MAX-ACCESS  read-create
               STATUS      current
               DESCRIPTION
                   "Specify the options flag setting for this ACE.
                    default: 2,
                    0: No,
                    1: Yes,
                    2: Any,
                    3: No data."
               DEFVAL  { any }
               ::= {     sm48tat4xarpACLACEEntry 41 }

    sm48tat4xarpACLACEICMPType OBJECT-TYPE
               SYNTAX      Integer32(0..257)
               MAX-ACCESS  read-create
               STATUS      current
               DESCRIPTION
                   "Configure ICMP type for this ACE.
                    default: 256,
                    256: Any - Don't care.
                    257: No data.
                    range : 0 - 257."
               ::= { sm48tat4xarpACLACEEntry 42 }

    sm48tat4xarpACLACEICMPCode OBJECT-TYPE
               SYNTAX      Integer32(0..257)
               MAX-ACCESS  read-create
               STATUS      current
               DESCRIPTION
                   "Configure ICMP code for this ACE.
                    default: 256,
                    256: Any - Don't care.
                    257: No data.
                    range : 0 - 257."
               ::= {     sm48tat4xarpACLACEEntry 43 }

    sm48tat4xarpACLACESourcePort OBJECT-TYPE
               SYNTAX      DisplayString
               MAX-ACCESS  read-create
               STATUS      current
               DESCRIPTION
                   "Configure Source UDP/TCP port range for this ACE.
                    default: any,
                    specific: 0~65535,
                    range : 0 - 65535."
               ::= {     sm48tat4xarpACLACEEntry 44 }

    sm48tat4xarpACLACEDestPort OBJECT-TYPE
               SYNTAX      DisplayString
               MAX-ACCESS  read-create
               STATUS      current
               DESCRIPTION
                   "Configure Destination UDP/TCP port range for this ACE.
                    default: any,
                    specific: 0~65535,
                    range : 0 - 65535."
               ::= {     sm48tat4xarpACLACEEntry 45 }

    sm48tat4xarpACLACETCPFlagsFin OBJECT-TYPE
               SYNTAX      INTEGER { unset(0), set(1), any(2), noData(3) }
               MAX-ACCESS  read-create
               STATUS      current
               DESCRIPTION
                   "Configure TCP (FIN) flags for this ACE.
                    default: 2,
                    0: TCP frames where the FIN field is unset.
                    1: TCP frames where the FIN field is set.
                    2: Any - Don't care.
                    3: No data."
               DEFVAL  { any }
               ::= {     sm48tat4xarpACLACEEntry 46 }

    sm48tat4xarpACLACETCPFlagsSyn OBJECT-TYPE
               SYNTAX      INTEGER { unset(0), set(1), any(2), noData(3) }
               MAX-ACCESS  read-create
               STATUS      current
               DESCRIPTION
                   "Configure TCP (SYN) flags for this ACE.
                    default: 2,
                    0: TCP frames where the SYN field is unset.
                    1: TCP frames where the SYN field is set.
                    2: Any - Don't care.
                    3: No data."
               DEFVAL  { any }
               ::= {     sm48tat4xarpACLACEEntry 47 }

    sm48tat4xarpACLACETCPFlagsRst OBJECT-TYPE
               SYNTAX      INTEGER { unset(0), set(1), any(2), noData(3) }
               MAX-ACCESS  read-create
               STATUS      current
               DESCRIPTION
                   "Configure TCP (RST) flags for this ACE.
                    default: 2,
                    0: TCP frames where the RST field is unset.
                    1: TCP frames where the RST field is set.
                    2: Any - Don't care.
                    3: No data."
               DEFVAL  { any }
               ::= {     sm48tat4xarpACLACEEntry 48 }

    sm48tat4xarpACLACETCPFlagsPsh OBJECT-TYPE
               SYNTAX      INTEGER { unset(0), set(1), any(2), noData(3) }
               MAX-ACCESS  read-create
               STATUS      current
               DESCRIPTION
                   "Configure TCP (PSH) flags for this ACE.
                    default: 2,
                    0: TCP frames where the PSH field is unset.
                    1: TCP frames where the PSH field is set.
                    2: Any - Don't care.
                    3: No data."
               DEFVAL  { any }
               ::= {     sm48tat4xarpACLACEEntry 49 }

    sm48tat4xarpACLACETCPFlagsAck OBJECT-TYPE
               SYNTAX      INTEGER { unset(0), set(1), any(2), noData(3) }
               MAX-ACCESS  read-create
               STATUS      current
               DESCRIPTION
                   "Configure TCP (ACK) flags for this ACE.
                    default: 2,
                    0: TCP frames where the ACK field is unset.
                    1: TCP frames where the ACK field is set.
                    2: Any - Don't care.
                    3: No data."
               DEFVAL  { any }
               ::= {     sm48tat4xarpACLACEEntry 50 }

    sm48tat4xarpACLACETCPFlagsUrg OBJECT-TYPE
               SYNTAX      INTEGER { unset(0), set(1), any(2), noData(3) }
               MAX-ACCESS  read-create
               STATUS      current
               DESCRIPTION
                   "Configure TCP (URG) flags for this ACE.
                    default: 2,
                    0: TCP frames where the URG field is unset.
                    1: TCP frames where the URG field is set.
                    2: Any - Don't care.
                    3: No data."
               DEFVAL  { any }
               ::= {     sm48tat4xarpACLACEEntry 51 }

    sm48tat4xarpACLACEIPv6SIPAddress OBJECT-TYPE
               SYNTAX      DisplayString
               MAX-ACCESS  read-create
               STATUS      current
               DESCRIPTION
                   "When 'Specific' is selected for the source IPv6 filter,
                    you can enter a specific SIPv6 address.
                    The field only supported last 32 bits for IPv6 address. "
               ::= {     sm48tat4xarpACLACEEntry 52 }

    sm48tat4xarpACLACEIPv6SIPBitmask OBJECT-TYPE
               SYNTAX      DisplayString
               MAX-ACCESS  read-create
               STATUS      current
               DESCRIPTION
                   "When 'Specific' is selected for the source IPv6 filter,
                    you can enter a specific SIPv6 mask.
                    The field only supported last 32 bits for IPv6 address. "
               ::= {     sm48tat4xarpACLACEEntry 53 }

    sm48tat4xarpACLACEIPv6HopLimit OBJECT-TYPE
               SYNTAX      INTEGER { unset(0), set(1), any(2), noData(3) }
               MAX-ACCESS  read-create
               STATUS      current
               DESCRIPTION
                   "Specify the hop limit settings for this ACE.
                    default: 2,
                    0: Where the Hop Limit field is unset.
                    1: Where the Hop Limit field is set.
                    2: Any - Don't care,
                    3: No data."
               DEFVAL  { any }
               ::= {     sm48tat4xarpACLACEEntry 54 }

    sm48tat4xarpACLACESMACMask OBJECT-TYPE
               SYNTAX      DisplayString
               MAX-ACCESS  read-create
               STATUS      current
               DESCRIPTION
                   "Configure source MAC address mask for this ACE.
                    <mac-address>: A frame that hits this ACE matches this
                    source MAC address value. xx-xx-xx-xx-xx-xx."
               ::= {    sm48tat4xarpACLACEEntry 56 }

    sm48tat4xarpACLACEDMACMask OBJECT-TYPE
               SYNTAX      DisplayString
               MAX-ACCESS  read-create
               STATUS      current
               DESCRIPTION
                   "Configure destination MAC address mask for this ACE.
                    <mac-address>: A frame that hits this ACE matches this
                    destination MAC address value. xx-xx-xx-xx-xx-xx."
               ::= {     sm48tat4xarpACLACEEntry 57 }

    sm48tat4xarpACLACERowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sm48tat4xarpACLACEEntry 58 }

--
-- =======================================================================================================================
-- Start sm48tat4xarpACLStatus group
-- =======================================================================================================================
--sm48tat4xarpACLStatusTable

    sm48tat4xarpACLStatusTable OBJECT-TYPE
               SYNTAX      SEQUENCE OF     SM48TAT4XARPACLStatusEntry
               MAX-ACCESS  not-accessible
               STATUS      current
               DESCRIPTION
                   " ACL ACE Status entry. "
               ::= {     sm48tat4xarpACL 4 }

    sm48tat4xarpACLStatusEntry OBJECT-TYPE
               SYNTAX          SM48TAT4XARPACLStatusEntry
               MAX-ACCESS  not-accessible
               STATUS      current
               DESCRIPTION
                   "The ACL Status Entry."
               INDEX    {    sm48tat4xarpACLStatusIndex  }
               ::= {     sm48tat4xarpACLStatusTable 1 }

    SM48TAT4XARPACLStatusEntry             ::= SEQUENCE {
                 sm48tat4xarpACLStatusIndex          Integer32,
                 sm48tat4xarpACLStatusUser           DisplayString,
                 sm48tat4xarpACLStatusID             Integer32,
                 sm48tat4xarpACLStatusIngressPort    DisplayString,
                 sm48tat4xarpACLStatusFrameType      DisplayString,
                 sm48tat4xarpACLStatusAction         DisplayString,
                 sm48tat4xarpACLStatusRateLimiter    DisplayString,
                 sm48tat4xarpACLStatusPortRedirect   DisplayString,
                 sm48tat4xarpACLStatusMirror         DisplayString,
                 sm48tat4xarpACLStatusCPU            DisplayString,
                 sm48tat4xarpACLStatusCPUOnce        DisplayString,
                 sm48tat4xarpACLStatusCounter        Counter32,
                 sm48tat4xarpACLStatusConflict       DisplayString
                 }

    sm48tat4xarpACLStatusIndex OBJECT-TYPE
               SYNTAX      Integer32(1..256)
               MAX-ACCESS  not-accessible
               STATUS      current
               DESCRIPTION
                   "The ACL status index. "
               ::= {     sm48tat4xarpACLStatusEntry 1 }

    sm48tat4xarpACLStatusUser OBJECT-TYPE
               SYNTAX      DisplayString
               MAX-ACCESS  read-only
               STATUS      current
               DESCRIPTION
                   "Indicates the ACL user.
                    S : Static,
                    IPMG : IP Management,
                    IPSG : IP Source Guard,
                    IPMC : IPMC,
                    ARPI : Arp Inspection,
                    UPnP : UPnP,
                    DHCP : DHCP. "
               ::= {     sm48tat4xarpACLStatusEntry 2 }

    sm48tat4xarpACLStatusID OBJECT-TYPE
               SYNTAX      Integer32(1..256)
               MAX-ACCESS  read-only
               STATUS      current
               DESCRIPTION
                   "ACE ID.
                    range : 1 - 256. "
               ::= {     sm48tat4xarpACLStatusEntry 3 }

    sm48tat4xarpACLStatusIngressPort OBJECT-TYPE
               SYNTAX      DisplayString
               MAX-ACCESS  read-only
               STATUS      current
               DESCRIPTION
                   "Indicates the ingress port of the ACE. Possible values are:
                    All: The ACE will match all ingress port.
                    Port: The ACE will match a specific ingress port. "
               ::= {     sm48tat4xarpACLStatusEntry 4 }

    sm48tat4xarpACLStatusFrameType OBJECT-TYPE
               SYNTAX      DisplayString
               MAX-ACCESS  read-only
               STATUS      current
               DESCRIPTION
                   "Indicates the frame type of the ACE.
                    Any: The ACE will match any frame type.
                    EType: The ACE will match Ethernet Type frames.
                    Note that an Ethernet Type based ACE will not get matched
                    by IP and ARP frames.
                    ARP: The ACE will match ARP/RARP frames.
                    IPv4: The ACE will match all IPv4 frames.
                    IPv4/ICMP: The ACE will match IPv4 frames with ICMP protocol.
                    IPv4/UDP: The ACE will match IPv4 frames with UDP protocol.
                    IPv4/TCP: The ACE will match IPv4 frames with TCP protocol.
                    IPv4/Other: The ACE will match IPv4 frames, which are not
                    ICMP/UDP/TCP.
                    IPv6: The ACE will match all IPv6 standard frames. "
               ::= {     sm48tat4xarpACLStatusEntry 5 }

    sm48tat4xarpACLStatusAction OBJECT-TYPE
               SYNTAX      DisplayString
               MAX-ACCESS  read-only
               STATUS      current
               DESCRIPTION
                   "Indicates the forwarding action of the ACE. "
               ::= {     sm48tat4xarpACLStatusEntry 6 }

    sm48tat4xarpACLStatusRateLimiter OBJECT-TYPE
               SYNTAX      DisplayString
               MAX-ACCESS  read-only
               STATUS      current
               DESCRIPTION
                   "Indicates the rate limiter number of the ACE. "
               ::= {     sm48tat4xarpACLStatusEntry 7 }

    sm48tat4xarpACLStatusPortRedirect OBJECT-TYPE
               SYNTAX      DisplayString
               MAX-ACCESS  read-only
               STATUS      current
               DESCRIPTION
                   "Indicates the port redirect operation of the ACE.
                    Frames matching the ACE are redirected to the port number. "
               ::= {     sm48tat4xarpACLStatusEntry 8 }

    sm48tat4xarpACLStatusMirror OBJECT-TYPE
               SYNTAX      DisplayString
               MAX-ACCESS  read-only
               STATUS      current
               DESCRIPTION
                   "Specify the mirror operation of this port."
               ::= {     sm48tat4xarpACLStatusEntry 9 }

    sm48tat4xarpACLStatusCPU OBJECT-TYPE
               SYNTAX      DisplayString
               MAX-ACCESS  read-only
               STATUS      current
               DESCRIPTION
                   "Forward packet that matched the specific ACE to CPU. "
               ::= {     sm48tat4xarpACLStatusEntry 10 }

    sm48tat4xarpACLStatusCPUOnce OBJECT-TYPE
               SYNTAX      DisplayString
               MAX-ACCESS  read-only
               STATUS      current
               DESCRIPTION
                   "Forward first packet that matched the specific ACE to CPU. "
               ::= {     sm48tat4xarpACLStatusEntry 11 }

    sm48tat4xarpACLStatusCounter OBJECT-TYPE
               SYNTAX      Counter32
               MAX-ACCESS  read-only
               STATUS      current
               DESCRIPTION
                   "The counter indicates the number of times the ACE was hit
                    by a frame. "
               ::= {     sm48tat4xarpACLStatusEntry 12 }

    sm48tat4xarpACLStatusConflict OBJECT-TYPE
               SYNTAX      DisplayString
               MAX-ACCESS  read-only
               STATUS      current
               DESCRIPTION
                   "Indicates the hardware status of the specific ACE.
                    The specific ACE is not applied to the hardware due to
                    hardware limitations. "
               ::= {     sm48tat4xarpACLStatusEntry 13 }


-- =======================================================================================================================
-- sm48tat4xarpAclConformance
-- =======================================================================================================================
sm48tat4xarpAclConformance OBJECT IDENTIFIER ::= { sm48tat4xarpACL 200 }

sm48tat4xarpAclCompliances OBJECT IDENTIFIER ::= { sm48tat4xarpAclConformance 1 }

sm48tat4xarpAclGroups    OBJECT IDENTIFIER ::= { sm48tat4xarpAclConformance 2 }

sm48tat4xarpACLPortConfGroup OBJECT-GROUP
    OBJECTS {
                -- sm48tat4xarpACLPortConfTable
                 sm48tat4xarpACLPortConfPolicyID,
                 sm48tat4xarpACLPortConfAction,
                 sm48tat4xarpACLPortConfRateLimiterID,
                 sm48tat4xarpACLPortConfPortRedirect,
                 sm48tat4xarpACLPortConfMirror,
                 sm48tat4xarpACLPortConfLogging,
                 sm48tat4xarpACLPortConfShutdown,
                 sm48tat4xarpACLPortConfState,
                 sm48tat4xarpACLPortConfCounter
            }
     STATUS  current
     DESCRIPTION
            "The collection of objects which are used to indicate
            sm48tat4xarp ACL information."
    ::= { sm48tat4xarpAclGroups 1 }

sm48tat4xarpACLRateLimiterGroup OBJECT-GROUP
    OBJECTS {
                -- sm48tat4xarpACLRateLimiterTable
                 sm48tat4xarpACLRateLimiterRate,
                 sm48tat4xarpACLRateLimiterUnit
            }
     STATUS  current
     DESCRIPTION
            "The collection of objects which are used to indicate
            sm48tat4xarp ACL information."
    ::= { sm48tat4xarpAclGroups 2 }

sm48tat4xarpACLACEGroup OBJECT-GROUP
    OBJECTS {
                -- sm48tat4xarpACLACEClear
                 sm48tat4xarpACLACEClear,

                -- sm48tat4xarpACLACETable
                 sm48tat4xarpACLACEID,
                 sm48tat4xarpACLACENextID,
--               sm48tat4xarpACLACELoopUp,
                 sm48tat4xarpACLACEIngressPort,
                 sm48tat4xarpACLACEPortPolicyNumber,
                 sm48tat4xarpACLACEPortPolicyBitmask,
                 sm48tat4xarpACLACEFrameType,
                 sm48tat4xarpACLACEAction,
                 sm48tat4xarpACLACEFilterPort,
                 sm48tat4xarpACLACEDenyPortRedirect,
                 sm48tat4xarpACLACERateLimiter,
                 sm48tat4xarpACLACEMirror,
                 sm48tat4xarpACLACELogging,
                 sm48tat4xarpACLACEShutdown,
                 sm48tat4xarpACLACECounter,
                 sm48tat4xarpACLACEVLAN8021QTagged,
                 sm48tat4xarpACLACEVLANVID,
                 sm48tat4xarpACLACEVLANTagPriority,
                 sm48tat4xarpACLACESMAC,
                 sm48tat4xarpACLACEDMACType,
                 sm48tat4xarpACLACEDMAC,
                 sm48tat4xarpACLACEEtherType,
                 sm48tat4xarpACLACEArpOpCode,
                 sm48tat4xarpACLACEArpFlagsRequestReply,
                 sm48tat4xarpACLACEArpFlagsArpSMac,
                 sm48tat4xarpACLACEArpFlagsRarpDmac,
                 sm48tat4xarpACLACEArpFlagsLength,
                 sm48tat4xarpACLACEArpFlagsIp,
                 sm48tat4xarpACLACEArpFlagsEthernet,
                 sm48tat4xarpACLACESIPType,
                 sm48tat4xarpACLACESIPIPAddress,
                 sm48tat4xarpACLACESIPIPMask,
                 sm48tat4xarpACLACEDIPType,
                 sm48tat4xarpACLACEDIPIPAddress,
                 sm48tat4xarpACLACEDIPIPMask,
                 sm48tat4xarpACLACEIPProtocol,
                 sm48tat4xarpACLACEIPProtocolValue,
                 sm48tat4xarpACLACEIPFlagsTTL,
                 sm48tat4xarpACLACEIPFlagsFragment,
                 sm48tat4xarpACLACEIPFlagsOptions,
                 sm48tat4xarpACLACEICMPType,
                 sm48tat4xarpACLACEICMPCode,
                 sm48tat4xarpACLACESourcePort,
                 sm48tat4xarpACLACEDestPort,
                 sm48tat4xarpACLACETCPFlagsFin,
                 sm48tat4xarpACLACETCPFlagsSyn,
                 sm48tat4xarpACLACETCPFlagsRst,
                 sm48tat4xarpACLACETCPFlagsPsh,
                 sm48tat4xarpACLACETCPFlagsAck,
                 sm48tat4xarpACLACETCPFlagsUrg,
                 sm48tat4xarpACLACEIPv6SIPAddress,
                 sm48tat4xarpACLACEIPv6SIPBitmask,
                 sm48tat4xarpACLACEIPv6HopLimit,
                 sm48tat4xarpACLACERowStatus
            }
     STATUS  current
     DESCRIPTION
            "The collection of objects which are used to indicate
            sm48tat4xarp ACL information."
    ::= { sm48tat4xarpAclGroups 3 }

sm48tat4xarpACLStatusGroup OBJECT-GROUP
    OBJECTS {
                -- sm48tat4xarpACLStatusTable
                 sm48tat4xarpACLStatusUser,
                 sm48tat4xarpACLStatusID,
                 sm48tat4xarpACLStatusIngressPort,
                 sm48tat4xarpACLStatusFrameType,
                 sm48tat4xarpACLStatusAction,
                 sm48tat4xarpACLStatusRateLimiter,
                 sm48tat4xarpACLStatusPortRedirect,
                 sm48tat4xarpACLStatusMirror,
                 sm48tat4xarpACLStatusCPU,
                 sm48tat4xarpACLStatusCPUOnce,
                 sm48tat4xarpACLStatusCounter,
                 sm48tat4xarpACLStatusConflict
            }
     STATUS  current
     DESCRIPTION
            "The collection of objects which are used to indicate
            sm48tat4xarp ACL information."
    ::= { sm48tat4xarpAclGroups 4 }


-- =======================================================================================================================
-- =======================================================================================================================
 -- RowStatus Info:  createAndGo, notReady not supported.
-- =======================================================================================================================
-- Textual Conventions for the sm48tat4xarp Qos Mib
-- =======================================================================================================================
--
sm48tat4xarpQosConf                    OBJECT IDENTIFIER ::= { sm48tat4xarpConfiguration 10 }
    sm48tat4xarpQos                        OBJECT IDENTIFIER   ::= { sm48tat4xarpQosConf  1  }
    sm48tat4xarpQosPortClassification      OBJECT IDENTIFIER   ::= { sm48tat4xarpQos 1 }
    sm48tat4xarpQosPortPolicing            OBJECT IDENTIFIER   ::= { sm48tat4xarpQos 2 }
--  sm48tat4xarpQosQueuePolicing           OBJECT IDENTIFIER   ::= { sm48tat4xarpQos 3 }
--  sm48tat4xarpQosPortScheduler           OBJECT IDENTIFIER   ::= { sm48tat4xarpQos 4 }
    sm48tat4xarpQosEgressPortPCPRemarking  OBJECT IDENTIFIER   ::= { sm48tat4xarpQos 6 }
    sm48tat4xarpQosPortDSCP                OBJECT IDENTIFIER   ::= { sm48tat4xarpQos 7 }
    sm48tat4xarpQosDSCPBasedQoS            OBJECT IDENTIFIER   ::= { sm48tat4xarpQos 8 }
    sm48tat4xarpQosDSCPTranslation         OBJECT IDENTIFIER   ::= { sm48tat4xarpQos 9 }
    sm48tat4xarpQosDSCPClassification      OBJECT IDENTIFIER   ::= { sm48tat4xarpQos 10 }
    sm48tat4xarpQosControlList             OBJECT IDENTIFIER   ::= { sm48tat4xarpQos 11 }
    sm48tat4xarpQosStormControl            OBJECT IDENTIFIER   ::= { sm48tat4xarpQos 12 }
    sm48tat4xarpQosPortStormControl        OBJECT IDENTIFIER   ::= { sm48tat4xarpQos 13 }
    sm48tat4xarpQosWRED                    OBJECT IDENTIFIER   ::= { sm48tat4xarpQos 14 }
    sm48tat4xarpQosQCLStatus               OBJECT IDENTIFIER   ::= { sm48tat4xarpQos 15 }
    sm48tat4xarpQosPortShapers             OBJECT IDENTIFIER   ::= { sm48tat4xarpQos 16 }
    sm48tat4xarpQosPortSchedulers          OBJECT IDENTIFIER   ::= { sm48tat4xarpQos 17 }
--
-- =======================================================================================================================
-- Start sm48tat4xarpQosPortClassification group
-- =======================================================================================================================
--sm48tat4xarpQosPortClassificationTable

     sm48tat4xarpQosPortClassificationTable OBJECT-TYPE
               SYNTAX      SEQUENCE OF     SM48TAT4XARPQosPortClassificationEntry
               MAX-ACCESS  not-accessible
               STATUS      current
               DESCRIPTION
                   "QoS Ingress Port Classification.
                    INDEX for this table is ifIndex which is
                    equivalent to the panel port number."
               ::= {     sm48tat4xarpQosPortClassification  1 }

    sm48tat4xarpQosPortClassificationEntry OBJECT-TYPE
               SYNTAX          SM48TAT4XARPQosPortClassificationEntry
               MAX-ACCESS  not-accessible
               STATUS      current
               DESCRIPTION
                   "The Qos Port Classification Table."
               INDEX    {     ifIndex  }
               ::= {     sm48tat4xarpQosPortClassificationTable 1 }

    SM48TAT4XARPQosPortClassificationEntry             ::= SEQUENCE {
                sm48tat4xarpQosPortClassificationQoSClass        Integer32,
                sm48tat4xarpQosPortClassificationDPlevel         Integer32,
                sm48tat4xarpQosPortClassificationPCP             Integer32,
                sm48tat4xarpQosPortClassificationDEI             Integer32,
                sm48tat4xarpQosPortClassificationPCPClassification AdminMode,
                sm48tat4xarpQosPortClassificationDSCPBased       AdminMode,
--              sm48tat4xarpQosPortClassificationQCLAddr         INTEGER,
--              sm48tat4xarpQosPortClassificationKeyType         KeyType,
                sm48tat4xarpQosPortClassificationWredGroup       Integer32
                }

    sm48tat4xarpQosPortClassificationQoSClass OBJECT-TYPE
               SYNTAX      Integer32(0..7)
               MAX-ACCESS  read-write
               STATUS      current
               DESCRIPTION
                  "Controls the default QoS class, i.e., the QoS class for
                   frames not classified
                   in any way. There is a one to one mapping between
                   QoS class, queue and
                   priority. A QoS class of 0 (zero) has the lowest priority.
                   NOTe: If the QoS class has been dynamically changed, then
                   the actual QoS class
                   is shown in parentheses after the configured QoS class.
                   range: 0~7,
                   default: 0."
               ::= {     sm48tat4xarpQosPortClassificationEntry 2 }

    sm48tat4xarpQosPortClassificationDPlevel OBJECT-TYPE
               SYNTAX      Integer32(0..3)
               MAX-ACCESS  read-write
               STATUS      current
               DESCRIPTION
                   "DP level for frames not classified in any way.
                    range: 0~3,
                    default: 0."
               ::= {     sm48tat4xarpQosPortClassificationEntry 3 }

    sm48tat4xarpQosPortClassificationPCP OBJECT-TYPE
               SYNTAX      Integer32(0..7)
               MAX-ACCESS  read-write
               STATUS      current
               DESCRIPTION
                  "Priority Code Point. It is a 3-bit field storing
                   the priority level for the 802.1Q frame.
                   range: 0~7,
                   default: 0.
                   "
               ::= {     sm48tat4xarpQosPortClassificationEntry 4 }

    sm48tat4xarpQosPortClassificationDEI OBJECT-TYPE
               SYNTAX      Integer32(0|1)
               MAX-ACCESS  read-write
               STATUS      current
               DESCRIPTION
                  "Drop Eligible Indicator. It is a 1-bit field in the VLAN.
                   range 0~1,
                   default: 0.
                  "
               ::= {     sm48tat4xarpQosPortClassificationEntry 5 }

    sm48tat4xarpQosPortClassificationPCPClassification OBJECT-TYPE
               SYNTAX      AdminMode
               MAX-ACCESS  read-write
               STATUS      current
               DESCRIPTION
                  "Configure the classification mode for tagged frames.
                  "
               DEFVAL  { disable }
               ::= {     sm48tat4xarpQosPortClassificationEntry 6 }

    sm48tat4xarpQosPortClassificationDSCPBased OBJECT-TYPE
               SYNTAX      AdminMode
               MAX-ACCESS  read-write
               STATUS      current
               DESCRIPTION
                  "Click to Enable DSCP Based QoS Ingress Port Classification."
               DEFVAL  { disable }
               ::= {     sm48tat4xarpQosPortClassificationEntry 7 }

--    sm48tat4xarpQosPortClassificationQCLAddr OBJECT-TYPE
--               SYNTAX      INTEGER { sMacSip(0), dMacDip (1) }
--               MAX-ACCESS  read-write
--               STATUS      current
--               DESCRIPTION
--                  "Controls the QCL address matching mode.
--                   0: SMAC/SIP,
--                   1: DMAC/DIP,
--                  default: SMAC/SIP.
--                  Only support SPARX_III."
--               DEFVAL  { sMacSip }
--               ::= {     sm48tat4xarpQosPortClassificationEntry 8 }

--    sm48tat4xarpQosPortClassificationKeyType OBJECT-TYPE
--               SYNTAX      KeyType
--               MAX-ACCESS  read-write
--               STATUS      current
--               DESCRIPTION
--                  "The key type specifying the key generated for frames received
--                   on the port.
--                   0: Normal, Half key, match outer tag, SIP/DIP and SMAC/DMAC.
--                   1: Double Tag: Quarter key, match inner and outer tag.
--                   2: IP Address: Half key, match inner and outer tag, SIP and
--                      DIP. For non-IP frames, match outer tag only.
--                   3: MAC and IP Address: Full key, match inner and outer tag,
--                      SMAC, DMAC, SIP and DIP.
--                   Only support on SERVAL version."
--               DEFVAL  { normal }
--               ::= {     sm48tat4xarpQosPortClassificationEntry 9 }

    sm48tat4xarpQosPortClassificationWredGroup OBJECT-TYPE
               SYNTAX      Integer32
               MAX-ACCESS  read-write
               STATUS      current
               DESCRIPTION
                  "Controls the WRED group membership. Range:1-3."
               ::= {     sm48tat4xarpQosPortClassificationEntry 10 }

--sm48tat4xarpQoSIngressPortTagClassificationTable
    sm48tat4xarpQoSIngressPortTagClassificationTable OBJECT-TYPE
               SYNTAX      SEQUENCE OF     SM48TAT4XARPQoSIngressPortTagClassificationEntry
               MAX-ACCESS  not-accessible
               STATUS      current
               DESCRIPTION
                   "Show QoS Ingress Port Tag Classification.
                    INDEX for this table is ifIndex which is
                    equivalent to the panel port number."
               ::= {     sm48tat4xarpQosPortClassification 2 }

    sm48tat4xarpQoSIngressPortTagClassificationEntry OBJECT-TYPE
               SYNTAX          SM48TAT4XARPQoSIngressPortTagClassificationEntry
               MAX-ACCESS  not-accessible
               STATUS      current
               DESCRIPTION
                   "QoS Ingress Port Tag Classification entry."
               INDEX    {     ifIndex,
                              sm48tat4xarpQoSIngressPortTagPCP,
                              sm48tat4xarpQoSIngressPortTagDEI  }
               ::= {     sm48tat4xarpQoSIngressPortTagClassificationTable 1 }

    SM48TAT4XARPQoSIngressPortTagClassificationEntry             ::= SEQUENCE {
                sm48tat4xarpQoSIngressPortTagPCP                   INTEGER,
                sm48tat4xarpQoSIngressPortTagDEI                   INTEGER,
                sm48tat4xarpQoSIngressPortTagQosClass              Integer32,
                sm48tat4xarpQoSIngressPortTagDPLevel               Integer32
                }

    sm48tat4xarpQoSIngressPortTagPCP OBJECT-TYPE
               SYNTAX      INTEGER { pcp0(1),
                                     pcp1(2),
                                     pcp2(3),
                                     pcp3(4),
                                     pcp4(5),
                                     pcp5(6),
                                     pcp6(7),
                                     pcp7(8) }
               MAX-ACCESS  not-accessible
               STATUS      current
               DESCRIPTION
                   "range: 1-8,
                    PCP0:1, PCP1:2..."
               ::= {     sm48tat4xarpQoSIngressPortTagClassificationEntry 2 }

    sm48tat4xarpQoSIngressPortTagDEI OBJECT-TYPE
               SYNTAX      INTEGER { dei0(1), dei1(2) }
               MAX-ACCESS  not-accessible
               STATUS      current
               DESCRIPTION
                   "Ingress Port Tag dei,
                    DEI0:1, DEI1:2."
               ::= {     sm48tat4xarpQoSIngressPortTagClassificationEntry 3 }

    sm48tat4xarpQoSIngressPortTagQosClass OBJECT-TYPE
               SYNTAX      Integer32(0..7)
               MAX-ACCESS  read-write
               STATUS      current
               DESCRIPTION
                   "range: 0-7."
               ::= {     sm48tat4xarpQoSIngressPortTagClassificationEntry 4 }

    sm48tat4xarpQoSIngressPortTagDPLevel OBJECT-TYPE
               SYNTAX      Integer32(0..3)
               MAX-ACCESS  read-write
               STATUS      current
               DESCRIPTION
                   "range: 0-3."
               ::= {     sm48tat4xarpQoSIngressPortTagClassificationEntry 5 }


--
-- =======================================================================================================================
-- Start sm48tat4xarpQosPortPolicing group
-- =======================================================================================================================
--sm48tat4xarpQosPortPolicingTable
   sm48tat4xarpQosPortPolicingTable OBJECT-TYPE
               SYNTAX      SEQUENCE OF     SM48TAT4XARPQosPortPolicingEntry
               MAX-ACCESS  not-accessible
               STATUS      current
               DESCRIPTION
                   "The Policer settings.
                    INDEX for this table is ifIndex which is
                    equivalent to the panel port number."
               ::= {     sm48tat4xarpQosPortPolicing 1 }

    sm48tat4xarpQosPortPolicingEntry OBJECT-TYPE
               SYNTAX          SM48TAT4XARPQosPortPolicingEntry
               MAX-ACCESS  not-accessible
               STATUS      current
               DESCRIPTION
                   "The Policer setting entry."
               INDEX    {     ifIndex  }
               ::= {     sm48tat4xarpQosPortPolicingTable 1 }

    SM48TAT4XARPQosPortPolicingEntry             ::= SEQUENCE {
                sm48tat4xarpQosPortPolicingEnabled         AdminMode,
                sm48tat4xarpQosPortPolicingRate            Integer32,
                sm48tat4xarpQosPortPolicingUnit            Integer32,
                sm48tat4xarpQosPortPolicingFlowControl     AdminMode
                }

    sm48tat4xarpQosPortPolicingEnabled OBJECT-TYPE
               SYNTAX      AdminMode
               MAX-ACCESS  read-write
               STATUS      current
               DESCRIPTION
                  "Controls whether the policer is enabled on this switch port."
               DEFVAL  { disable }
               ::= {     sm48tat4xarpQosPortPolicingEntry 2 }

    sm48tat4xarpQosPortPolicingRate OBJECT-TYPE
               SYNTAX      Integer32
               MAX-ACCESS  read-write
               STATUS      current
               DESCRIPTION
                   "Controls the rate for the policer.
                    default: 500(kbps)."
               ::= {     sm48tat4xarpQosPortPolicingEntry 3 }

    sm48tat4xarpQosPortPolicingUnit OBJECT-TYPE
               SYNTAX      Integer32
               MAX-ACCESS  read-write
               STATUS      current
               DESCRIPTION
                   "Controls the unit of measure for the policer rate.
                    0: kbps
                    1: Mbps
		    2: fps
		    3: kfps
		    "
               ::= {     sm48tat4xarpQosPortPolicingEntry 4 }

    sm48tat4xarpQosPortPolicingFlowControl OBJECT-TYPE
               SYNTAX      AdminMode
               MAX-ACCESS  read-write
               STATUS      current
               DESCRIPTION
                   "If flow control is enabled and the port is in flow control mode,
                    then pause frames are sent instead of discarding frames."
               DEFVAL  { disable }
               ::= {     sm48tat4xarpQosPortPolicingEntry 5 }

--
-- =======================================================================================================================
-- Start sm48tat4xarpQosQueuePolicing group
-- =======================================================================================================================
--sm48tat4xarpQosQueuePolicingTable
--    sm48tat4xarpQosQueuePolicingTable OBJECT-TYPE
--               SYNTAX      SEQUENCE OF     SM48TAT4XARPQosQueuePolicingEntry
--               MAX-ACCESS  not-accessible
--               STATUS      current
--               DESCRIPTION
--                   "The Queue Policer settings.
--                    INDEX for this table is ifIndex which is
--                    equivalent to the panel port number."
--               ::= {     sm48tat4xarpQosQueuePolicing 1 }
--
--    sm48tat4xarpQosQueuePolicingEntry OBJECT-TYPE
--               SYNTAX          SM48TAT4XARPQosQueuePolicingEntry
--               MAX-ACCESS  not-accessible
--               STATUS      current
--               DESCRIPTION
--                   "The Qos Queue Policing Entry."
--               INDEX    {     ifIndex  }
--               ::= {     sm48tat4xarpQosQueuePolicingTable 1 }
--
--    SM48TAT4XARPQosQueuePolicingEntry             ::= SEQUENCE {
--                sm48tat4xarpQosQueuePolicingQueue0Enable   AdminMode,
--                sm48tat4xarpQosQueuePolicingQueue0Rate     Integer32,
--		sm48tat4xarpQosQueuePolicingQueue0Unit     Integer32,
--                sm48tat4xarpQosQueuePolicingQueue1Enable   AdminMode,
--                sm48tat4xarpQosQueuePolicingQueue1Rate     Integer32,
--		sm48tat4xarpQosQueuePolicingQueue1Unit     Integer32,
--                sm48tat4xarpQosQueuePolicingQueue2Enable   AdminMode,
--                sm48tat4xarpQosQueuePolicingQueue2Rate     Integer32,
--                sm48tat4xarpQosQueuePolicingQueue2Unit     Integer32,
--                sm48tat4xarpQosQueuePolicingQueue3Enable   AdminMode,
--                sm48tat4xarpQosQueuePolicingQueue3Rate     Integer32,
--                sm48tat4xarpQosQueuePolicingQueue3Unit     Integer32,
--                sm48tat4xarpQosQueuePolicingQueue4Enable   AdminMode,
--                sm48tat4xarpQosQueuePolicingQueue4Rate     Integer32,
--		sm48tat4xarpQosQueuePolicingQueue4Unit     Integer32,
--                sm48tat4xarpQosQueuePolicingQueue5Enable   AdminMode,
--                sm48tat4xarpQosQueuePolicingQueue5Rate     Integer32,
--		sm48tat4xarpQosQueuePolicingQueue5Unit     Integer32,
--                sm48tat4xarpQosQueuePolicingQueue6Enable   AdminMode,
--                sm48tat4xarpQosQueuePolicingQueue6Rate     Integer32,
--		sm48tat4xarpQosQueuePolicingQueue6Unit     Integer32,
--                sm48tat4xarpQosQueuePolicingQueue7Enable   AdminMode,
--                sm48tat4xarpQosQueuePolicingQueue7Rate     Integer32,
--		sm48tat4xarpQosQueuePolicingQueue7Unit     Integer32
--                }
--
--    sm48tat4xarpQosQueuePolicingQueue0Enable OBJECT-TYPE
--               SYNTAX      AdminMode
--               MAX-ACCESS  read-write
--               STATUS      current
--               DESCRIPTION
--                   "Controls whether the queue 0 policer is enabled on this switch port."
--               DEFVAL  { disable }
--               ::= {     sm48tat4xarpQosQueuePolicingEntry 3 }
--
--    sm48tat4xarpQosQueuePolicingQueue0Rate OBJECT-TYPE
--               SYNTAX      Integer32
--               MAX-ACCESS  read-write
--               STATUS      current
--               DESCRIPTION
--                   "Controls whether the queue 0 policer is enabled on this switch port.
--                    default: 500(Kbps)"
--               ::= {     sm48tat4xarpQosQueuePolicingEntry 4 }
--
--    sm48tat4xarpQosQueuePolicingQueue0Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sm48tat4xarpQosQueuePolicingEntry 5 }
--
--    sm48tat4xarpQosQueuePolicingQueue1Enable OBJECT-TYPE
--               SYNTAX      AdminMode
--               MAX-ACCESS  read-write
--               STATUS      current
--               DESCRIPTION
--                   "Controls whether the queue 1 policer is enabled on this switch port."
--               DEFVAL  { disable }
--               ::= {     sm48tat4xarpQosQueuePolicingEntry 6 }
--
--    sm48tat4xarpQosQueuePolicingQueue1Rate OBJECT-TYPE
--               SYNTAX      Integer32
--               MAX-ACCESS  read-write
--               STATUS      current
--               DESCRIPTION
--                   "Controls whether the queue 1 policer is enabled on this switch port.,
--                    default: 500(Kbps)"
--               ::= {     sm48tat4xarpQosQueuePolicingEntry 7 }
--
--    sm48tat4xarpQosQueuePolicingQueue1Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sm48tat4xarpQosQueuePolicingEntry 8 }
--
--    sm48tat4xarpQosQueuePolicingQueue2Enable OBJECT-TYPE
--               SYNTAX      AdminMode
--               MAX-ACCESS  read-write
--               STATUS      current
--               DESCRIPTION
--                   "Controls whether the queue 2 policer is enabled on this switch port."
--               DEFVAL  { disable }
--               ::= {     sm48tat4xarpQosQueuePolicingEntry 9 }
--
--    sm48tat4xarpQosQueuePolicingQueue2Rate OBJECT-TYPE
--               SYNTAX      Integer32
--               MAX-ACCESS  read-write
--               STATUS      current
--               DESCRIPTION
--                   "Controls whether the queue 2 policer is enabled on this switch port.
--                    default: 500(Kbps)"
--               ::= {     sm48tat4xarpQosQueuePolicingEntry 10 }
--
--    sm48tat4xarpQosQueuePolicingQueue2Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sm48tat4xarpQosQueuePolicingEntry 11 }
--
--    sm48tat4xarpQosQueuePolicingQueue3Enable OBJECT-TYPE
--               SYNTAX      AdminMode
--               MAX-ACCESS  read-write
--               STATUS      current
--               DESCRIPTION
--                   "Controls whether the queue 3 policer is enabled on this switch port."
--               DEFVAL  { disable }
--               ::= {     sm48tat4xarpQosQueuePolicingEntry 12 }
--
--    sm48tat4xarpQosQueuePolicingQueue3Rate OBJECT-TYPE
--               SYNTAX      Integer32
--               MAX-ACCESS  read-write
--               STATUS      current
--               DESCRIPTION
--                   "Controls whether the queue 3 policer is enabled on this switch port.
--                    default: 500(Kbps)"
--               ::= {     sm48tat4xarpQosQueuePolicingEntry 13 }
--
--    sm48tat4xarpQosQueuePolicingQueue3Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sm48tat4xarpQosQueuePolicingEntry 14 }
--
--    sm48tat4xarpQosQueuePolicingQueue4Enable OBJECT-TYPE
--               SYNTAX      AdminMode
--               MAX-ACCESS  read-write
--               STATUS      current
--               DESCRIPTION
--                   "Controls whether the queue 4 policer is enabled on this switch port."
--               DEFVAL  { disable }
--               ::= {     sm48tat4xarpQosQueuePolicingEntry 15 }
--
--    sm48tat4xarpQosQueuePolicingQueue4Rate OBJECT-TYPE
--               SYNTAX      Integer32
--               MAX-ACCESS  read-write
--               STATUS      current
--               DESCRIPTION
--                   "Controls whether the queue 4 policer is enabled on this switch port.
--                    default: 500(Kbps)"
--               ::= {     sm48tat4xarpQosQueuePolicingEntry 16 }
--
--    sm48tat4xarpQosQueuePolicingQueue4Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sm48tat4xarpQosQueuePolicingEntry 17 }
--
--    sm48tat4xarpQosQueuePolicingQueue5Enable OBJECT-TYPE
--               SYNTAX      AdminMode
--               MAX-ACCESS  read-write
--               STATUS      current
--               DESCRIPTION
--                   "Controls whether the queue 5 policer is enabled on this switch port."
--               DEFVAL  { disable }
--               ::= {     sm48tat4xarpQosQueuePolicingEntry 18 }
--
--    sm48tat4xarpQosQueuePolicingQueue5Rate OBJECT-TYPE
--               SYNTAX      Integer32
--               MAX-ACCESS  read-write
--               STATUS      current
--               DESCRIPTION
--                   "Controls whether the queue 5 policer is enabled on this switch port.
--                    default: 500(Kbps)"
--               ::= {     sm48tat4xarpQosQueuePolicingEntry 19 }
--
--    sm48tat4xarpQosQueuePolicingQueue5Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sm48tat4xarpQosQueuePolicingEntry 20 }
--
--    sm48tat4xarpQosQueuePolicingQueue6Enable OBJECT-TYPE
--               SYNTAX      AdminMode
--               MAX-ACCESS  read-write
--               STATUS      current
--               DESCRIPTION
--                   "Controls whether the queue 6 policer is enabled on this switch port."
--               DEFVAL  { disable }
--               ::= {     sm48tat4xarpQosQueuePolicingEntry 21 }
--
--    sm48tat4xarpQosQueuePolicingQueue6Rate OBJECT-TYPE
--               SYNTAX      Integer32
--               MAX-ACCESS  read-write
--               STATUS      current
--               DESCRIPTION
--                   "Controls whether the queue 6 policer is enabled on this switch port.
--                    default: 500(Kbps)"
--               ::= {     sm48tat4xarpQosQueuePolicingEntry 22 }
--
--    sm48tat4xarpQosQueuePolicingQueue6Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sm48tat4xarpQosQueuePolicingEntry 23 }
--
--    sm48tat4xarpQosQueuePolicingQueue7Enable OBJECT-TYPE
--               SYNTAX      AdminMode
--               MAX-ACCESS  read-write
--               STATUS      current
--               DESCRIPTION
--                   "Controls whether the queue 7 policer is enabled on this switch port."
--               DEFVAL  { disable }
--               ::= {     sm48tat4xarpQosQueuePolicingEntry 24 }
--
--    sm48tat4xarpQosQueuePolicingQueue7Rate OBJECT-TYPE
--               SYNTAX      Integer32
--               MAX-ACCESS  read-write
--               STATUS      current
--               DESCRIPTION
--                   "Controls whether the queue 7 policer is enabled on this switch port.
--                    default: 500(Kbps)"
--               ::= {     sm48tat4xarpQosQueuePolicingEntry 25 }
--
--    sm48tat4xarpQosQueuePolicingQueue7Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sm48tat4xarpQosQueuePolicingEntry 26 }
--
--
-- =======================================================================================================================
-- Start sm48tat4xarpQosPortScheduler group
-- =======================================================================================================================
--sm48tat4xarpQosPortSchedulerModeTable

--     sm48tat4xarpQosPortSchedulerModeTable OBJECT-TYPE
--               SYNTAX      SEQUENCE OF     SM48TAT4XARPQosPortSchedulerModeEntry
--               MAX-ACCESS  not-accessible
--               STATUS      current
--               DESCRIPTION
--                   "The basic QoS Port Scheduler Mode settings.
--                    INDEX for this table is ifIndex which is
--                    equivalent to the panel port number."
--               ::= {     sm48tat4xarpQosPortScheduler  1 }
--
--    sm48tat4xarpQosPortSchedulerModeEntry OBJECT-TYPE
--               SYNTAX          SM48TAT4XARPQosPortSchedulerModeEntry
--               MAX-ACCESS  not-accessible
--               STATUS      current
--               DESCRIPTION
--                   "The Qos Port Scheduler Mode entry."
--               INDEX    {     ifIndex  }
--               ::= {     sm48tat4xarpQosPortSchedulerModeTable 1 }
--
--    SM48TAT4XARPQosPortSchedulerModeEntry             ::= SEQUENCE {
--                sm48tat4xarpQosSchedulerMode            Integer32,
--                sm48tat4xarpQosSchedulerShaper          AdminMode,
--                sm48tat4xarpQosSchedulerShaperRate      Integer32
--                }
--
--    sm48tat4xarpQosSchedulerMode OBJECT-TYPE
--               SYNTAX      Integer32
--               MAX-ACCESS  read-write
--               STATUS      current
--               DESCRIPTION
--                   "Controls whether the scheduler mode is Strict Priority or Weighted
--                    on this switch port.
--                    0:Strict Priority,
--		    2: 2 Queues Weighted
--		    3: 3 Queues Weighted: only Jaguar2 support
--		    4: 4 Queues Weighted: only Jaguar2 support
--		    5: 5 Queues Weighted: only Jaguar2 support
--                    6: 6 Queues Weighted
--		    7: 7 Queues Weighted: only Jaguar2 support
--		    8: 8 Queues Weighted: only Jaguar2 support"
--               ::= {     sm48tat4xarpQosPortSchedulerModeEntry 2 }
--
--    sm48tat4xarpQosSchedulerShaper OBJECT-TYPE
--               SYNTAX      AdminMode
--               MAX-ACCESS  read-write
--               STATUS      current
--               DESCRIPTION
--                   "Controls whether the port shaper is enabled."
--               DEFVAL  { disable }
--               ::= {     sm48tat4xarpQosPortSchedulerModeEntry 3 }
--
--    sm48tat4xarpQosSchedulerShaperRate OBJECT-TYPE
--               SYNTAX      Integer32
--               MAX-ACCESS  read-write
--               STATUS      current
--               DESCRIPTION
--                   "Controls the rate for the port shaper.
--                    default: 500 kbps."
--               ::= {     sm48tat4xarpQosPortSchedulerModeEntry 4 }
--
--sm48tat4xarpQosPortSchedulerTable
--    sm48tat4xarpQosPortSchedulerTable OBJECT-TYPE
--               SYNTAX      SEQUENCE OF     SM48TAT4XARPQosPortSchedulerEntry
--               MAX-ACCESS  not-accessible
--               STATUS      current
--               DESCRIPTION
--                   "Show Qos Port Scheduler.
--                    INDEX for this table is ifIndex which is
--                    equivalent to the panel port number."
--               ::= {     sm48tat4xarpQosPortScheduler 2 }
--
--    sm48tat4xarpQosPortSchedulerEntry OBJECT-TYPE
--               SYNTAX          SM48TAT4XARPQosPortSchedulerEntry
--               MAX-ACCESS  not-accessible
--               STATUS      current
--               DESCRIPTION
--                   "The Qos Port Scheduler Entry."
--               INDEX    {     ifIndex,
--                              sm48tat4xarpQosSchedulerPortQueue}
--               ::= {     sm48tat4xarpQosPortSchedulerTable 1 }
--
--    SM48TAT4XARPQosPortSchedulerEntry             ::= SEQUENCE {
--                sm48tat4xarpQosSchedulerPortQueue                  INTEGER,
--                sm48tat4xarpQosSchedulerPortQueueShaper            AdminMode,
--                sm48tat4xarpQosSchedulerPortQueueShaperRate        Integer32,
--                sm48tat4xarpQosSchedulerPortQueueShaperExcess      AdminMode,
--                sm48tat4xarpQosSchedulerPortQueueSchedulerWeight   Integer32,
--                sm48tat4xarpQosSchedulerPortQueueSchedulerPercent  DisplayString
--                }
--
--    sm48tat4xarpQosSchedulerPortQueue OBJECT-TYPE
--               SYNTAX      INTEGER { q0(1),
--                                     q1(2),
--                                     q2(3),
--                                     q3(4),
--                                     q4(5),
--                                     q5(6),
--                                     q6(7),
--                                     q7(8) }
--               MAX-ACCESS  not-accessible
--               STATUS      current
--               DESCRIPTION
--                   "range: 1-8.
--                    Q0: 1, Q1: 2, ..."
--               ::= {     sm48tat4xarpQosPortSchedulerEntry 2 }
--
--    sm48tat4xarpQosSchedulerPortQueueShaper OBJECT-TYPE
--               SYNTAX     AdminMode
--               MAX-ACCESS  read-write
--               STATUS      current
--               DESCRIPTION
--                   "Qos scheduler admin state."
--               DEFVAL  { disable }
--               ::= {     sm48tat4xarpQosPortSchedulerEntry 3 }
--
--    sm48tat4xarpQosSchedulerPortQueueShaperRate OBJECT-TYPE
--               SYNTAX      Integer32(100..1000000)
--               MAX-ACCESS  read-write
--               STATUS      current
--               DESCRIPTION
--                   "range: 100..1000000 kbps. "
--               ::= {     sm48tat4xarpQosPortSchedulerEntry 4 }
--
--    sm48tat4xarpQosSchedulerPortQueueShaperExcess OBJECT-TYPE
--               SYNTAX      AdminMode
--               MAX-ACCESS  read-write
--               STATUS      current
--               DESCRIPTION
--                   "admin state sm48tat4xarpQosSchedulerPortQueueShaperExcess"
--               DEFVAL  { disable }
--               ::= {     sm48tat4xarpQosPortSchedulerEntry 5 }
--
--    sm48tat4xarpQosSchedulerPortQueueSchedulerWeight OBJECT-TYPE
--               SYNTAX      Integer32(0..100)
--               MAX-ACCESS  read-write
--               STATUS      current
--               DESCRIPTION
--                   "range: 1-100,
--                    default: 17.
--                    Only use in Q0 - Q5.  Q6 & Q7 show 0"
--               ::= {     sm48tat4xarpQosPortSchedulerEntry 6 }
--
--    sm48tat4xarpQosSchedulerPortQueueSchedulerPercent OBJECT-TYPE
--               SYNTAX      DisplayString
--               MAX-ACCESS  read-only
--               STATUS      current
--               DESCRIPTION
--                   "Only use in Q0 - Q5. Q6 & Q7 show empty"
--               ::= {     sm48tat4xarpQosPortSchedulerEntry 7 }
--
-- =======================================================================================================================
-- Start sm48tat4xarpQosEgressPortPCPRemarking group
-- =======================================================================================================================
--sm48tat4xarpQosEgressPortPCPRemarkingTable
    sm48tat4xarpQosEgressPortPCPRemarkingTable OBJECT-TYPE
               SYNTAX      SEQUENCE OF     SM48TAT4XARPQosEgressPortPCPRemarkingEntry
               MAX-ACCESS  not-accessible
               STATUS      current
               DESCRIPTION
                   "The basic Qos Egress Port PCP Remarking
                    Configuration settings.
                    INDEX for this table is ifIndex which is
                    equivalent to the panel port number."
               ::= {     sm48tat4xarpQosEgressPortPCPRemarking  1 }

    sm48tat4xarpQosEgressPortPCPRemarkingEntry OBJECT-TYPE
               SYNTAX          SM48TAT4XARPQosEgressPortPCPRemarkingEntry
               MAX-ACCESS  not-accessible
               STATUS      current
               DESCRIPTION
                   "The Qos Egress Port PCP Remarking Entry."
               INDEX    {     ifIndex  }
               ::= {     sm48tat4xarpQosEgressPortPCPRemarkingTable 1 }

    SM48TAT4XARPQosEgressPortPCPRemarkingEntry             ::= SEQUENCE {
                sm48tat4xarpQosEgressPortPCPRemarkingMode                    INTEGER
                }

    sm48tat4xarpQosEgressPortPCPRemarkingMode OBJECT-TYPE
               SYNTAX      INTEGER { keep(0), specific(1), mapped(2) }
               MAX-ACCESS  read-write
               STATUS      current
               DESCRIPTION
                   "the tag remarking mode for this port.
                    0:Keep, Use classified PCP/DEI values.
                    1:Specific, Use default PCP/DEI values.
                    2:Mapped, Use mapped versions of QoS class and DP level."
               ::= {     sm48tat4xarpQosEgressPortPCPRemarkingEntry 2 }

--sm48tat4xarpQosEgressPortPCPRemarkingSpecificTable
    sm48tat4xarpQosEgressPortPCPRemarkingSpecificTable OBJECT-TYPE
               SYNTAX      SEQUENCE OF     SM48TAT4XARPQosEgressPortPCPRemarkingSpecificEntry
               MAX-ACCESS  not-accessible
               STATUS      current
               DESCRIPTION
                   "The basic Qos Egress Port PCP Remarking Specific
                    Configuration settings.
                    INDEX for this table is ifIndex which is
                    equivalent to the panel port number."
               ::= {     sm48tat4xarpQosEgressPortPCPRemarking  2 }

    sm48tat4xarpQosEgressPortPCPRemarkingSpecificEntry OBJECT-TYPE
               SYNTAX          SM48TAT4XARPQosEgressPortPCPRemarkingSpecificEntry
               MAX-ACCESS  not-accessible
               STATUS      current
               DESCRIPTION
                   "The Qos Egress Port PCP Remarking Specific Entry."
               INDEX    {     ifIndex  }
               ::= {     sm48tat4xarpQosEgressPortPCPRemarkingSpecificTable 1 }

    SM48TAT4XARPQosEgressPortPCPRemarkingSpecificEntry             ::= SEQUENCE {
                sm48tat4xarpQosEgressPortPCPRemarkingSpecificPCP                Integer32,
                sm48tat4xarpQosEgressPortPCPRemarkingSpecificDEI                AdminMode
                }

    sm48tat4xarpQosEgressPortPCPRemarkingSpecificPCP OBJECT-TYPE
               SYNTAX      Integer32(0..7)
               MAX-ACCESS  read-write
               STATUS      current
               DESCRIPTION
                   "Controls the specific PCP
                    Range : 0-7"
               ::= {     sm48tat4xarpQosEgressPortPCPRemarkingSpecificEntry 2 }

    sm48tat4xarpQosEgressPortPCPRemarkingSpecificDEI OBJECT-TYPE
               SYNTAX      AdminMode
               MAX-ACCESS  read-write
               STATUS      current
               DESCRIPTION
                   "controls the admin state of DEI"
               ::= {     sm48tat4xarpQosEgressPortPCPRemarkingSpecificEntry 3 }

--sm48tat4xarpQosPortEgressTagRemarkingMapDPTable
--    sm48tat4xarpQosPortEgressTagRemarkingMapDPTable OBJECT-TYPE
--               SYNTAX      SEQUENCE OF     SM48TAT4XARPQosPortEgressTagRemarkingMapDPEntry
--               MAX-ACCESS  not-accessible
--               STATUS      current
--               DESCRIPTION
--                   "Show Qos Port Egress Tag Remarking Map DP.
--                    INDEX for this table is ifIndex which is
--                    equivalent to the panel port number."
--               ::= {     sm48tat4xarpQosPortEgressTagRemarking 3 }

--    sm48tat4xarpQosPortEgressTagRemarkingMapDPEntry OBJECT-TYPE
--               SYNTAX          SM48TAT4XARPQosPortEgressTagRemarkingMapDPEntry
--               MAX-ACCESS  not-accessible
--               STATUS      current
--               DESCRIPTION
--                   "The Qos Port Egress Tag Remarking Map DP Entry."
--               INDEX    {     ifIndex,
--                              sm48tat4xarpQosPortEgressTagRemarkingClassifiedDPLevel}
--               ::= {     sm48tat4xarpQosPortEgressTagRemarkingMapDPTable 1 }

--    SM48TAT4XARPQosPortEgressTagRemarkingMapDPEntry             ::= SEQUENCE {
--                sm48tat4xarpQosPortEgressTagRemarkingClassifiedDPLevel      Integer32,
--                sm48tat4xarpQosPortEgressTagRemarkingDPLevel                AdminMode
--                }

--    sm48tat4xarpQosPortEgressTagRemarkingClassifiedDPLevel OBJECT-TYPE
--               SYNTAX      Integer32(1..4)
--               MAX-ACCESS  not-accessible
--               STATUS      current
--               DESCRIPTION
--                   "range: 1-4."
--               ::= {     sm48tat4xarpQosPortEgressTagRemarkingMapDPEntry 2 }

--    sm48tat4xarpQosPortEgressTagRemarkingDPLevel OBJECT-TYPE
--               SYNTAX      AdminMode
--               MAX-ACCESS  read-write
--               STATUS      current
--               DESCRIPTION
--                   "admin state of Tag remark"
--               ::= {     sm48tat4xarpQosPortEgressTagRemarkingMapDPEntry 3 }

--sm48tat4xarpQosEgressPortPCPRemarkingMappedTable
    sm48tat4xarpQosEgressPortPCPRemarkingMappedTable OBJECT-TYPE
               SYNTAX      SEQUENCE OF     SM48TAT4XARPQosEgressPortPCPRemarkingMappedEntry
               MAX-ACCESS  not-accessible
               STATUS      current
               DESCRIPTION
                   "Show Qos Egress Port PCP Remarking Mapped.
                    INDEX for this table is ifIndex which is
                    equivalent to the panel port number."
               ::= {     sm48tat4xarpQosEgressPortPCPRemarking 4 }

    sm48tat4xarpQosEgressPortPCPRemarkingMappedEntry OBJECT-TYPE
               SYNTAX          SM48TAT4XARPQosEgressPortPCPRemarkingMappedEntry
               MAX-ACCESS  not-accessible
               STATUS      current
               DESCRIPTION
                   "The Qos Egress Port PCP Remarking Mapped Entry."
               INDEX    {     ifIndex,
                              sm48tat4xarpQosEgressPortPCPRemarkingMappedQueuePriority,
                              sm48tat4xarpQosEgressPortPCPRemarkingMappedDPLevel  }
               ::= {     sm48tat4xarpQosEgressPortPCPRemarkingMappedTable 1 }

    SM48TAT4XARPQosEgressPortPCPRemarkingMappedEntry             ::= SEQUENCE {
                sm48tat4xarpQosEgressPortPCPRemarkingMappedQueuePriority          INTEGER,
                sm48tat4xarpQosEgressPortPCPRemarkingMappedDPLevel                INTEGER,
                sm48tat4xarpQosEgressPortPCPRemarkingMappedPCP                    Integer32,
                sm48tat4xarpQosEgressPortPCPRemarkingMappedDEI                    Integer32
                }

    sm48tat4xarpQosEgressPortPCPRemarkingMappedQueuePriority OBJECT-TYPE
               SYNTAX      INTEGER {
                        class0(1),
                        class1(2),
                        class2(3),
                        class3(4),
                        class4(5),
                        class5(6),
                        class6(7),
                        class7(8)
                        }
               MAX-ACCESS  not-accessible
               STATUS      current
               DESCRIPTION
                   "range: 1-8,
                    QoS Class0: 1, QoS Class1: 2..."
               ::= {     sm48tat4xarpQosEgressPortPCPRemarkingMappedEntry 2 }

    sm48tat4xarpQosEgressPortPCPRemarkingMappedDPLevel OBJECT-TYPE
               SYNTAX      INTEGER { level0(1), level1(2) }
               MAX-ACCESS  not-accessible
               STATUS      current
               DESCRIPTION
                   "range: 1-2,
                    DP Level0: 1, DP Level1: 2."
               ::= {     sm48tat4xarpQosEgressPortPCPRemarkingMappedEntry 3 }

    sm48tat4xarpQosEgressPortPCPRemarkingMappedPCP OBJECT-TYPE
               SYNTAX      Integer32(0..7)
               MAX-ACCESS  read-write
               STATUS      current
               DESCRIPTION
                   "range: 0-7."
               ::= {     sm48tat4xarpQosEgressPortPCPRemarkingMappedEntry 4 }

    sm48tat4xarpQosEgressPortPCPRemarkingMappedDEI OBJECT-TYPE
               SYNTAX      Integer32 (0|1)
               MAX-ACCESS  read-write
               STATUS      current
               DESCRIPTION
                   "range: 0-1."
               ::= {     sm48tat4xarpQosEgressPortPCPRemarkingMappedEntry 5 }

--
-- =======================================================================================================================
-- Start sm48tat4xarpQosPortDSCP group
-- =======================================================================================================================
--sm48tat4xarpQosPortDSCPTable
    sm48tat4xarpQosPortDSCPTable OBJECT-TYPE
               SYNTAX      SEQUENCE OF     SM48TAT4XARPQosPortDSCPEntry
               MAX-ACCESS  not-accessible
               STATUS      current
               DESCRIPTION
                   "The basic QoS Port DSCP Configuration settings.
                    INDEX for this table is ifIndex which is
                    equivalent to the panel port number."
               ::= {     sm48tat4xarpQosPortDSCP 1 }

    sm48tat4xarpQosPortDSCPEntry OBJECT-TYPE
               SYNTAX          SM48TAT4XARPQosPortDSCPEntry
               MAX-ACCESS  not-accessible
               STATUS      current
               DESCRIPTION
                   "The Qos Port DSCP Entry."
               INDEX    {     ifIndex  }
               ::= {     sm48tat4xarpQosPortDSCPTable 1 }

    SM48TAT4XARPQosPortDSCPEntry             ::= SEQUENCE {
                sm48tat4xarpQosPortDSCPIngressTranslate        AdminMode,
                sm48tat4xarpQosPortDSCPIngressClassify         INTEGER,
                sm48tat4xarpQosPortDSCPEgressRewrite           INTEGER
                }

    sm48tat4xarpQosPortDSCPIngressTranslate OBJECT-TYPE
               SYNTAX      AdminMode
               MAX-ACCESS  read-write
               STATUS      current
               DESCRIPTION
                  "Configure DSCP ingress translation mode."
               DEFVAL  { disable }
               ::= {     sm48tat4xarpQosPortDSCPEntry 2 }

    sm48tat4xarpQosPortDSCPIngressClassify OBJECT-TYPE
               SYNTAX      INTEGER { disable (0), dscp (1), selected (2), all(3) }
               MAX-ACCESS  read-write
               STATUS      current
               DESCRIPTION
                   "Classification for a port have 4 different values.
                    0: disable,
                    1: DSCP=0,
                    2: Selected,
                    3: All."
               DEFVAL  { disable }
               ::= {     sm48tat4xarpQosPortDSCPEntry 3 }

    sm48tat4xarpQosPortDSCPEgressRewrite OBJECT-TYPE
               SYNTAX      INTEGER { disable (0),enable (1),
                                     remap (2) }
               MAX-ACCESS  read-write
               STATUS      current
               DESCRIPTION
                   "Configure the port egress rewriting mode.
                    0: Disable,1: Enable,2: Remap,range: 0-2"
               ::= {     sm48tat4xarpQosPortDSCPEntry 4 }

--
-- =======================================================================================================================
-- Start sm48tat4xarpQosDSCPBasedQoS group
-- =======================================================================================================================
    sm48tat4xarpQosDSCPBasedQoSTable OBJECT-TYPE
               SYNTAX      SEQUENCE OF     SM48TAT4XARPQosDSCPBasedQoSEntry
               MAX-ACCESS  not-accessible
               STATUS      current
               DESCRIPTION
                   "configure the basic Qos DSCP-Based QoS Ingress Classification settings for all switches."
               ::= {     sm48tat4xarpQosDSCPBasedQoS 1 }

    sm48tat4xarpQosDSCPBasedQoSEntry OBJECT-TYPE
               SYNTAX          SM48TAT4XARPQosDSCPBasedQoSEntry
               MAX-ACCESS  not-accessible
               STATUS      current
               DESCRIPTION
                   "The Qos DSCP Based QoS Entry."
               INDEX    {     sm48tat4xarpQosDSCPBasedQoSList  }
               ::= {     sm48tat4xarpQosDSCPBasedQoSTable 1 }

    SM48TAT4XARPQosDSCPBasedQoSEntry             ::= SEQUENCE {
                sm48tat4xarpQosDSCPBasedQoSList          Integer32,
                sm48tat4xarpQosDSCPBasedQoSDSCP          DisplayString,
                sm48tat4xarpQosDSCPBasedQoSTrust         AdminMode,
                sm48tat4xarpQosDSCPBasedQoSQueuePriority Integer32,
                sm48tat4xarpQosDSCPBasedQoSDPL           Integer32
                }

    sm48tat4xarpQosDSCPBasedQoSList OBJECT-TYPE
               SYNTAX      Integer32(1..64)
               MAX-ACCESS  not-accessible
               STATUS      current
               DESCRIPTION
                  "DSCP mapping table index(1-64)."
               ::= {     sm48tat4xarpQosDSCPBasedQoSEntry 1 }

    sm48tat4xarpQosDSCPBasedQoSDSCP OBJECT-TYPE
               SYNTAX      DisplayString
               MAX-ACCESS  read-only
               STATUS      current
               DESCRIPTION
                  "Maximum number of supported DSCP values are 64."
               ::= {     sm48tat4xarpQosDSCPBasedQoSEntry 2 }

    sm48tat4xarpQosDSCPBasedQoSTrust OBJECT-TYPE
               SYNTAX      AdminMode
               MAX-ACCESS  read-write
               STATUS      current
               DESCRIPTION
                  "Controls whether a specific DSCP value is trusted. Only frames with
                   trusted DSCP values are mapped to a specific QoS class
                   and Drop Precedence
                   Level. Frames with untrusted DSCP values are
                   treated as a non-IP frame."
               DEFVAL  { disable }
              ::= {     sm48tat4xarpQosDSCPBasedQoSEntry 3 }

    sm48tat4xarpQosDSCPBasedQoSQueuePriority OBJECT-TYPE
               SYNTAX      Integer32(0..7)
               MAX-ACCESS  read-write
               STATUS      current
               DESCRIPTION
                  "QoS class.
                   range: 0-7,
                   default: 0."
               ::= {     sm48tat4xarpQosDSCPBasedQoSEntry 4 }

    sm48tat4xarpQosDSCPBasedQoSDPL OBJECT-TYPE
               SYNTAX      Integer32(0|1)
               MAX-ACCESS  read-write
               STATUS      current
               DESCRIPTION
                  "Drop Precedence Level.
                   range: 0-1,
                   default: 0."
               ::= {     sm48tat4xarpQosDSCPBasedQoSEntry 5 }

--
-- =======================================================================================================================
-- Start sm48tat4xarpQosDSCPTranslation group
-- =======================================================================================================================
--sm48tat4xarpQosDSCPTranslationTable
    sm48tat4xarpQosDSCPTranslationTable OBJECT-TYPE
               SYNTAX      SEQUENCE OF     SM48TAT4XARPQosDSCPTranslationEntry
               MAX-ACCESS  not-accessible
               STATUS      current
               DESCRIPTION
                   "The basic QoS DSCP Translation settings for all switches."
               ::= {     sm48tat4xarpQosDSCPTranslation  1 }

    sm48tat4xarpQosDSCPTranslationEntry OBJECT-TYPE
               SYNTAX          SM48TAT4XARPQosDSCPTranslationEntry
               MAX-ACCESS  not-accessible
               STATUS      current
               DESCRIPTION
                   "The Qos DSCP Translation Entry."
               INDEX    {     sm48tat4xarpQosDSCPTranslationList  }
               ::= {     sm48tat4xarpQosDSCPTranslationTable 1 }

    SM48TAT4XARPQosDSCPTranslationEntry             ::= SEQUENCE {
                sm48tat4xarpQosDSCPTranslationList                 Integer32,
                sm48tat4xarpQosDSCPTranslationDSCPBasedId          DisplayString,
                sm48tat4xarpQosDSCPTranslationIngressTranslate     Integer32,
                sm48tat4xarpQosDSCPTranslationIngressClassify      AdminMode,
                sm48tat4xarpQosDSCPTranslationEgressRemap          Integer32
--              sm48tat4xarpQosDSCPTranslationEgressRemapDP1       Integer32
                }

    sm48tat4xarpQosDSCPTranslationList OBJECT-TYPE
               SYNTAX      Integer32(1..64)
               MAX-ACCESS  not-accessible
               STATUS      current
               DESCRIPTION
                  "DSCP translation table index(1-64)."
               ::= {     sm48tat4xarpQosDSCPTranslationEntry 1 }

    sm48tat4xarpQosDSCPTranslationDSCPBasedId OBJECT-TYPE
               SYNTAX      DisplayString
               MAX-ACCESS  read-only
               STATUS      current
               DESCRIPTION
                  "Configure global ingress DSCP translation table."
               ::= {     sm48tat4xarpQosDSCPTranslationEntry 2 }

    sm48tat4xarpQosDSCPTranslationIngressTranslate OBJECT-TYPE
               SYNTAX      Integer32(0..63)
               MAX-ACCESS  read-write
               STATUS      current
               DESCRIPTION
                  "DSCP at Ingress side can be translated to any of DSCP values.
                   range: 0-63,
                   default: 0."
               ::= {     sm48tat4xarpQosDSCPTranslationEntry 3 }

    sm48tat4xarpQosDSCPTranslationIngressClassify OBJECT-TYPE
               SYNTAX      AdminMode
               MAX-ACCESS  read-write
               STATUS      current
               DESCRIPTION
                  "Configure DSCP ingress classification."
               DEFVAL  { disable }
               ::= {     sm48tat4xarpQosDSCPTranslationEntry 4 }

    sm48tat4xarpQosDSCPTranslationEgressRemap OBJECT-TYPE
               SYNTAX      Integer32(0..63)
               MAX-ACCESS  read-write
               STATUS      current
               DESCRIPTION
                  "Select the DSCP value from select menu to which you want to remap.
                   range: 0-63,
                   default: 0."
               ::= {     sm48tat4xarpQosDSCPTranslationEntry 5 }

--    sm48tat4xarpQosDSCPTranslationEgressRemapDP1 OBJECT-TYPE
--               SYNTAX      Integer32(0..63)
--               MAX-ACCESS  read-write
--               STATUS      current
--               DESCRIPTION
--                  "Select the DSCP value from select menu to which you want to remap.
--                   range: 0-63,
--                   default: 0.
--                   Only support LUTON26."
--               ::= {     sm48tat4xarpQosDSCPTranslationEntry 6 }

--
-- =======================================================================================================================
-- Start sm48tat4xarpQosDSCPClassification group
-- =======================================================================================================================
--sm48tat4xarpQosDSCPClassificationTable
    sm48tat4xarpQosDSCPClassificationTable OBJECT-TYPE
               SYNTAX      SEQUENCE OF     SM48TAT4XARPQosDSCPClassificationEntry
               MAX-ACCESS  not-accessible
               STATUS      current
               DESCRIPTION
                   "The mapping of QoS class  to DSCP value."
               ::= {     sm48tat4xarpQosDSCPClassification 1 }

    sm48tat4xarpQosDSCPClassificationEntry OBJECT-TYPE
               SYNTAX          SM48TAT4XARPQosDSCPClassificationEntry
               MAX-ACCESS  not-accessible
               STATUS      current
               DESCRIPTION
                   "The Qos DSCP Classification Entry."
               INDEX    {     sm48tat4xarpQosDSCPClassificationQoSClass  }
               ::= {     sm48tat4xarpQosDSCPClassificationTable 1 }

    SM48TAT4XARPQosDSCPClassificationEntry             ::= SEQUENCE {
                sm48tat4xarpQosDSCPClassificationQoSClass   Integer32,
                sm48tat4xarpQosDSCPClassificationDSCPDP0    Integer32,
		sm48tat4xarpQosDSCPClassificationDSCPDP1    Integer32,
		sm48tat4xarpQosDSCPClassificationDSCPDP2    Integer32,
		sm48tat4xarpQosDSCPClassificationDSCPDP3    Integer32
                }

    sm48tat4xarpQosDSCPClassificationQoSClass OBJECT-TYPE
               SYNTAX      Integer32(1..8)
               MAX-ACCESS  not-accessible
               STATUS      current
               DESCRIPTION
                  "This page allows you to configure the mapping of QoS class
                   and Drop Precedence Level to DSCP value.
                   range: 1-8}"
               ::= {     sm48tat4xarpQosDSCPClassificationEntry 1 }

    sm48tat4xarpQosDSCPClassificationDSCPDP0 OBJECT-TYPE
               SYNTAX      Integer32(0..63)
               MAX-ACCESS  read-write
               STATUS      current
               DESCRIPTION
                  "Select the classified DSCP value.
                   range: 0-63,
                   default: 0."
               ::= {     sm48tat4xarpQosDSCPClassificationEntry 2 }

    sm48tat4xarpQosDSCPClassificationDSCPDP1 OBJECT-TYPE
               SYNTAX      Integer32(0..63)
               MAX-ACCESS  read-write
               STATUS      current
               DESCRIPTION
                  "Select the classified DSCP value.
                   range: 0-63,
                   default: 0."
               ::= {     sm48tat4xarpQosDSCPClassificationEntry 3 }

    sm48tat4xarpQosDSCPClassificationDSCPDP2 OBJECT-TYPE
               SYNTAX      Integer32(0..63)
               MAX-ACCESS  read-write
               STATUS      current
               DESCRIPTION
                  "Select the classified DSCP value.
                   range: 0-63,
                   default: 0."
               ::= {     sm48tat4xarpQosDSCPClassificationEntry 4 }

    sm48tat4xarpQosDSCPClassificationDSCPDP3 OBJECT-TYPE
               SYNTAX      Integer32(0..63)
               MAX-ACCESS  read-write
               STATUS      current
               DESCRIPTION
                  "Select the classified DSCP value.
                   range: 0-63,
                   default: 0."
               ::= {     sm48tat4xarpQosDSCPClassificationEntry 5 }

--
-- =======================================================================================================================
-- Start sm48tat4xarpQosControlList group
-- =======================================================================================================================
--sm48tat4xarpQosQceTable

    sm48tat4xarpQosQceTable OBJECT-TYPE
               SYNTAX      SEQUENCE OF     SM48TAT4XARPQosQceEntry
               MAX-ACCESS  not-accessible
               STATUS      current
               DESCRIPTION
                   "Create Qos QCE entry."
               ::= {     sm48tat4xarpQosControlList 1 }

    sm48tat4xarpQosQceEntry OBJECT-TYPE
               SYNTAX          SM48TAT4XARPQosQceEntry
               MAX-ACCESS  not-accessible
               STATUS      current
               DESCRIPTION
                   "Qos Qce Entry."
               INDEX    {     sm48tat4xarpQosQceIndex  }
               ::= {     sm48tat4xarpQosQceTable 1 }

    SM48TAT4XARPQosQceEntry             ::= SEQUENCE {
                sm48tat4xarpQosQceIndex                Integer32,
                sm48tat4xarpQosQceID                   Integer32,
                sm48tat4xarpQosQceList                 Integer32,
--              sm48tat4xarpQosQcePortMembersSwitch    Integer32,
                sm48tat4xarpQosQcePortMembers          DisplayString,
                sm48tat4xarpQosQceTag                  DisplayString,
                sm48tat4xarpQosQceVID                  DisplayString,
                sm48tat4xarpQosPCP                     DisplayString,
                sm48tat4xarpQosDEI                     DisplayString,
                sm48tat4xarpQosSMAC                    DisplayString,
                sm48tat4xarpQosDMACType                DisplayString,
                sm48tat4xarpQosDMACValue               DisplayString,
                sm48tat4xarpQosQceInnerTag             DisplayString,
                sm48tat4xarpQosQceInnerVID             DisplayString,
                sm48tat4xarpQosInnerPCP                DisplayString,
                sm48tat4xarpQosInnerDEI                DisplayString,
                sm48tat4xarpQosFrameType               INTEGER,
                sm48tat4xarpQosMacEtherType            DisplayString,
                sm48tat4xarpQosLLCSSAPAddr             DisplayString,
                sm48tat4xarpQosLLCDSAPAddr             DisplayString,
                sm48tat4xarpQosLLCControl              DisplayString,
                sm48tat4xarpQosSNAPPID                 DisplayString,
                sm48tat4xarpQosIpv4Protocol            DisplayString,
                sm48tat4xarpQosIpv4ProtocolValue       Integer32,
                sm48tat4xarpQosIpv4ProtocolUDPSPort    DisplayString,
                sm48tat4xarpQosIpv4ProtocolUDPDPort    DisplayString,
                sm48tat4xarpQosIpv4ProtocolTCPSPort    DisplayString,
                sm48tat4xarpQosIpv4ProtocolTCPDPort    DisplayString,
                sm48tat4xarpQosIpv4SourceIp            DisplayString,
                sm48tat4xarpQosIpv4SourceMask          DisplayString,
                sm48tat4xarpQosIpv4DestIp              DisplayString,
                sm48tat4xarpQosIpv4DestMask            DisplayString,
                sm48tat4xarpQosIpv4IPFragment          INTEGER,
                sm48tat4xarpQosIpv4DSCP                DisplayString,
                sm48tat4xarpQosIpv6Protocol            DisplayString,
                sm48tat4xarpQosIpv6ProtocolValue       Integer32,
                sm48tat4xarpQosIpv6ProtocolUDPSPort    DisplayString,
                sm48tat4xarpQosIpv6ProtocolUDPDPort    DisplayString,
                sm48tat4xarpQosIpv6ProtocolTCPSPort    DisplayString,
                sm48tat4xarpQosIpv6ProtocolTCPDPort    DisplayString,
                sm48tat4xarpQosIpv6SourceIp            DisplayString,
                sm48tat4xarpQosIpv6SourceMask          DisplayString,
                sm48tat4xarpQosIpv6DestIp              DisplayString,
                sm48tat4xarpQosIpv6DestMask            DisplayString,
                sm48tat4xarpQosIpv6DSCP                DisplayString,
                sm48tat4xarpQosActionQueuePriority     Integer32,
                sm48tat4xarpQosActionDPL               Integer32,
                sm48tat4xarpQosActionDSCP              Integer32,
                sm48tat4xarpQosActionPCP               Integer32,
                sm48tat4xarpQosActionDEI               Integer32,
                sm48tat4xarpQosActionPolicy            Integer32,
                sm48tat4xarpQosActionIngressMapID      Integer32,
                sm48tat4xarpQosQceRowStatus            RowStatus
                }

    sm48tat4xarpQosQceIndex OBJECT-TYPE
               SYNTAX      Integer32(1..256)
               MAX-ACCESS  not-accessible
               STATUS      current
               DESCRIPTION
                   "the index to this table."
               ::= {     sm48tat4xarpQosQceEntry 1 }

    sm48tat4xarpQosQceID OBJECT-TYPE
               SYNTAX      Integer32(1..256)
               MAX-ACCESS  read-only
               STATUS      current
               DESCRIPTION
                   "If the QCE ID is specified and an entry with this QCE ID
                    already exists, the QCE will be modified. Otherwise, a
                    new QCE will be added.
                    range : 1 - 256."
               ::= {     sm48tat4xarpQosQceEntry 2 }

    sm48tat4xarpQosQceList OBJECT-TYPE
               SYNTAX      Integer32(0..256)
               MAX-ACCESS  read-create
               STATUS      current
               DESCRIPTION
                   "If the QCE List is non zero, the QCE will be placed in the list.
                    If the QCE List is zero, the QCE will be placed last in the list.
                    range : 0 - 256."
               ::= {     sm48tat4xarpQosQceEntry 3 }

--    sm48tat4xarpQosQcePortMembersSwitch OBJECT-TYPE
--               SYNTAX      Integer32
--               MAX-ACCESS  read-create
--               STATUS      current
--               DESCRIPTION
--                   "Switch number for port members.
--                   -1:Any.
--                   Only support stacking switch."
--               ::= {     sm48tat4xarpQosQceEntry 4 }

    sm48tat4xarpQosQcePortMembers OBJECT-TYPE
               SYNTAX      DisplayString
               MAX-ACCESS  read-create
               STATUS      current
               DESCRIPTION
                   "Indicates the ingress port of the QCE. Possible values are:
                    All: The QCE will match all ingress port.
                    Port: The QCE will match a specific ingress port.Format: 1,3-6."
               ::= {     sm48tat4xarpQosQceEntry 5 }

    sm48tat4xarpQosQceTag OBJECT-TYPE
               SYNTAX      DisplayString
               MAX-ACCESS  read-create
               STATUS      current
               DESCRIPTION
                  "'Any', 'Untagged' or 'Tagged' or 'C-Tag' or 'S-Tag'"
               ::= {     sm48tat4xarpQosQceEntry 6 }

    sm48tat4xarpQosQceVID OBJECT-TYPE
               SYNTAX      DisplayString
               MAX-ACCESS  read-create
               STATUS      current
               DESCRIPTION
                   "Valid value of VLAN ID can be any value in
                   'Specific 1~4095' or 'range 1-4095' or 'Any'."
               ::= {     sm48tat4xarpQosQceEntry 7 }

    sm48tat4xarpQosPCP OBJECT-TYPE
               SYNTAX      DisplayString
               MAX-ACCESS  read-create
               STATUS      current
               DESCRIPTION
                   "Priority Code Point: Valid value PCP are
                    specific(0, 1, 2, 3, 4, 5, 6, 7)
                    or range(0-1, 2-3, 4-5, 6-7, 0-3, 4-7) or 'Any'."
               ::= {     sm48tat4xarpQosQceEntry 8 }

    sm48tat4xarpQosDEI OBJECT-TYPE
               SYNTAX      DisplayString
               MAX-ACCESS  read-create
               STATUS      current
               DESCRIPTION
                   "Drop Eligible Indicator: Valid value of DEI can be
                    any of values between 0, 1 or 'Any'."
               ::= {     sm48tat4xarpQosQceEntry 9 }

    sm48tat4xarpQosSMAC  OBJECT-TYPE
               SYNTAX      DisplayString
               MAX-ACCESS  read-create
               STATUS      current
               DESCRIPTION
                   "Source MAC address: xx-xx-xx-xx-xx-xx or 'Any'."
               ::= {     sm48tat4xarpQosQceEntry 10 }

    sm48tat4xarpQosDMACType OBJECT-TYPE
               SYNTAX      DisplayString
               MAX-ACCESS  read-create
               STATUS      current
               DESCRIPTION
                   "Destination MAC type: possible values are 'UC'(unicast),
                    'MC'(multicast), 'BC'(broadcast), 'SP'(Specific) or 'Any'."
               ::= {     sm48tat4xarpQosQceEntry 11 }

    sm48tat4xarpQosDMACValue OBJECT-TYPE
               SYNTAX      DisplayString
               MAX-ACCESS  read-create
               STATUS      current
               DESCRIPTION
                   "when QosDMACType is 'SP'(specific) can set mac address.
                   "
               ::= {     sm48tat4xarpQosQceEntry 12 }

    sm48tat4xarpQosQceInnerTag OBJECT-TYPE
               SYNTAX      DisplayString
               MAX-ACCESS  read-create
               STATUS      current
               DESCRIPTION
                   "Value of Inner Tag field can be 'Any', 'Untagged' or 'Tagged' or
                    'C-tagged' or 'S-tagged'."
               ::= {     sm48tat4xarpQosQceEntry 13 }

    sm48tat4xarpQosQceInnerVID OBJECT-TYPE
               SYNTAX      DisplayString
               MAX-ACCESS  read-create
               STATUS      current
               DESCRIPTION
                   "Valid value of Inner VLAN ID can be any value in
                    'Specific 1~4095' or 'range 1-4095' or 'Any'.
                    "
               ::= {     sm48tat4xarpQosQceEntry 14 }

    sm48tat4xarpQosInnerPCP OBJECT-TYPE
               SYNTAX      DisplayString
               MAX-ACCESS  read-create
               STATUS      current
               DESCRIPTION
                   "Valid value Inner PCP are specific(0, 1, 2, 3, 4, 5, 6, 7)
                    or range(0-1, 2-3, 4-5, 6-7, 0-3, 4-7) or 'Any'.
                   "
               ::= {     sm48tat4xarpQosQceEntry 15 }

    sm48tat4xarpQosInnerDEI OBJECT-TYPE
               SYNTAX      DisplayString
               MAX-ACCESS  read-create
               STATUS      current
               DESCRIPTION
                   "Valid value of Inner DEI can be any of values between
                    0, 1 or 'Any'.
                   "
               ::= {     sm48tat4xarpQosQceEntry 16 }

    sm48tat4xarpQosFrameType OBJECT-TYPE
               SYNTAX      INTEGER {
                            any(1),
                            ethernet(2),
                            llc(3),
                            snap(4),
                            ipv4(5),
                            ipv6(6)
                           }
               MAX-ACCESS  read-create
               STATUS      current
               DESCRIPTION
                   "Frame Type can have any of the following values:
                    1: Any,
                    2: Ethernet,
                    3: LLC,
                    4: SNAP,
                    5: IPv4,
                    6: IPv6."
               ::= {     sm48tat4xarpQosQceEntry 17 }

    sm48tat4xarpQosMacEtherType OBJECT-TYPE
               SYNTAX      DisplayString
               MAX-ACCESS  read-create
               STATUS      current
               DESCRIPTION
                   "Valid ethernet type can have a value within 0x600-0xFFFF or 'Any' ,
                    but excluding 0x800(IPv4) and 0x86DD(IPv6),
                    range: 0000-FFFF,
                    default: Any."
               ::= {     sm48tat4xarpQosQceEntry 18 }

    sm48tat4xarpQosLLCSSAPAddr OBJECT-TYPE
               SYNTAX      DisplayString
               MAX-ACCESS  read-create
               STATUS      current
               DESCRIPTION
                   "Valid SSAP(Source Service Access Point) can vary from
                    0x00 to 0xFF or 'Any',
                    range: 00-FF,
                    default: Any."
               ::= {     sm48tat4xarpQosQceEntry 19 }

    sm48tat4xarpQosLLCDSAPAddr OBJECT-TYPE
               SYNTAX      DisplayString
               MAX-ACCESS  read-create
               STATUS      current
               DESCRIPTION
                   "Valid DSAP(Destination Service Access Point) can
                    vary from 0x00 to 0xFF or 'Any',
                    range: 00-FF,
                    default: Any."
               ::= {     sm48tat4xarpQosQceEntry 20 }

    sm48tat4xarpQosLLCControl OBJECT-TYPE
               SYNTAX      DisplayString
               MAX-ACCESS  read-create
               STATUS      current
               DESCRIPTION
                   "Valid Control field can vary from 0x00 to 0xFF or 'Any',
                    range: 00-FF,
                    default: Any."
               ::= {     sm48tat4xarpQosQceEntry 21 }

    sm48tat4xarpQosSNAPPID OBJECT-TYPE
               SYNTAX      DisplayString
               MAX-ACCESS  read-create
               STATUS      current
               DESCRIPTION
                   "Valid PID(a.k.a ethernet type) can have value within
                    0x00-0xFFFF or 'Any',
                    range: 0000-FFFF,
                    default: Any."
               ::= {     sm48tat4xarpQosQceEntry 22 }

   sm48tat4xarpQosIpv4Protocol OBJECT-TYPE
               SYNTAX      DisplayString
               MAX-ACCESS  read-create
               STATUS      current
               DESCRIPTION
                   "IP protocol number: (Other, TCP or UDP) or 'Any'."
               ::= {     sm48tat4xarpQosQceEntry 23 }

    sm48tat4xarpQosIpv4ProtocolValue  OBJECT-TYPE
               SYNTAX      Integer32(0..255)
               MAX-ACCESS  read-create
               STATUS      current
               DESCRIPTION
                   "Ipv4 Protocol is Other.
                    range: 0-255
                    default: 0."
               ::= {     sm48tat4xarpQosQceEntry 24 }

    sm48tat4xarpQosIpv4ProtocolUDPSPort OBJECT-TYPE
               SYNTAX      DisplayString
               MAX-ACCESS  read-create
               STATUS      current
               DESCRIPTION
                   "Source  TCP/UDP Port:(0-65535) or 'Any',
                    specific or port range applicable for IP protocol UDP/TCP."
               ::= {     sm48tat4xarpQosQceEntry 25 }

    sm48tat4xarpQosIpv4ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sm48tat4xarpQosQceEntry 26 }

    sm48tat4xarpQosIpv4ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sm48tat4xarpQosQceEntry 27 }

    sm48tat4xarpQosIpv4ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sm48tat4xarpQosQceEntry 28 }

    sm48tat4xarpQosIpv4SourceIp OBJECT-TYPE
               SYNTAX      DisplayString
               MAX-ACCESS  read-create
               STATUS      current
               DESCRIPTION
                   "Specific Source IP address in value format or value 0.0.0.0 is 'Any'.
                    if Ipv4 Mask value 0.0.0.0 is 'Any' ,IP address value also is 'Any'.
                    (x.y.z.w),x=0 unless y.z.w also 0,x not is 127 or greater than 223."
               ::= {     sm48tat4xarpQosQceEntry 29 }

    sm48tat4xarpQosIpv4SourceMask OBJECT-TYPE
               SYNTAX      DisplayString
               MAX-ACCESS  read-create
               STATUS      current
               DESCRIPTION
                   "Specific Source IP address in mask format or value 0.0.0.0 is 'Any'."
               ::= {     sm48tat4xarpQosQceEntry 30 }

    sm48tat4xarpQosIpv4DestIp OBJECT-TYPE
               SYNTAX      DisplayString
               MAX-ACCESS  read-create
               STATUS      current
               DESCRIPTION
                   "Specific Destination IP address in value format or value 0.0.0.0 is 'Any'.
                    if Ipv4 Mask value 0.0.0.0 is 'Any' ,IP address value also is 'Any'.
                    (x.y.z.w),x=0 unless y.z.w also 0,x not is 127 or greater than 223."
               ::= {     sm48tat4xarpQosQceEntry 31 }

    sm48tat4xarpQosIpv4DestMask OBJECT-TYPE
               SYNTAX      DisplayString
               MAX-ACCESS  read-create
               STATUS      current
               DESCRIPTION
                   "Specific Destination IP address in mask format or value 0.0.0.0 is 'Any'."
               ::= {     sm48tat4xarpQosQceEntry 32 }

    sm48tat4xarpQosIpv4IPFragment OBJECT-TYPE
               SYNTAX      INTEGER { any(0), no(1), yes(2) }
               MAX-ACCESS  read-create
               STATUS      current
               DESCRIPTION
                   "IPv4 frame fragmented option:
                    2: yes,
                    1: no,
                    0: any."
               ::= {     sm48tat4xarpQosQceEntry 33 }

    sm48tat4xarpQosIpv4DSCP OBJECT-TYPE
               SYNTAX      DisplayString
               MAX-ACCESS  read-create
               STATUS      current
               DESCRIPTION
                   "Diffserv Code Point value (DSCP): It can be a specific value,
                    range of values or 'Any'. DSCP values are in the range 0-63."
               ::= {     sm48tat4xarpQosQceEntry 34 }

    sm48tat4xarpQosIpv6Protocol OBJECT-TYPE
               SYNTAX      DisplayString
               MAX-ACCESS  read-create
               STATUS      current
               DESCRIPTION
                   "IP protocol number: (Other, TCP or UDP) or 'Any'."
               ::= {     sm48tat4xarpQosQceEntry 35 }

    sm48tat4xarpQosIpv6ProtocolValue OBJECT-TYPE
               SYNTAX      Integer32(0..255)
               MAX-ACCESS  read-create
               STATUS      current
               DESCRIPTION
                   "when IPv6 protocol is Other ,
                    range: 0-255."
               ::= {     sm48tat4xarpQosQceEntry 36 }

    sm48tat4xarpQosIpv6ProtocolUDPSPort OBJECT-TYPE
               SYNTAX      DisplayString
               MAX-ACCESS  read-create
               STATUS      current
               DESCRIPTION
                   "Source TCP/UDP port:(0-65535) or 'Any',
                    specific or port range applicable for IP protocol UDP/TCP."
               ::= {     sm48tat4xarpQosQceEntry 37 }

    sm48tat4xarpQosIpv6ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sm48tat4xarpQosQceEntry 38 }

    sm48tat4xarpQosIpv6ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sm48tat4xarpQosQceEntry 39 }


    sm48tat4xarpQosIpv6ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sm48tat4xarpQosQceEntry 40 }

    sm48tat4xarpQosIpv6SourceIp OBJECT-TYPE
               SYNTAX      DisplayString
               MAX-ACCESS  read-create
               STATUS      current
               DESCRIPTION
                   "IPv6 source address: (a.b.c.d) or value 0.0.0.0 is 'Any', 32 LS bits."
               ::= {     sm48tat4xarpQosQceEntry 41 }

    sm48tat4xarpQosIpv6SourceMask OBJECT-TYPE
               SYNTAX      DisplayString
               MAX-ACCESS  read-create
               STATUS      current
               DESCRIPTION
                   "IPv6 mask address: (a.b.c.d) or value 0.0.0.0 is 'Any', 32 LS bits."
               ::= {     sm48tat4xarpQosQceEntry 42 }

    sm48tat4xarpQosIpv6DestIp OBJECT-TYPE
               SYNTAX      DisplayString
               MAX-ACCESS  read-create
               STATUS      current
               DESCRIPTION
                   "IPv6 destination address: (a.b.c.d) or value 0.0.0.0 is 'Any', 32 LS bits."
               ::= {     sm48tat4xarpQosQceEntry 43 }

    sm48tat4xarpQosIpv6DestMask OBJECT-TYPE
               SYNTAX      DisplayString
               MAX-ACCESS  read-create
               STATUS      current
               DESCRIPTION
                   "IPv6 mask address: (a.b.c.d) or value 0.0.0.0 is 'Any', 32 LS bits."
               ::= {     sm48tat4xarpQosQceEntry 44 }

    sm48tat4xarpQosIpv6DSCP OBJECT-TYPE
               SYNTAX      DisplayString
               MAX-ACCESS  read-create
               STATUS      current
               DESCRIPTION
                   "Diffserv Code Point value (DSCP): It can be a specific value,
                    range of values or 'Any'. DSCP values are in the
                    range 0-63 including BE,
                    CS1-CS7, EF or AF11-AF43."
               ::= {     sm48tat4xarpQosQceEntry 45 }

    sm48tat4xarpQosActionQueuePriority  OBJECT-TYPE
               SYNTAX      Integer32(0..8)
               MAX-ACCESS  read-create
               STATUS      current
               DESCRIPTION
                   "QoS class: (0-7) or 8: Default."
               ::= {     sm48tat4xarpQosQceEntry 46 }

    sm48tat4xarpQosActionDPL OBJECT-TYPE
               SYNTAX      Integer32 (0..4)
               MAX-ACCESS  read-create
               STATUS      current
               DESCRIPTION
                   "range:0-4. 4: Default"
               ::= {     sm48tat4xarpQosQceEntry 47 }

    sm48tat4xarpQosActionDSCP OBJECT-TYPE
               SYNTAX      Integer32(0..64)
               MAX-ACCESS  read-create
               STATUS      current
               DESCRIPTION
                   "Valid DSCP value can be (0-63, BE, CS1-CS7,
                    EF or AF11-AF43) or 64: Default."
               ::= {     sm48tat4xarpQosQceEntry 48 }

    sm48tat4xarpQosActionPCP  OBJECT-TYPE
               SYNTAX      Integer32(0..8)
               MAX-ACCESS  read-create
               STATUS      current
               DESCRIPTION
                   "pcp: (0-7) or 8: Default.
                   "
               ::= {     sm48tat4xarpQosQceEntry 49 }

    sm48tat4xarpQosActionDEI OBJECT-TYPE
               SYNTAX      Integer32 (0..2)
               MAX-ACCESS  read-create
               STATUS      current
               DESCRIPTION
                   "dei: (0-1) or 2: Default.
                    "
               ::= {     sm48tat4xarpQosQceEntry 50 }

    sm48tat4xarpQosActionPolicy OBJECT-TYPE
               SYNTAX      Integer32(0..128)
               MAX-ACCESS  read-create
               STATUS      current
               DESCRIPTION
                   "ACL Policy number: (0-127) or 'empty'(128). Default: empty.
                    "
               ::= {     sm48tat4xarpQosQceEntry 51 }

    sm48tat4xarpQosActionIngressMapID OBJECT-TYPE
               SYNTAX      Integer32(-1..255)
               MAX-ACCESS  read-create
               STATUS      current
               DESCRIPTION
                   "Classify Ingress Map ID:
                   Range: 0-255
                   Default: -1
                   "
               ::= {     sm48tat4xarpQosQceEntry 52 }

    sm48tat4xarpQosQceRowStatus OBJECT-TYPE
               SYNTAX      RowStatus
               MAX-ACCESS  read-create
               STATUS      current
               DESCRIPTION
                   "This object indicates the status of this entry, and is used
                   to create/delete entries.  Any object in an entry of this table
                   may be modified while the value of the corresponding instance
                   of this object is active(1).
                   createAndGo, notReady not supported."
               ::= {     sm48tat4xarpQosQceEntry 53 }

--
-- =======================================================================================================================
-- Start  sm48tat4xarpQosStormControl group
-- =======================================================================================================================
--sm48tat4xarpQosStormControlTable
    sm48tat4xarpQosStormControlTable OBJECT-TYPE
               SYNTAX      SEQUENCE OF     SM48TAT4XARPQosStormControlEntry
               MAX-ACCESS  not-accessible
               STATUS      current
               DESCRIPTION
                   "The basic QoS DSCP Translation settings for all switches."
               ::= {     sm48tat4xarpQosStormControl  1 }

    sm48tat4xarpQosStormControlEntry OBJECT-TYPE
               SYNTAX          SM48TAT4XARPQosStormControlEntry
               MAX-ACCESS  not-accessible
               STATUS      current
               DESCRIPTION
                   "The Qos Storm Control Entry."
               INDEX    {     sm48tat4xarpQosStormControlFrameType  }
               ::= {     sm48tat4xarpQosStormControlTable 1 }

    SM48TAT4XARPQosStormControlEntry             ::= SEQUENCE {
                sm48tat4xarpQosStormControlFrameType        INTEGER,
                sm48tat4xarpQosStormControlEnabled          AdminMode,
                sm48tat4xarpQosStormControlRate             Integer32,
                sm48tat4xarpQosStormControlUnit             Integer32
                }

    sm48tat4xarpQosStormControlFrameType OBJECT-TYPE
               SYNTAX      INTEGER { unicast(1), multicast (2), broadcast (3)}
               MAX-ACCESS  not-accessible
               STATUS      current
               DESCRIPTION
                   "The settings in a particular row apply to the frame type listed here.
                    1:Unicast,
                    2:Multicast,
                    3:Broadcast."
               ::= {     sm48tat4xarpQosStormControlEntry 1 }

    sm48tat4xarpQosStormControlEnabled OBJECT-TYPE
               SYNTAX      AdminMode
               MAX-ACCESS  read-write
               STATUS      current
               DESCRIPTION
                  "Enable or disable the global storm policer for the given frame type."
               ::= {     sm48tat4xarpQosStormControlEntry 2 }

    sm48tat4xarpQosStormControlRate OBJECT-TYPE
               SYNTAX      Integer32
               MAX-ACCESS  read-write
               STATUS      current
               DESCRIPTION
                   "Controls the rate for the global storm policer."
               ::= {     sm48tat4xarpQosStormControlEntry 3 }

    sm48tat4xarpQosStormControlUnit OBJECT-TYPE
               SYNTAX      Integer32
               MAX-ACCESS  read-write
               STATUS      current
               DESCRIPTION
                   "Controls the unit of measure for the global storm policer rate as fps or kfps.
                   0: kbps
                   1: Mbps
                   2: fps
                   3: kfps"
               ::= {     sm48tat4xarpQosStormControlEntry 4 }

--
-- =======================================================================================================================
-- Start  sm48tat4xarpQosPortStormControl group
-- =======================================================================================================================
--sm48tat4xarpQosPortStormControlTable
    sm48tat4xarpQosPortStormControlTable OBJECT-TYPE
               SYNTAX      SEQUENCE OF     SM48TAT4XARPQosPortStormControlEntry
               MAX-ACCESS  not-accessible
               STATUS      current
               DESCRIPTION
                   "Configure the storm control settings.
                    INDEX for this table is ifIndex which is
                    equivalent to the panel port number."
               ::= {     sm48tat4xarpQosPortStormControl  1 }

    sm48tat4xarpQosPortStormControlEntry OBJECT-TYPE
               SYNTAX      SM48TAT4XARPQosPortStormControlEntry
               MAX-ACCESS  not-accessible
               STATUS      current
               DESCRIPTION
                   "The Qos Port Storm Control Entry."
               INDEX    {     ifIndex  }
               ::= {     sm48tat4xarpQosPortStormControlTable 1 }

    SM48TAT4XARPQosPortStormControlEntry             ::= SEQUENCE {
                sm48tat4xarpQosPortStormControlUnicastEnabled   AdminMode,
                sm48tat4xarpQosPortStormControlUnicastRate      Integer32,
                sm48tat4xarpQosPortStormControlUnicastUnit      Integer32,
                sm48tat4xarpQosPortStormControlBroadcastEnabled AdminMode,
                sm48tat4xarpQosPortStormControlBroadcastRate    Integer32,
                sm48tat4xarpQosPortStormControlBroadcastUnit    Integer32,
                sm48tat4xarpQosPortStormControlUnknownEnabled   AdminMode,
                sm48tat4xarpQosPortStormControlUnknownRate      Integer32,
                sm48tat4xarpQosPortStormControlUnknownUnit      Integer32
                }

     sm48tat4xarpQosPortStormControlUnicastEnabled OBJECT-TYPE
               SYNTAX      AdminMode
               MAX-ACCESS  read-write
               STATUS      current
               DESCRIPTION
                  "Controls whether the storm control is enabled on this
                   switch port."
               ::= {     sm48tat4xarpQosPortStormControlEntry 2 }

    sm48tat4xarpQosPortStormControlUnicastRate OBJECT-TYPE
               SYNTAX      Integer32
               MAX-ACCESS  read-write
               STATUS      current
               DESCRIPTION
                   "Controls the rate for the storm control."
               ::= {     sm48tat4xarpQosPortStormControlEntry 3 }

    sm48tat4xarpQosPortStormControlUnicastUnit OBJECT-TYPE
               SYNTAX      Integer32
               MAX-ACCESS  read-write
               STATUS      current
               DESCRIPTION
                   "Controls the unit of measure for the storm control rate.
                   0: kbps
                   1: Mbps
                   2: fps
                   3: kfps"
               ::= {     sm48tat4xarpQosPortStormControlEntry 4 }

     sm48tat4xarpQosPortStormControlBroadcastEnabled  OBJECT-TYPE
               SYNTAX      AdminMode
               MAX-ACCESS  read-write
               STATUS      current
               DESCRIPTION
                  "Controls whether the storm control is enabled on this
                   switch port."
               ::= {     sm48tat4xarpQosPortStormControlEntry 5 }

    sm48tat4xarpQosPortStormControlBroadcastRate OBJECT-TYPE
               SYNTAX      Integer32
               MAX-ACCESS  read-write
               STATUS      current
               DESCRIPTION
                   "Controls the rate for the storm control."
               ::= {     sm48tat4xarpQosPortStormControlEntry 6 }

    sm48tat4xarpQosPortStormControlBroadcastUnit OBJECT-TYPE
               SYNTAX      Integer32
               MAX-ACCESS  read-write
               STATUS      current
               DESCRIPTION
                   "Controls the unit of measure for the storm control rate.
                   0: kbps
                   1: Mbps
                   2: fps
                   3: kfps"
               ::= {     sm48tat4xarpQosPortStormControlEntry 7 }

    sm48tat4xarpQosPortStormControlUnknownEnabled  OBJECT-TYPE
               SYNTAX      AdminMode
               MAX-ACCESS  read-write
               STATUS      current
               DESCRIPTION
                  "Controls whether the storm control is enabled on this
                   switch port."
               ::= {     sm48tat4xarpQosPortStormControlEntry 8 }

    sm48tat4xarpQosPortStormControlUnknownRate OBJECT-TYPE
               SYNTAX      Integer32
               MAX-ACCESS  read-write
               STATUS      current
               DESCRIPTION
                   "Controls the rate for the storm control."
               ::= {     sm48tat4xarpQosPortStormControlEntry 9 }

    sm48tat4xarpQosPortStormControlUnknownUnit OBJECT-TYPE
               SYNTAX      Integer32
               MAX-ACCESS  read-write
               STATUS      current
               DESCRIPTION
                   "Controls the unit of measure for the storm control rate.
                   0: kbps
                   1: Mbps
                   2: fps
                   3: kfps"
               ::= {     sm48tat4xarpQosPortStormControlEntry 10 }

--
-- =======================================================================================================================
-- Start  sm48tat4xarpQosWRED group
-- =======================================================================================================================
--sm48tat4xarpQosWREDTable
    sm48tat4xarpQosWREDTable OBJECT-TYPE
               SYNTAX      SEQUENCE OF     SM48TAT4XARPQosWREDEntry
               MAX-ACCESS  not-accessible
               STATUS      current
               DESCRIPTION
                   "The basic QoS DSCP Translation settings for all switches."
               ::= {     sm48tat4xarpQosWRED  1 }

    sm48tat4xarpQosWREDEntry OBJECT-TYPE
               SYNTAX          SM48TAT4XARPQosWREDEntry
               MAX-ACCESS  not-accessible
               STATUS      current
               DESCRIPTION
                   "The Qos WRED Entry."
               INDEX    {     sm48tat4xarpQosWREDQueue  }
               ::= {     sm48tat4xarpQosWREDTable 1 }

    SM48TAT4XARPQosWREDEntry             ::= SEQUENCE {
                sm48tat4xarpQosWREDGroupIndex      Integer32,
                sm48tat4xarpQosWREDQueue           Integer32,
                sm48tat4xarpQosWREDDPL             Integer32,
                sm48tat4xarpQosWREDEnable          AdminMode,
                sm48tat4xarpQosWREDMinThreshold    Integer32,
                sm48tat4xarpQosWREDMaxThreshold    Integer32,
                sm48tat4xarpQosWREDMaxUnit         INTEGER
                }

    sm48tat4xarpQosWREDGroupIndex OBJECT-TYPE
               SYNTAX      Integer32
               MAX-ACCESS  not-accessible
               STATUS      current
               DESCRIPTION
                   "The group number for which the configuration
                    below applies."
               ::= {     sm48tat4xarpQosWREDEntry 1 }

    sm48tat4xarpQosWREDQueue OBJECT-TYPE
               SYNTAX      Integer32(1..65535)
               MAX-ACCESS  not-accessible
               STATUS      current
               DESCRIPTION
                   "The queue number (QoS class) for which the configuration
                    below applies."
               ::= {     sm48tat4xarpQosWREDEntry 2 }

    sm48tat4xarpQosWREDDPL OBJECT-TYPE
               SYNTAX      Integer32
               MAX-ACCESS  not-accessible
               STATUS      current
               DESCRIPTION
                   "The dpl number for which the configuration
                    below applies."
               ::= {     sm48tat4xarpQosWREDEntry 3 }


    sm48tat4xarpQosWREDEnable OBJECT-TYPE
               SYNTAX      AdminMode
               MAX-ACCESS  read-write
               STATUS      current
               DESCRIPTION
                  "Controls whether RED is enabled for this queue.
                  "
               DEFVAL  { disable }
               ::= {     sm48tat4xarpQosWREDEntry 4 }

    sm48tat4xarpQosWREDMinThreshold OBJECT-TYPE
               SYNTAX      Integer32(0..100)
               MAX-ACCESS  read-write
               STATUS      current
               DESCRIPTION
                   "Controls the lower RED fill level threshold. If the queue filling
                    level is below this threshold, the drop probability is zero.
                    range:0-100%,
                    default: 0.
                  "
               ::= {     sm48tat4xarpQosWREDEntry 5 }

    sm48tat4xarpQosWREDMaxThreshold OBJECT-TYPE
               SYNTAX      Integer32(0..100)
               MAX-ACCESS  read-write
               STATUS      current
               DESCRIPTION
                   "Controls the upper RED drop probability or fill level threshold
                    for frames marked with Drop Precedence Level 1 (yellow frames).
                    range:0-100%,
                    default: 50.
                  "
               ::= {     sm48tat4xarpQosWREDEntry 6 }

    sm48tat4xarpQosWREDMaxUnit OBJECT-TYPE
               SYNTAX      INTEGER {dropProbability (0), fillLevel (1) }
               MAX-ACCESS  read-write
               STATUS      current
               DESCRIPTION
                   "Selects the unit for Max.
                    0: Drop Probability,
                    1: Fill Level,
                    default: Drop Probability.
                  "
               DEFVAL  { dropProbability }
               ::= {     sm48tat4xarpQosWREDEntry 7 }

--
-- =======================================================================================================================
-- Start  sm48tat4xarpQosQCLStatus
-- =======================================================================================================================

--sm48tat4xarpQosQCLStatusTable
    sm48tat4xarpQosQCLStatusTable OBJECT-TYPE
               SYNTAX      SEQUENCE OF     SM48TAT4XARPQosQCLStatusEntry
               MAX-ACCESS  not-accessible
               STATUS      current
               DESCRIPTION
                   "The basic QoS DSCP Translation settings for all switches."
               ::= {     sm48tat4xarpQosQCLStatus 1 }

    sm48tat4xarpQosQCLStatusEntry OBJECT-TYPE
               SYNTAX          SM48TAT4XARPQosQCLStatusEntry
               MAX-ACCESS  not-accessible
               STATUS      current
               DESCRIPTION
                   "The Qos QCL Status Entry."
               INDEX    {     sm48tat4xarpQosQCLStatusList  }
               ::= {     sm48tat4xarpQosQCLStatusTable 1 }

    SM48TAT4XARPQosQCLStatusEntry             ::= SEQUENCE {
        sm48tat4xarpQosQCLStatusList               Integer32,
        sm48tat4xarpQosQCLStatusUser               DisplayString,
        sm48tat4xarpQosQCLStatusQCEId              DisplayString,
        sm48tat4xarpQosQCLStatusFrameType          DisplayString,
        sm48tat4xarpQosQCLStatusPortlist           DisplayString,
        sm48tat4xarpQosQCLStatusActionQueuePriority DisplayString,
        sm48tat4xarpQosQCLStatusActionDPL          DisplayString,
        sm48tat4xarpQosQCLStatusActionDSCP         DisplayString,
        sm48tat4xarpQosQCLStatusActionPCP          DisplayString,
        sm48tat4xarpQosQCLStatusActionDEL          DisplayString,
        sm48tat4xarpQosQCLStatusActionPolicy       DisplayString,
        sm48tat4xarpQosQCLStatusConflict           DisplayString,
--      sm48tat4xarpQosQCLStatusSwitch             Integer32,
		sm48tat4xarpQosQCLStatusDMAC               DisplayString,
		sm48tat4xarpQosQCLStatusSMAC               DisplayString,
		sm48tat4xarpQosQCLStatusTag                DisplayString,
		sm48tat4xarpQosQCLStatusVID                DisplayString,
		sm48tat4xarpQosQCLStatusPCP                DisplayString,
		sm48tat4xarpQosQCLStatusDEI                DisplayString
                }

    sm48tat4xarpQosQCLStatusList OBJECT-TYPE
               SYNTAX      Integer32(1..4095)
               MAX-ACCESS  not-accessible
               STATUS      current
               DESCRIPTION
                   "QCL table index."
               ::= {     sm48tat4xarpQosQCLStatusEntry 1}

    sm48tat4xarpQosQCLStatusUser OBJECT-TYPE
               SYNTAX      DisplayString
               MAX-ACCESS  read-only
               STATUS      current
               DESCRIPTION
                   "Indicates the QCL user."
               ::= {     sm48tat4xarpQosQCLStatusEntry 2 }

    sm48tat4xarpQosQCLStatusQCEId OBJECT-TYPE
               SYNTAX      DisplayString
               MAX-ACCESS  read-only
               STATUS      current
               DESCRIPTION
                  "Indicates the index of QCE."
               ::= {     sm48tat4xarpQosQCLStatusEntry 3}

    sm48tat4xarpQosQCLStatusFrameType OBJECT-TYPE
               SYNTAX      DisplayString
               MAX-ACCESS  read-only
               STATUS      current
               DESCRIPTION
                   "Indicates the type of frame to look for incomming frames.
                    Any: The QCE will match all frame type.
                    Ethernet: Only Ethernet frames (with Ether Type 0x600-0xFFFF)
                    are allowed.
                    LLC: Only (LLC) frames are allowed.
                    SNAP: Only (SNAP) frames are allowed.
                    IPv4: The QCE will match only IPV4 frames.
                    IPv6: The QCE will match only IPV6 frames."
               ::= {     sm48tat4xarpQosQCLStatusEntry 4}

    sm48tat4xarpQosQCLStatusPortlist OBJECT-TYPE
               SYNTAX      DisplayString
               MAX-ACCESS  read-only
               STATUS      current
               DESCRIPTION
                   "Indicates the list of ports configured with the QCE."
               ::= {     sm48tat4xarpQosQCLStatusEntry 5}

    sm48tat4xarpQosQCLStatusActionQueuePriority OBJECT-TYPE
               SYNTAX      DisplayString
               MAX-ACCESS  read-only
               STATUS      current
               DESCRIPTION
                   "Classified QoS class; if a frame matches the
                    QCE it will be put in the  queue."
               ::= {     sm48tat4xarpQosQCLStatusEntry 6}

    sm48tat4xarpQosQCLStatusActionDPL OBJECT-TYPE
               SYNTAX      DisplayString
               MAX-ACCESS  read-only
               STATUS      current
               DESCRIPTION
                   "Drop Precedence Level; if a frame matches the QCE then
                    DP level will set to value displayed under DPL column."
               ::= {     sm48tat4xarpQosQCLStatusEntry 7}

    sm48tat4xarpQosQCLStatusActionDSCP OBJECT-TYPE
               SYNTAX      DisplayString
               MAX-ACCESS  read-only
               STATUS      current
               DESCRIPTION
                   "If a frame matches the QCE then DSCP will be
                    classified with the value
                    displayed under DSCP column."
               ::= {     sm48tat4xarpQosQCLStatusEntry 8}

    sm48tat4xarpQosQCLStatusActionPCP OBJECT-TYPE
               SYNTAX      DisplayString
               MAX-ACCESS  read-only
               STATUS      current
               DESCRIPTION
                   "Classify PCP value.
                    Only support SERVAL."
               ::= {     sm48tat4xarpQosQCLStatusEntry 9}

    sm48tat4xarpQosQCLStatusActionDEL OBJECT-TYPE
               SYNTAX      DisplayString
               MAX-ACCESS  read-only
               STATUS      current
               DESCRIPTION
                   "Classify DEI value.
                    Only support SERVAL."
               ::= {     sm48tat4xarpQosQCLStatusEntry 10}

    sm48tat4xarpQosQCLStatusActionPolicy OBJECT-TYPE
               SYNTAX      DisplayString
               MAX-ACCESS  read-only
               STATUS      current
               DESCRIPTION
                   "Classify ACL Policy number.
                    "
               ::= {     sm48tat4xarpQosQCLStatusEntry 11}

    sm48tat4xarpQosQCLStatusConflict OBJECT-TYPE
               SYNTAX      DisplayString
               MAX-ACCESS  read-only
               STATUS      current
               DESCRIPTION
                   "Displays Conflict status of QCL entries."
               ::= {     sm48tat4xarpQosQCLStatusEntry 12}

--    sm48tat4xarpQosQCLStatusSwitch OBJECT-TYPE
--               SYNTAX      Integer32
--               MAX-ACCESS  read-only
--               STATUS      current
--               DESCRIPTION
--                   "Switch number for port members. -1:Any.
--                    Only support stacking switch."
--               ::= {     sm48tat4xarpQosQCLStatusEntry 13}

    sm48tat4xarpQosQCLStatusDMAC OBJECT-TYPE
               SYNTAX      DisplayString
               MAX-ACCESS  read-only
               STATUS      current
               DESCRIPTION
                   "Destination MAC address: Possible values are 'Unicast', 'Multicast', 'Broadcast' or 'Any'."
               ::= {     sm48tat4xarpQosQCLStatusEntry 14}

    sm48tat4xarpQosQCLStatusSMAC OBJECT-TYPE
               SYNTAX      DisplayString
               MAX-ACCESS  read-only
               STATUS      current
               DESCRIPTION
                   "Source MAC address: xx-xx-xx-xx-xx-xx or 'Any'."
               ::= {     sm48tat4xarpQosQCLStatusEntry 15}

    sm48tat4xarpQosQCLStatusTag OBJECT-TYPE
               SYNTAX      DisplayString
               MAX-ACCESS  read-only
               STATUS      current
               DESCRIPTION
                   "Value of Tag field can be 'Untagged', 'Tagged', 'C-Tagged', 'S-Tagged' or 'Any'."
               ::= {     sm48tat4xarpQosQCLStatusEntry 16}

    sm48tat4xarpQosQCLStatusVID OBJECT-TYPE
               SYNTAX      DisplayString
               MAX-ACCESS  read-only
               STATUS      current
               DESCRIPTION
                   "Valid value of VLAN ID can be any value in the range 1-4095 or 'Any'"
               ::= {     sm48tat4xarpQosQCLStatusEntry 17}

    sm48tat4xarpQosQCLStatusPCP OBJECT-TYPE
               SYNTAX      DisplayString
               MAX-ACCESS  read-only
               STATUS      current
               DESCRIPTION
                   "Valid value PCP are specific (0, 1, 2, 3, 4, 5, 6, 7) or range (0-1, 2-3, 4-5, 6-7, 0-3, 4-7) or 'Any'."
               ::= {     sm48tat4xarpQosQCLStatusEntry 18}

    sm48tat4xarpQosQCLStatusDEI OBJECT-TYPE
               SYNTAX      DisplayString
               MAX-ACCESS  read-only
               STATUS      current
               DESCRIPTION
                   "Valid value of DEI can be '0', '1' or 'Any'."
               ::= {     sm48tat4xarpQosQCLStatusEntry 19}

    sm48tat4xarpQosPortShaperTable OBJECT-TYPE
               SYNTAX      SEQUENCE OF     SM48TAT4XARPQosPortShaperEntry
               MAX-ACCESS  not-accessible
               STATUS      current
               DESCRIPTION
                   "INDEX for this table is ifIndex which is
                    equivalent to the panel port number."
               ::= {     sm48tat4xarpQosPortShapers 1 }

    sm48tat4xarpQosPortShaperEntry OBJECT-TYPE
               SYNTAX          SM48TAT4XARPQosPortShaperEntry
               MAX-ACCESS  not-accessible
               STATUS      current
               DESCRIPTION
                   "The Qos Port Shaper Entry."
               INDEX    {     ifIndex  }
               ::= {     sm48tat4xarpQosPortShaperTable 1 }

    SM48TAT4XARPQosPortShaperEntry             ::= SEQUENCE {
                sm48tat4xarpQosPortShaperQueue0Enable   AdminMode,
                sm48tat4xarpQosPortShaperQueue0Rate     Integer32,
                sm48tat4xarpQosPortShaperQueue0Unit     Integer32,
                sm48tat4xarpQosPortShaperQueue1Enable   AdminMode,
                sm48tat4xarpQosPortShaperQueue1Rate     Integer32,
                sm48tat4xarpQosPortShaperQueue1Unit     Integer32,
                sm48tat4xarpQosPortShaperQueue2Enable   AdminMode,
                sm48tat4xarpQosPortShaperQueue2Rate     Integer32,
                sm48tat4xarpQosPortShaperQueue2Unit     Integer32,
                sm48tat4xarpQosPortShaperQueue3Enable   AdminMode,
                sm48tat4xarpQosPortShaperQueue3Rate     Integer32,
                sm48tat4xarpQosPortShaperQueue3Unit     Integer32,
                sm48tat4xarpQosPortShaperQueue4Enable   AdminMode,
                sm48tat4xarpQosPortShaperQueue4Rate     Integer32,
                sm48tat4xarpQosPortShaperQueue4Unit     Integer32,
                sm48tat4xarpQosPortShaperQueue5Enable   AdminMode,
                sm48tat4xarpQosPortShaperQueue5Rate     Integer32,
                sm48tat4xarpQosPortShaperQueue5Unit     Integer32,
                sm48tat4xarpQosPortShaperQueue6Enable   AdminMode,
                sm48tat4xarpQosPortShaperQueue6Rate     Integer32,
                sm48tat4xarpQosPortShaperQueue6Unit     Integer32,
                sm48tat4xarpQosPortShaperQueue7Enable   AdminMode,
                sm48tat4xarpQosPortShaperQueue7Rate     Integer32,
                sm48tat4xarpQosPortShaperQueue7Unit     Integer32,
                sm48tat4xarpQosPortShaperEnable         AdminMode,
                sm48tat4xarpQosPortShaperRate           Integer32,
                sm48tat4xarpQosPortShaperRateType       Integer32
                }

    sm48tat4xarpQosPortShaperQueue0Enable OBJECT-TYPE
               SYNTAX      AdminMode
               MAX-ACCESS  read-write
               STATUS      current
               DESCRIPTION
                   "Controls whether the queue shaper is enabled on this switch port."
               DEFVAL  { disable }
               ::= {     sm48tat4xarpQosPortShaperEntry 3 }

    sm48tat4xarpQosPortShaperQueue0Rate OBJECT-TYPE
               SYNTAX      Integer32
               MAX-ACCESS  read-write
               STATUS      current
               DESCRIPTION
                   "Controls whether the queue shaper rate.
                    default: 500(Kbps)"
               ::= {     sm48tat4xarpQosPortShaperEntry 4 }

    sm48tat4xarpQosPortShaperQueue0Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sm48tat4xarpQosPortShaperEntry 5 }

    sm48tat4xarpQosPortShaperQueue1Enable OBJECT-TYPE
               SYNTAX      AdminMode
               MAX-ACCESS  read-write
               STATUS      current
               DESCRIPTION
                   "Controls whether the queue shaper is enabled on this switch port."
               DEFVAL  { disable }
               ::= {     sm48tat4xarpQosPortShaperEntry 6 }

    sm48tat4xarpQosPortShaperQueue1Rate OBJECT-TYPE
               SYNTAX      Integer32
               MAX-ACCESS  read-write
               STATUS      current
               DESCRIPTION
                   "Controls whether the queue shaper rate.
                    default: 500(Kbps)"
               ::= {     sm48tat4xarpQosPortShaperEntry 7 }

    sm48tat4xarpQosPortShaperQueue1Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sm48tat4xarpQosPortShaperEntry 8 }

    sm48tat4xarpQosPortShaperQueue2Enable OBJECT-TYPE
               SYNTAX      AdminMode
               MAX-ACCESS  read-write
               STATUS      current
               DESCRIPTION
                   "Controls whether the queue shaper is enabled on this switch port."
               DEFVAL  { disable }
               ::= {     sm48tat4xarpQosPortShaperEntry 9 }

    sm48tat4xarpQosPortShaperQueue2Rate OBJECT-TYPE
               SYNTAX      Integer32
               MAX-ACCESS  read-write
               STATUS      current
               DESCRIPTION
                   "Controls whether the queue shaper rate.
                    default: 500(Kbps)"
               ::= {     sm48tat4xarpQosPortShaperEntry 10 }

    sm48tat4xarpQosPortShaperQueue2Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sm48tat4xarpQosPortShaperEntry 11 }

    sm48tat4xarpQosPortShaperQueue3Enable OBJECT-TYPE
               SYNTAX      AdminMode
               MAX-ACCESS  read-write
               STATUS      current
               DESCRIPTION
                   "Controls whether the queue shaper is enabled on this switch port."
               DEFVAL  { disable }
               ::= {     sm48tat4xarpQosPortShaperEntry 12 }

    sm48tat4xarpQosPortShaperQueue3Rate OBJECT-TYPE
               SYNTAX      Integer32
               MAX-ACCESS  read-write
               STATUS      current
               DESCRIPTION
                   "Controls whether the queue shaper rate.
                    default: 500(Kbps)"
               ::= {     sm48tat4xarpQosPortShaperEntry 13 }

    sm48tat4xarpQosPortShaperQueue3Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sm48tat4xarpQosPortShaperEntry 14 }

    sm48tat4xarpQosPortShaperQueue4Enable OBJECT-TYPE
               SYNTAX      AdminMode
               MAX-ACCESS  read-write
               STATUS      current
               DESCRIPTION
                   "Controls whether the queue shaper is enabled on this switch port."
               DEFVAL  { disable }
               ::= {     sm48tat4xarpQosPortShaperEntry 15 }

    sm48tat4xarpQosPortShaperQueue4Rate OBJECT-TYPE
               SYNTAX      Integer32
               MAX-ACCESS  read-write
               STATUS      current
               DESCRIPTION
                   "Controls whether the queue shaper rate.
                    default: 500(Kbps)"
               ::= {     sm48tat4xarpQosPortShaperEntry 16 }

    sm48tat4xarpQosPortShaperQueue4Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sm48tat4xarpQosPortShaperEntry 17 }

    sm48tat4xarpQosPortShaperQueue5Enable OBJECT-TYPE
               SYNTAX      AdminMode
               MAX-ACCESS  read-write
               STATUS      current
               DESCRIPTION
                   "Controls whether the queue shaper is enabled on this switch port."
               DEFVAL  { disable }
               ::= {     sm48tat4xarpQosPortShaperEntry 18 }

    sm48tat4xarpQosPortShaperQueue5Rate OBJECT-TYPE
               SYNTAX      Integer32
               MAX-ACCESS  read-write
               STATUS      current
               DESCRIPTION
                   "Controls whether the queue shaper rate.
                    default: 500(Kbps)"
               ::= {     sm48tat4xarpQosPortShaperEntry 19 }

    sm48tat4xarpQosPortShaperQueue5Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sm48tat4xarpQosPortShaperEntry 20 }

    sm48tat4xarpQosPortShaperQueue6Enable OBJECT-TYPE
               SYNTAX      AdminMode
               MAX-ACCESS  read-write
               STATUS      current
               DESCRIPTION
                   "Controls whether the queue shaper is enabled on this switch port."
               DEFVAL  { disable }
               ::= {     sm48tat4xarpQosPortShaperEntry 21 }

    sm48tat4xarpQosPortShaperQueue6Rate OBJECT-TYPE
               SYNTAX      Integer32
               MAX-ACCESS  read-write
               STATUS      current
               DESCRIPTION
                   "Controls whether the queue shaper rate.
                    default: 500(Kbps)"
               ::= {     sm48tat4xarpQosPortShaperEntry 22 }

    sm48tat4xarpQosPortShaperQueue6Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sm48tat4xarpQosPortShaperEntry 23 }

    sm48tat4xarpQosPortShaperQueue7Enable OBJECT-TYPE
               SYNTAX      AdminMode
               MAX-ACCESS  read-write
               STATUS      current
               DESCRIPTION
                   "Controls whether the queue shaper is enabled on this switch port."
               DEFVAL  { disable }
               ::= {     sm48tat4xarpQosPortShaperEntry 24 }

    sm48tat4xarpQosPortShaperQueue7Rate OBJECT-TYPE
               SYNTAX      Integer32
               MAX-ACCESS  read-write
               STATUS      current
               DESCRIPTION
                   "Controls whether the queue shaper rate.
                    default: 500(Kbps)"
               ::= {     sm48tat4xarpQosPortShaperEntry 25 }

    sm48tat4xarpQosPortShaperQueue7Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sm48tat4xarpQosPortShaperEntry 26 }

    sm48tat4xarpQosPortShaperEnable OBJECT-TYPE
               SYNTAX      AdminMode
               MAX-ACCESS  read-write
               STATUS      current
               DESCRIPTION
                   "Controls whether the port shaper is enabled."
               DEFVAL  { disable }
               ::= {     sm48tat4xarpQosPortShaperEntry 27 }

    sm48tat4xarpQosPortShaperRate OBJECT-TYPE
               SYNTAX      Integer32
               MAX-ACCESS  read-write
               STATUS      current
               DESCRIPTION
                   "Controls the rate for the port shaper.
                    default: 500 kbps."
               ::= {     sm48tat4xarpQosPortShaperEntry 28 }

    sm48tat4xarpQosPortShaperRateType OBJECT-TYPE
               SYNTAX      Integer32(0|1)
               MAX-ACCESS  read-write
               STATUS      current
               DESCRIPTION
                   "The rate type of the port shaper.
                    0:Line
                    1:Data"
               ::= {     sm48tat4xarpQosPortShaperEntry 29 }

    sm48tat4xarpQosPortSchedulersTable OBJECT-TYPE
               SYNTAX      SEQUENCE OF     SM48TAT4XARPQosPortSchedulersEntry
               MAX-ACCESS  not-accessible
               STATUS      current
               DESCRIPTION
                   "INDEX for this table is ifIndex which is
                    equivalent to the panel port number."
               ::= {     sm48tat4xarpQosPortSchedulers 1 }

    sm48tat4xarpQosPortSchedulersEntry OBJECT-TYPE
               SYNTAX          SM48TAT4XARPQosPortSchedulersEntry
               MAX-ACCESS  not-accessible
               STATUS      current
               DESCRIPTION
                   "The Qos Port Shaper Entry."
               INDEX    {     ifIndex  }
               ::= {     sm48tat4xarpQosPortSchedulersTable 1 }

    SM48TAT4XARPQosPortSchedulersEntry             ::= SEQUENCE {
                sm48tat4xarpQosPortSchedulersMode     Integer32,
                sm48tat4xarpQosPortSchedulersQ0Weight Integer32,
                sm48tat4xarpQosPortSchedulersQ1Weight Integer32,
                sm48tat4xarpQosPortSchedulersQ2Weight Integer32,
                sm48tat4xarpQosPortSchedulersQ3Weight Integer32,
                sm48tat4xarpQosPortSchedulersQ4Weight Integer32,
                sm48tat4xarpQosPortSchedulersQ5Weight Integer32,
                sm48tat4xarpQosPortSchedulersQ6Weight Integer32,
                sm48tat4xarpQosPortSchedulersQ7Weight Integer32
                }

    sm48tat4xarpQosPortSchedulersMode OBJECT-TYPE
               SYNTAX      Integer32(0|8)
               MAX-ACCESS  read-write
               STATUS      current
               DESCRIPTION
                   "0:Strict Priority
                    8:Weighted"
               ::= {     sm48tat4xarpQosPortSchedulersEntry 2 }

    sm48tat4xarpQosPortSchedulersQ0Weight OBJECT-TYPE
               SYNTAX      Integer32(1..100)
               MAX-ACCESS  read-write
               STATUS      current
               DESCRIPTION
                   "Controls the weight for this queue. This value is restricted to 1-100."
               ::= {     sm48tat4xarpQosPortSchedulersEntry 3 }

    sm48tat4xarpQosPortSchedulersQ1Weight OBJECT-TYPE
               SYNTAX      Integer32(1..100)
               MAX-ACCESS  read-write
               STATUS      current
               DESCRIPTION
                   "Controls the weight for this queue. This value is restricted to 1-100."
               ::= {     sm48tat4xarpQosPortSchedulersEntry 4 }

    sm48tat4xarpQosPortSchedulersQ2Weight OBJECT-TYPE
               SYNTAX      Integer32(1..100)
               MAX-ACCESS  read-write
               STATUS      current
               DESCRIPTION
                   "Controls the weight for this queue. This value is restricted to 1-100."
               ::= {     sm48tat4xarpQosPortSchedulersEntry 5 }

    sm48tat4xarpQosPortSchedulersQ3Weight OBJECT-TYPE
               SYNTAX      Integer32(1..100)
               MAX-ACCESS  read-write
               STATUS      current
               DESCRIPTION
                   "Controls the weight for this queue. This value is restricted to 1-100."
               ::= {     sm48tat4xarpQosPortSchedulersEntry 6 }

    sm48tat4xarpQosPortSchedulersQ4Weight OBJECT-TYPE
               SYNTAX      Integer32(1..100)
               MAX-ACCESS  read-write
               STATUS      current
               DESCRIPTION
                   "Controls the weight for this queue. This value is restricted to 1-100."
               ::= {     sm48tat4xarpQosPortSchedulersEntry 7 }

    sm48tat4xarpQosPortSchedulersQ5Weight OBJECT-TYPE
               SYNTAX      Integer32(1..100)
               MAX-ACCESS  read-write
               STATUS      current
               DESCRIPTION
                   "Controls the weight for this queue. This value is restricted to 1-100."
               ::= {     sm48tat4xarpQosPortSchedulersEntry 8 }

    sm48tat4xarpQosPortSchedulersQ6Weight OBJECT-TYPE
               SYNTAX      Integer32(1..100)
               MAX-ACCESS  read-write
               STATUS      current
               DESCRIPTION
                   "Controls the weight for this queue. This value is restricted to 1-100."
               ::= {     sm48tat4xarpQosPortSchedulersEntry 9 }

    sm48tat4xarpQosPortSchedulersQ7Weight OBJECT-TYPE
               SYNTAX      Integer32(1..100)
               MAX-ACCESS  read-write
               STATUS      current
               DESCRIPTION
                   "Controls the weight for this queue. This value is restricted to 1-100."
               ::= {     sm48tat4xarpQosPortSchedulersEntry 10 }

-- =======================================================================================================================
--sm48tat4xarpBroadcastStormProtection                                                  OBJECT IDENTIFIER ::= { sm48tat4xarpConfiguration 11 }
--
--sm48tat4xarpBroadcastStormProtectionConfigurationTable OBJECT-TYPE
--   SYNTAX      SEQUENCE OF SM48TAT4XARPBroadcastStormProtectionConfigurationEntry
--   MAX-ACCESS  not-accessible
--   STATUS      current
--   DESCRIPTION
--       " Show Broadcast Storm Protection configurations. "
--   ::= { sm48tat4xarpBroadcastStormProtection 1 }
--
--sm48tat4xarpBroadcastStormProtectionConfigurationEntry OBJECT-TYPE
--   SYNTAX      SM48TAT4XARPBroadcastStormProtectionConfigurationEntry
--   MAX-ACCESS  not-accessible
--   STATUS      current
--   DESCRIPTION
--       ""
--   INDEX    { sm48tat4xarpBroadcastStormProtectionConfPort  }
--   ::= { sm48tat4xarpBroadcastStormProtectionConfigurationTable 1 }
--
--SM48TAT4XARPBroadcastStormProtectionConfigurationEntry ::= SEQUENCE {
--   sm48tat4xarpBroadcastStormProtectionConfPort	    Integer32,
--   sm48tat4xarpBroadcastStormProtectionConfMode	    INTEGER,
--   sm48tat4xarpBroadcastStormProtectionConfAction	Integer32,
--   sm48tat4xarpBroadcastStormProtectionConfPPS		Integer32,
--   sm48tat4xarpBroadcastStormProtectionConfTimer	Integer32,
--   sm48tat4xarpBroadcastStormProtectionConfstatus	DisplayString
--}
--
--sm48tat4xarpBroadcastStormProtectionConfPort OBJECT-TYPE
--   SYNTAX      Integer32 (1..4095)
--   MAX-ACCESS  not-accessible
--   STATUS      current
--   DESCRIPTION
--       " port, range : 1 - port number. "
--   ::= { sm48tat4xarpBroadcastStormProtectionConfigurationEntry 1 }
--
--sm48tat4xarpBroadcastStormProtectionConfMode OBJECT-TYPE
--   SYNTAX      INTEGER { disable(0), enable(1)}
--   MAX-ACCESS  read-write
--   STATUS      current
--   DESCRIPTION
--       " Configure broadcast storm protection port mode.
--         0: disable,
--         1: enable
--         default: disable. "
--   ::= { sm48tat4xarpBroadcastStormProtectionConfigurationEntry 2 }
--
--sm48tat4xarpBroadcastStormProtectionConfAction OBJECT-TYPE
--   SYNTAX      Integer32 (0..2)
--   MAX-ACCESS  read-write
--   STATUS      current
--   DESCRIPTION
--       " Configure broadcast storm protection port action.
--         0: Shutdown port,
--         1: Shutdown port and Log,
--         2: Log Only,
--         default: Shutdown port. "
--   ::= { sm48tat4xarpBroadcastStormProtectionConfigurationEntry 3 }
--
--sm48tat4xarpBroadcastStormProtectionConfPPS OBJECT-TYPE
--   SYNTAX      Integer32 (0..1000000)
--   MAX-ACCESS  read-write
--   STATUS      current
--   DESCRIPTION
--       " Configure broadcast storm protection pps.
--         default: 0. "
--   ::= { sm48tat4xarpBroadcastStormProtectionConfigurationEntry 4 }
--
--sm48tat4xarpBroadcastStormProtectionConfTimer OBJECT-TYPE
--   SYNTAX      Integer32 (0..65535)
--   MAX-ACCESS  read-write
--   STATUS      current
--   DESCRIPTION
--       "Configure broadcast storm protection timer(seconds)
--        default: 300(seconds). "
--   ::= { sm48tat4xarpBroadcastStormProtectionConfigurationEntry 5 }
--
--sm48tat4xarpBroadcastStormProtectionConfstatus OBJECT-TYPE
--   SYNTAX      DisplayString
--   MAX-ACCESS  read-only
--   STATUS      current
--   DESCRIPTION
--       " Show broadcast storm protection status. "
--   ::= { sm48tat4xarpBroadcastStormProtectionConfigurationEntry 6 }
--
-- =======================================================================================================================
sm48tat4xarpLoopProtection                                                  OBJECT IDENTIFIER ::= { sm48tat4xarpConfiguration 12 }

sm48tat4xarpLoopProtectionConfig                                            OBJECT IDENTIFIER ::= { sm48tat4xarpLoopProtection 1 }

sm48tat4xarpLoopProtectionGlobalEnable OBJECT-TYPE
   SYNTAX      Integer32(0|1)
   MAX-ACCESS  read-write
   STATUS      current
   DESCRIPTION
       "Configure loop protection mode.
        0: disable,
        1: enable,
        default: disable. "
   ::= { sm48tat4xarpLoopProtectionConfig 1 }

sm48tat4xarpLoopProtectionTranmisstionTime OBJECT-TYPE
   SYNTAX      Integer32(1..10)
   MAX-ACCESS  read-write
   STATUS      current
   DESCRIPTION
       "Configure loop protection transmit interval.
        default: 5,
        range: 1-10. "
   ::= { sm48tat4xarpLoopProtectionConfig 2 }

sm48tat4xarpLoopProtectionShutdownTime OBJECT-TYPE
   SYNTAX      Integer32(0..604800)
   MAX-ACCESS  read-write
   STATUS      current
   DESCRIPTION
       "Configure loop protection shutdown time.
        default: 180,
        range: 0-604800. "
   ::= { sm48tat4xarpLoopProtectionConfig 3 }

sm48tat4xarpLoopProtectionConfigurationTable OBJECT-TYPE
   SYNTAX      SEQUENCE OF SM48TAT4XARPLoopProtectionConfigurationEntry
   MAX-ACCESS  not-accessible
   STATUS      current
   DESCRIPTION
       " Show Loop Protection configurations. "
   ::= { sm48tat4xarpLoopProtectionConfig 4 }

sm48tat4xarpLoopProtectionConfigurationEntry OBJECT-TYPE
   SYNTAX      SM48TAT4XARPLoopProtectionConfigurationEntry
   MAX-ACCESS  not-accessible
   STATUS      current
   DESCRIPTION
       " "
   INDEX    { sm48tat4xarpLoopProtectionConfPort  }
   ::= { sm48tat4xarpLoopProtectionConfigurationTable 1 }

SM48TAT4XARPLoopProtectionConfigurationEntry ::= SEQUENCE {
   sm48tat4xarpLoopProtectionConfPort	    Integer32,
   sm48tat4xarpLoopProtectionConfEnable	Integer32,
   sm48tat4xarpLoopProtectionConfAction	Integer32,
   sm48tat4xarpLoopProtectionConfTxmode	Integer32
}

sm48tat4xarpLoopProtectionConfPort OBJECT-TYPE
   SYNTAX      Integer32 (1..4095)
   MAX-ACCESS  not-accessible
   STATUS      current
   DESCRIPTION
       " port, range : 1 - port number. "
   ::= { sm48tat4xarpLoopProtectionConfigurationEntry 1 }

sm48tat4xarpLoopProtectionConfEnable OBJECT-TYPE
   SYNTAX      Integer32(0|1)
   MAX-ACCESS  read-write
   STATUS      current
   DESCRIPTION
       "Configure loop protection port mode.
        0: disable,
        1: enable,
        default: enable. "
   ::= { sm48tat4xarpLoopProtectionConfigurationEntry 2 }

sm48tat4xarpLoopProtectionConfAction OBJECT-TYPE
   SYNTAX      Integer32(0..2)
   MAX-ACCESS  read-write
   STATUS      current
   DESCRIPTION
       " Configure loop protection port action.
         0: Shutdown port,
         1: Shutdown port and Log,
         2: Log Only,
         default: Shutdown port. "
   ::= { sm48tat4xarpLoopProtectionConfigurationEntry 3 }

sm48tat4xarpLoopProtectionConfTxmode OBJECT-TYPE
   SYNTAX      Integer32(0|1)
   MAX-ACCESS  read-write
   STATUS      current
   DESCRIPTION
       "Configure loop protection port transmit mode.
        0: disable,
        1: enable,
        default: enable. "
   ::= { sm48tat4xarpLoopProtectionConfigurationEntry 4 }

sm48tat4xarpLoopProtectionStatusTable OBJECT-TYPE
   SYNTAX      SEQUENCE OF SM48TAT4XARPLoopProtectionStatusEntry
   MAX-ACCESS  not-accessible
   STATUS      current
   DESCRIPTION
       " Show Loop Protection Status. "
   ::= { sm48tat4xarpLoopProtection 2 }

sm48tat4xarpLoopProtectionStatusEntry OBJECT-TYPE
   SYNTAX      SM48TAT4XARPLoopProtectionStatusEntry
   MAX-ACCESS  not-accessible
   STATUS      current
   DESCRIPTION
       " "
   INDEX    { sm48tat4xarpLoopProtectionStatusPort  }
   ::= { sm48tat4xarpLoopProtectionStatusTable 1 }

SM48TAT4XARPLoopProtectionStatusEntry ::= SEQUENCE {
   sm48tat4xarpLoopProtectionStatusPort	       Integer32,
   sm48tat4xarpLoopProtectionStatusAction	       DisplayString,
   sm48tat4xarpLoopProtectionStatusTransmit	   DisplayString,
   sm48tat4xarpLoopProtectionStatusLoops	       Integer32,
   sm48tat4xarpLoopProtectionStatusStatus	       DisplayString,
   sm48tat4xarpLoopProtectionStatusLoop	       DisplayString,
   sm48tat4xarpLoopProtectionStatusTimeLastLoop  DisplayString
}

sm48tat4xarpLoopProtectionStatusPort OBJECT-TYPE
   SYNTAX      Integer32 (1..4095)
   MAX-ACCESS  not-accessible
   STATUS      current
   DESCRIPTION
       " port, range : 1 - port number. "
   ::= { sm48tat4xarpLoopProtectionStatusEntry 1 }

sm48tat4xarpLoopProtectionStatusAction OBJECT-TYPE
   SYNTAX      DisplayString
   MAX-ACCESS  read-only
   STATUS      current
   DESCRIPTION
       " The currently configured port action. "
   ::= { sm48tat4xarpLoopProtectionStatusEntry 2 }

sm48tat4xarpLoopProtectionStatusTransmit OBJECT-TYPE
   SYNTAX      DisplayString
   MAX-ACCESS  read-only
   STATUS      current
   DESCRIPTION
       " The currently configured port transmit mode. "
   ::= { sm48tat4xarpLoopProtectionStatusEntry 3 }

sm48tat4xarpLoopProtectionStatusLoops OBJECT-TYPE
   SYNTAX      Integer32 (0..1000000)
   MAX-ACCESS  read-only
   STATUS      current
   DESCRIPTION
       " The number of loops detected on this port. "
   ::= { sm48tat4xarpLoopProtectionStatusEntry 4 }

sm48tat4xarpLoopProtectionStatusStatus OBJECT-TYPE
   SYNTAX      DisplayString
   MAX-ACCESS  read-only
   STATUS      current
   DESCRIPTION
       " The current loop protection status of the port. "
   ::= { sm48tat4xarpLoopProtectionStatusEntry 5 }

sm48tat4xarpLoopProtectionStatusLoop OBJECT-TYPE
   SYNTAX      DisplayString
   MAX-ACCESS  read-only
   STATUS      current
   DESCRIPTION
       " Whether a loop is currently detected on the port. "
   ::= { sm48tat4xarpLoopProtectionStatusEntry 6 }

sm48tat4xarpLoopProtectionStatusTimeLastLoop OBJECT-TYPE
   SYNTAX      DisplayString
   MAX-ACCESS  read-only
   STATUS      current
   DESCRIPTION
       " The time of the last loop event detected. "
   ::= { sm48tat4xarpLoopProtectionStatusEntry 7 }
-- =======================================================================================================================
sm48tat4xarpPoe                                                           OBJECT IDENTIFIER ::= { sm48tat4xarpConfiguration 13 }

sm48tat4xarpPoeStatus                                            OBJECT IDENTIFIER ::= { sm48tat4xarpPoe 1 }

sm48tat4xarpPoeStatusTable OBJECT-TYPE
   SYNTAX      SEQUENCE OF SM48TAT4XARPPoeStatusEntry
   MAX-ACCESS  not-accessible
   STATUS      current
   DESCRIPTION
       " Configure PoE Scheduling Table. "
   ::= { sm48tat4xarpPoeStatus 1 }

sm48tat4xarpPoeStatusEntry OBJECT-TYPE
   SYNTAX      SM48TAT4XARPPoeStatusEntry
   MAX-ACCESS  not-accessible
   STATUS      current
   DESCRIPTION
       " "
   INDEX    { sm48tat4xarpPoeStatusLocalPort }
   ::= { sm48tat4xarpPoeStatusTable 1 }

SM48TAT4XARPPoeStatusEntry ::= SEQUENCE {
   sm48tat4xarpPoeStatusLocalPort              Integer32,
   sm48tat4xarpPoeStatusPDclass	          DisplayString,
   sm48tat4xarpPoeStatusPowerRequested	  DisplayString,
   sm48tat4xarpPoeStatusPowerAllocated     DisplayString,
   sm48tat4xarpPoeStatusPowerUsed          DisplayString,
   sm48tat4xarpPoeStatusCurrentUsed        DisplayString,
   sm48tat4xarpPoeStatusPriority           DisplayString,
   sm48tat4xarpPoeStatusPortStatus         DisplayString
}

sm48tat4xarpPoeStatusLocalPort OBJECT-TYPE
   SYNTAX      Integer32 (1..10)
   MAX-ACCESS  not-accessible
   STATUS      current
   DESCRIPTION
       "Local port Index."
   ::= { sm48tat4xarpPoeStatusEntry 1 }


sm48tat4xarpPoeStatusPDclass OBJECT-TYPE
   SYNTAX      DisplayString
   MAX-ACCESS  read-only
   STATUS      current
   DESCRIPTION
       " Indicates the QCL user.
         0: Max. power 15.4 W,
         1: Max. power 4.0 W,
         2: Max. power 7.0 W,
         3: Max. power 15.4 W,
         4: Max. power 30.0 W. "
   ::= { sm48tat4xarpPoeStatusEntry 2 }

sm48tat4xarpPoeStatusPowerRequested OBJECT-TYPE
   SYNTAX      DisplayString
   MAX-ACCESS  read-only
   STATUS      current
   DESCRIPTION
      " The Power Requested shows the requested amount of power the PD wants to be reserved. "
   ::= { sm48tat4xarpPoeStatusEntry 3}

sm48tat4xarpPoeStatusPowerAllocated OBJECT-TYPE
   SYNTAX      DisplayString
   MAX-ACCESS  read-only
   STATUS      current
   DESCRIPTION
      " The Power Allocated shows the amount of power the switch has allocated for the PD. "
   ::= { sm48tat4xarpPoeStatusEntry 4}

sm48tat4xarpPoeStatusPowerUsed OBJECT-TYPE
   SYNTAX      DisplayString
   MAX-ACCESS  read-only
   STATUS      current
   DESCRIPTION
      " The Power Used shows how much power the PD currently is using. "
   ::= { sm48tat4xarpPoeStatusEntry 5}

sm48tat4xarpPoeStatusCurrentUsed OBJECT-TYPE
   SYNTAX      DisplayString
   MAX-ACCESS  read-only
   STATUS      current
   DESCRIPTION
      " The Power Used shows how much current the PD currently is using. "
   ::= { sm48tat4xarpPoeStatusEntry 6}

sm48tat4xarpPoeStatusPriority OBJECT-TYPE
   SYNTAX      DisplayString
   MAX-ACCESS  read-only
   STATUS      current
   DESCRIPTION
      " The Priority shows the port's priority configured by the user.  "
   ::= { sm48tat4xarpPoeStatusEntry 7}

sm48tat4xarpPoeStatusPortStatus OBJECT-TYPE
   SYNTAX      DisplayString
   MAX-ACCESS  read-only
   STATUS      current
   DESCRIPTION
      " The Port Status shows the port's status.  "
   ::= { sm48tat4xarpPoeStatusEntry 8}

sm48tat4xarpPoeStatusTotalTable OBJECT-TYPE
   SYNTAX      SEQUENCE OF SM48TAT4XARPPoeStatusTotalEntry
   MAX-ACCESS  not-accessible
   STATUS      current
   DESCRIPTION
       " Configure PoE Scheduling Total Table. "
   ::= { sm48tat4xarpPoeStatus 2 }

sm48tat4xarpPoeStatusTotalEntry OBJECT-TYPE
   SYNTAX      SM48TAT4XARPPoeStatusTotalEntry
   MAX-ACCESS  not-accessible
   STATUS      current
   DESCRIPTION
       " "
   INDEX    { sm48tat4xarpPoeStatusSwitchIndex }
   ::= { sm48tat4xarpPoeStatusTotalTable 1 }

SM48TAT4XARPPoeStatusTotalEntry ::= SEQUENCE {
   sm48tat4xarpPoeStatusSwitchIndex            Integer32,
   sm48tat4xarpPoeStatusTotalPowerRequested    DisplayString,
   sm48tat4xarpPoeStatusTotalPowerAllocated    DisplayString,
   sm48tat4xarpPoeStatusTotalPowerUsed         DisplayString,
   sm48tat4xarpPoeStatusTotalCurrentUsed       DisplayString
}

sm48tat4xarpPoeStatusSwitchIndex OBJECT-TYPE
   SYNTAX      Integer32 (1..16)
   MAX-ACCESS  not-accessible
   STATUS      current
   DESCRIPTION
       "Switch Index."
   ::= { sm48tat4xarpPoeStatusTotalEntry 1 }

sm48tat4xarpPoeStatusTotalPowerRequested OBJECT-TYPE
   SYNTAX      DisplayString
   MAX-ACCESS  read-only
   STATUS      current
   DESCRIPTION
      " Total Power Requested."
   ::= { sm48tat4xarpPoeStatusTotalEntry 2}

sm48tat4xarpPoeStatusTotalPowerAllocated OBJECT-TYPE
   SYNTAX      DisplayString
   MAX-ACCESS  read-only
   STATUS      current
   DESCRIPTION
      " Total Power allocated."
   ::= { sm48tat4xarpPoeStatusTotalEntry 3}

sm48tat4xarpPoeStatusTotalPowerUsed OBJECT-TYPE
   SYNTAX      DisplayString
   MAX-ACCESS  read-only
   STATUS      current
   DESCRIPTION
      " Total Power Used."
   ::= { sm48tat4xarpPoeStatusTotalEntry 4}

sm48tat4xarpPoeStatusTotalCurrentUsed OBJECT-TYPE
   SYNTAX      DisplayString
   MAX-ACCESS  read-only
   STATUS      current
   DESCRIPTION
      " Total Current Used."
   ::= { sm48tat4xarpPoeStatusTotalEntry 5}


sm48tat4xarpPoePowerDelay                                                 OBJECT IDENTIFIER ::= { sm48tat4xarpPoe 2 }

sm48tat4xarpPoePowerDelayTable OBJECT-TYPE
   SYNTAX      SEQUENCE OF SM48TAT4XARPPoePowerDelayEntry
   MAX-ACCESS  not-accessible
   STATUS      current
   DESCRIPTION
       " Configure PoE Power Delay mode. "
   ::= { sm48tat4xarpPoePowerDelay 1 }

sm48tat4xarpPoePowerDelayEntry OBJECT-TYPE
   SYNTAX      SM48TAT4XARPPoePowerDelayEntry
   MAX-ACCESS  not-accessible
   STATUS      current
   DESCRIPTION
       " "
   INDEX    { sm48tat4xarpPoePowerDelayPort  }
   ::= { sm48tat4xarpPoePowerDelayTable 1 }

SM48TAT4XARPPoePowerDelayEntry ::= SEQUENCE {
   sm48tat4xarpPoePowerDelayPort	        Integer32,
   sm48tat4xarpPoePowerDelayMode	        Integer32,
   sm48tat4xarpPoePowerDelayTime	        Integer32
}

sm48tat4xarpPoePowerDelayPort OBJECT-TYPE
   SYNTAX      Integer32 (1..4094)
   MAX-ACCESS  not-accessible
   STATUS      current
   DESCRIPTION
       " port, range : 1 - port number. "
   ::= { sm48tat4xarpPoePowerDelayEntry 1 }

sm48tat4xarpPoePowerDelayMode OBJECT-TYPE
   SYNTAX      Integer32(0|1)
   MAX-ACCESS  read-write
   STATUS      current
   DESCRIPTION
       "Turn on / off the power delay function,
        0: disable,
        1: enable,
        default: disable. "
   ::= { sm48tat4xarpPoePowerDelayEntry 2 }

sm48tat4xarpPoePowerDelayTime OBJECT-TYPE
   SYNTAX      Integer32(0..300)
   MAX-ACCESS  read-write
   STATUS      current
   DESCRIPTION
       "set Delay Time,
        default: 0,
        range: 0-300 sec. "
   ::= { sm48tat4xarpPoePowerDelayEntry 3 }

sm48tat4xarpPoeAutoPowerReset                                                 OBJECT IDENTIFIER ::= { sm48tat4xarpPoe 3 }

sm48tat4xarpPoeAutoPowerResetPingCheck OBJECT-TYPE
   SYNTAX      INTEGER { disable(0), enable(1) }
   MAX-ACCESS  read-write
   STATUS      current
   DESCRIPTION
       "connection between PoE port and power device.
        0: disable,
        1: enable,
        default: disable. "
   ::= { sm48tat4xarpPoeAutoPowerReset 1 }

sm48tat4xarpPoeAutoPowerResetTable OBJECT-TYPE
   SYNTAX      SEQUENCE OF SM48TAT4XARPPoeAutoPowerResetEntry
   MAX-ACCESS  not-accessible
   STATUS      current
   DESCRIPTION
       " Configure PoE Auto Power Reset mode. "
   ::= { sm48tat4xarpPoeAutoPowerReset 2 }

sm48tat4xarpPoeAutoPowerResetEntry OBJECT-TYPE
   SYNTAX      SM48TAT4XARPPoeAutoPowerResetEntry
   MAX-ACCESS  not-accessible
   STATUS      current
   DESCRIPTION
       " "
   INDEX    { sm48tat4xarpPoeAutoPowerResetPort  }
   ::= { sm48tat4xarpPoeAutoPowerResetTable 1 }

SM48TAT4XARPPoeAutoPowerResetEntry ::= SEQUENCE {
   sm48tat4xarpPoeAutoPowerResetPort	   Integer32,
   sm48tat4xarpPoeAutoPowerResetPingIPAddress  DisplayString,
   sm48tat4xarpPoeAutoPowerResetStartupTime    Integer32,
   sm48tat4xarpPoeAutoPowerResetIntervalTime   Integer32,
   sm48tat4xarpPoeAutoPowerResetRetryTime      Integer32,
   sm48tat4xarpPoeAutoPowerResetFailureLog     DisplayString,
   sm48tat4xarpPoeAutoPowerResetFailureAction  INTEGER,
   sm48tat4xarpPoeAutoPowerResetRebootTime     Integer32,
   sm48tat4xarpPoeAutoPowerResetMaxRebootTimes     Integer32
}

sm48tat4xarpPoeAutoPowerResetPort OBJECT-TYPE
   SYNTAX      Integer32(1..4094)
   MAX-ACCESS  not-accessible
   STATUS      current
   DESCRIPTION
       " port, range : 1 - port number. "
   ::= { sm48tat4xarpPoeAutoPowerResetEntry 1 }

sm48tat4xarpPoeAutoPowerResetPingIPAddress OBJECT-TYPE
   SYNTAX      DisplayString
   MAX-ACCESS  read-write
   STATUS      current
   DESCRIPTION
       "IP Address the system should ping.
        default: 0.0.0.0 . "
   ::= { sm48tat4xarpPoeAutoPowerResetEntry 2 }

sm48tat4xarpPoeAutoPowerResetStartupTime OBJECT-TYPE
   SYNTAX      Integer32(30..600)
   MAX-ACCESS  read-write
   STATUS      current
   DESCRIPTION
       "When PD has been start up, the Switch will wait Start up time to do PoE Auto Checking. default: 60, range: 30-600 sec. "
   ::= { sm48tat4xarpPoeAutoPowerResetEntry 3 }

sm48tat4xarpPoeAutoPowerResetIntervalTime OBJECT-TYPE
   SYNTAX      Integer32(10..120)
   MAX-ACCESS  read-write
   STATUS      current
   DESCRIPTION
       "Device will send checking message to PD each interval time.
        default: 30,
        range: 10-120 sec.  "
   ::= { sm48tat4xarpPoeAutoPowerResetEntry 4 }

sm48tat4xarpPoeAutoPowerResetRetryTime OBJECT-TYPE
   SYNTAX      Integer32(1..5)
   MAX-ACCESS  read-write
   STATUS      current
   DESCRIPTION
       "It will retry to send detection again.
        default: 3,
        range: 1-5.  "
   ::= { sm48tat4xarpPoeAutoPowerResetEntry 5 }

sm48tat4xarpPoeAutoPowerResetFailureLog OBJECT-TYPE
   SYNTAX      DisplayString
   MAX-ACCESS  read-only
   STATUS      current
   DESCRIPTION
       "Failure loggings counter. "
   ::= { sm48tat4xarpPoeAutoPowerResetEntry 6 }

sm48tat4xarpPoeAutoPowerResetFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { sm48tat4xarpPoeAutoPowerResetEntry 7 }

sm48tat4xarpPoeAutoPowerResetRebootTime OBJECT-TYPE
   SYNTAX      Integer32(3..120)
   MAX-ACCESS  read-write
   STATUS      current
   DESCRIPTION
       "When PD has been rebooted, the PoE port restored power after the specified time.
        default: 15,
        range: 3-120 sec. "
   ::= { sm48tat4xarpPoeAutoPowerResetEntry 8 }

sm48tat4xarpPoeAutoPowerResetMaxRebootTimes OBJECT-TYPE
   SYNTAX      Integer32(0..10)
   MAX-ACCESS  read-write
   STATUS      current
   DESCRIPTION
        "When Failure Action is Reboot Remote PD, it limits times of Reboot.
         default: 3,
         range: 0-10. 0 means without reboot limits."
   ::= { sm48tat4xarpPoeAutoPowerResetEntry 10 }

sm48tat4xarpPoeScheduling                                                 OBJECT IDENTIFIER ::= { sm48tat4xarpPoe 4 }

sm48tat4xarpPoeSchedulingProfileNumber OBJECT-TYPE
   SYNTAX      Integer32
   MAX-ACCESS  read-write
   STATUS      current
   DESCRIPTION
       "Specify the PoE Profile Number that want to configure. Range:1-16"
   ::= { sm48tat4xarpPoeScheduling 1 }

sm48tat4xarpPoeSchedulingPorofileName OBJECT-TYPE
   SYNTAX      DisplayString
   MAX-ACCESS  read-write
   STATUS      current
   DESCRIPTION
       "Profile Name. Maximum length:32."
   ::= { sm48tat4xarpPoeScheduling 2 }

sm48tat4xarpPoeSchedulingTimeTable OBJECT-TYPE
   SYNTAX      SEQUENCE OF SM48TAT4XARPPoeSchedulingTimeEntry
   MAX-ACCESS  not-accessible
   STATUS      current
   DESCRIPTION
       " Show Poe Scheduling Time Config. "
   ::= { sm48tat4xarpPoeScheduling 3 }

sm48tat4xarpPoeSchedulingTimeEntry OBJECT-TYPE
   SYNTAX      SM48TAT4XARPPoeSchedulingTimeEntry
   MAX-ACCESS  not-accessible
   STATUS      current
   DESCRIPTION
       " "
   INDEX    { sm48tat4xarpPoeSchedulingTimeWeekIndex  }
   ::= { sm48tat4xarpPoeSchedulingTimeTable 1 }

SM48TAT4XARPPoeSchedulingTimeEntry ::= SEQUENCE {
   sm48tat4xarpPoeSchedulingTimeWeekIndex        Integer32,
   sm48tat4xarpPoeSchedulingTimeStartTimeHourMinute  DisplayString,
   sm48tat4xarpPoeSchedulingTimeEndTimeHourMinute    DisplayString
}

sm48tat4xarpPoeSchedulingTimeWeekIndex OBJECT-TYPE
   SYNTAX      Integer32 (1..7)
   MAX-ACCESS  not-accessible
   STATUS      current
   DESCRIPTION
       "Week Index.
	   1: Mon, 2:Tue, 3: Wed, 4: Thu, 5: Fri, 6: Sat, 7: Sun"
   ::= { sm48tat4xarpPoeSchedulingTimeEntry 1 }

sm48tat4xarpPoeSchedulingTimeStartTimeHourMinute OBJECT-TYPE
   SYNTAX      DisplayString
   MAX-ACCESS  read-write
   STATUS      current
   DESCRIPTION
       "PoE Scheduling Start Time. Format: HH:MM. Hour Range: 0-23. Minute Range:0,5,10,...,55."
   ::= { sm48tat4xarpPoeSchedulingTimeEntry 2 }

sm48tat4xarpPoeSchedulingTimeEndTimeHourMinute OBJECT-TYPE
   SYNTAX      DisplayString
   MAX-ACCESS  read-write
   STATUS      current
   DESCRIPTION
       "PoE Scheduling End Time. Format: HH:MM. Hour Range: 0-23. Minute Range:0,5,10,...,55."
   ::= { sm48tat4xarpPoeSchedulingTimeEntry 3 }

sm48tat4xarpPoeConfiguration                                                 OBJECT IDENTIFIER ::= { sm48tat4xarpPoe 5 }

sm48tat4xarpPoeConfigurationPowerManagementMode OBJECT-TYPE
   SYNTAX      Integer32(0..5)
   MAX-ACCESS  read-write
   STATUS      current
   DESCRIPTION
       "The power management mode for PoE port.
        0: CLASS_RESERVED,
        1: CLASS_CONSUMP,
        2: ALLOCATED_RESERVED,
        3: ALLOCATED_CONSUMP,
        4: LLDPMED_RESERVED,
        5: LLDPMED_CONSUMP,
        default: CLASS_RESERVED. "
   ::= { sm48tat4xarpPoeConfiguration 1 }

sm48tat4xarpPoeConfigurationCapacitorDetection OBJECT-TYPE
   SYNTAX      Integer32(0..1)
   MAX-ACCESS  read-write
   STATUS      current
   DESCRIPTION
       "The capacitor detection mode.
        0: Disable
        1: Enable
       "
   ::= { sm48tat4xarpPoeConfiguration 2 }

sm48tat4xarpPoeConfigurationTable OBJECT-TYPE
   SYNTAX      SEQUENCE OF SM48TAT4XARPPoeConfigurationEntry
   MAX-ACCESS  not-accessible
   STATUS      current
   DESCRIPTION
       " Configure PoE Configuration mode. "
   ::= { sm48tat4xarpPoeConfiguration 4 }

sm48tat4xarpPoeConfigurationEntry OBJECT-TYPE
   SYNTAX      SM48TAT4XARPPoeConfigurationEntry
   MAX-ACCESS  not-accessible
   STATUS      current
   DESCRIPTION
       " "
   INDEX    { sm48tat4xarpPoeConfigurationSwitch  }
   ::= { sm48tat4xarpPoeConfigurationTable 1 }

SM48TAT4XARPPoeConfigurationEntry ::= SEQUENCE {
   sm48tat4xarpPoeConfigurationSwitch	                   Integer32,
   sm48tat4xarpPoeConfigurationPrimaryPowerSupply        Integer32,
   sm48tat4xarpPoeConfigurationAlwaysOnPoE        Integer32
}

sm48tat4xarpPoeConfigurationSwitch OBJECT-TYPE
   SYNTAX      Integer32 (1..16)
   MAX-ACCESS  not-accessible
   STATUS      current
   DESCRIPTION
       " switch index, range : 1 - 16. "
   ::= { sm48tat4xarpPoeConfigurationEntry 1 }

sm48tat4xarpPoeConfigurationPrimaryPowerSupply  OBJECT-TYPE
   SYNTAX      Integer32(0..2000)
   MAX-ACCESS  read-only
   STATUS      current
   DESCRIPTION
       "It must be defined what amount of power the primary and backup power sources
        can deliver. "
   ::= { sm48tat4xarpPoeConfigurationEntry 3 }

sm48tat4xarpPoeConfigurationAlwaysOnPoE  OBJECT-TYPE
   SYNTAX      Integer32(0..1)
   MAX-ACCESS  read-write
   STATUS      current
   DESCRIPTION
       "Configure always-on-poe"
   ::= { sm48tat4xarpPoeConfigurationEntry 4 }

sm48tat4xarpPoeConfigurationPortTable OBJECT-TYPE
   SYNTAX      SEQUENCE OF SM48TAT4XARPPoeConfigurationPortEntry
   MAX-ACCESS  not-accessible
   STATUS      current
   DESCRIPTION
       " Configure PoE Port Configuration mode. "
   ::= { sm48tat4xarpPoeConfiguration 5 }

sm48tat4xarpPoeConfigurationPortEntry OBJECT-TYPE
   SYNTAX      SM48TAT4XARPPoeConfigurationPortEntry
   MAX-ACCESS  not-accessible
   STATUS      current
   DESCRIPTION
       " "
   INDEX    { sm48tat4xarpPoeConfigurationPort  }
   ::= { sm48tat4xarpPoeConfigurationPortTable 1 }

SM48TAT4XARPPoeConfigurationPortEntry ::= SEQUENCE {
   sm48tat4xarpPoeConfigurationPort	       Integer32,
   sm48tat4xarpPoeConfigurationPortPoEMode       INTEGER,
   sm48tat4xarpPoeConfigurationPortPriority      INTEGER,
   sm48tat4xarpPoeConfigurationPortMaximumPower  DisplayString,
   sm48tat4xarpPoeConfigurationPortDetection     Integer32,
-- sm48tat4xarpPoeConfigurationPortPoEScheduleByProfileID     Integer32,
   sm48tat4xarpPoeConfigurationPortPoEScheduleByProfileName   DisplayString,
   sm48tat4xarpPoeConfigurationPortDelayMode     Integer32,
   sm48tat4xarpPoeConfigurationPortDelayTime     Integer32
}

sm48tat4xarpPoeConfigurationPort OBJECT-TYPE
   SYNTAX      Integer32(1..65535)
   MAX-ACCESS  not-accessible
   STATUS      current
   DESCRIPTION
       " port, range : 1 - port number. "
   ::= { sm48tat4xarpPoeConfigurationPortEntry 1 }

sm48tat4xarpPoeConfigurationPortPoEMode OBJECT-TYPE
   SYNTAX      INTEGER { disable(0), poe(1) , poeforce(3) }
   MAX-ACCESS  read-write
   STATUS      current
   DESCRIPTION
       "The PoE Mode represents the PoE operating mode for the port.
        0: Disable,
        1: Enable,
		3: Force,
        default: Enable. "
   ::= { sm48tat4xarpPoeConfigurationPortEntry 2 }

sm48tat4xarpPoeConfigurationPortPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { sm48tat4xarpPoeConfigurationPortEntry 3 }

sm48tat4xarpPoeConfigurationPortMaximumPower OBJECT-TYPE
   SYNTAX      DisplayString
   MAX-ACCESS  read-write
   STATUS      current
   DESCRIPTION
       "The Maximum Power value contains a numerical value that indicates the maximum
        power in watts that can be delivered to a remote device.
        max: 30[W]. "
   ::= { sm48tat4xarpPoeConfigurationPortEntry 4 }

sm48tat4xarpPoeConfigurationPortDetection OBJECT-TYPE
   SYNTAX      Integer32(1..5)
   MAX-ACCESS  read-write
   STATUS      current
   DESCRIPTION
       "The Detection represents the PoE capacitor detection for the port.
	      -1:Not support.
	   1:Legacy : Legacy capacitive detection only.
	   2:4-point : IEEE 802.3af 4-point detection only.
	   3:4-point-legacy : IEEE 802.3af 4-point detection followed by Legacy detection.
	   4:2-point : IEEE 802.3af 2-point detection only.
	   5:2-point-legacy : IEEE 802.3af 2-point detection followed by Legacy detection.
	   "
   ::= { sm48tat4xarpPoeConfigurationPortEntry 5 }

-- sm48tat4xarpPoeConfigurationPortPoEScheduleByProfileID OBJECT-TYPE
--   SYNTAX      Integer32(0..16)
--   MAX-ACCESS  read-write
--   STATUS      current
--   DESCRIPTION
--       "Specify a valid PoE schedule profile by profile id. 0:disable,1-16:1-16 profile."
--   ::= { sm48tat4xarpPoeConfigurationPortEntry 6 }

sm48tat4xarpPoeConfigurationPortPoEScheduleByProfileName OBJECT-TYPE
   SYNTAX      DisplayString
   MAX-ACCESS  read-write
   STATUS      current
   DESCRIPTION
       "Specify a valid PoE schedule profile by profile name. disabled: disable profile schedule."
   ::= { sm48tat4xarpPoeConfigurationPortEntry 7 }

sm48tat4xarpPoeConfigurationPortDelayMode OBJECT-TYPE
   SYNTAX      Integer32(0..1)
   MAX-ACCESS  read-write
   STATUS      current
   DESCRIPTION
       "Turn on off the power delay function.
	   0: Disable
        1: Enable"
   ::= { sm48tat4xarpPoeConfigurationPortEntry 8 }

sm48tat4xarpPoeConfigurationPortDelayTime OBJECT-TYPE
   SYNTAX      Integer32(0..300)
   MAX-ACCESS  read-write
   STATUS      current
   DESCRIPTION
       "When rebooting, the PoE port will start to provide power to the PD when it out of delay time.
	   Range:0-300"
   ::= { sm48tat4xarpPoeConfigurationPortEntry 9 }

sm48tat4xarpPoeChipsetRebootSchedule OBJECT IDENTIFIER ::= { sm48tat4xarpPoe 6 }

sm48tat4xarpPoeChipsetRebootMode OBJECT-TYPE
   SYNTAX      Integer32
   MAX-ACCESS  read-write
   STATUS      current
   DESCRIPTION
       "PoE Chipset Reboot Mode
	    0:disable
		1:enable"
   ::= { sm48tat4xarpPoeChipsetRebootSchedule 1 }

sm48tat4xarpPoeChipsetRebootTimeTable OBJECT-TYPE
   SYNTAX      SEQUENCE OF SM48TAT4XARPPoeChipsetRebootTimeEntry
   MAX-ACCESS  not-accessible
   STATUS      current
   DESCRIPTION
       " Configure PoE Chipset Reboot Time."
   ::= { sm48tat4xarpPoeChipsetRebootSchedule 2 }

sm48tat4xarpPoeChipsetRebootTimeEntry OBJECT-TYPE
   SYNTAX      SM48TAT4XARPPoeChipsetRebootTimeEntry
   MAX-ACCESS  not-accessible
   STATUS      current
   DESCRIPTION
       " "
   INDEX    { sm48tat4xarpPoeChipsetRebootWeekIndex  }
   ::= { sm48tat4xarpPoeChipsetRebootTimeTable 1 }

SM48TAT4XARPPoeChipsetRebootTimeEntry ::= SEQUENCE {
   sm48tat4xarpPoeChipsetRebootWeekIndex	       Integer32,
   sm48tat4xarpPoeChipsetRebootTimeHour           Integer32,
   sm48tat4xarpPoeChipsetRebootTimeMinute         Integer32
}

sm48tat4xarpPoeChipsetRebootWeekIndex OBJECT-TYPE
   SYNTAX      Integer32 (1..7)
   MAX-ACCESS  not-accessible
   STATUS      current
   DESCRIPTION
       "PoE chipset reboot week index.
	   1: Mon, 2:Tue, 3: Wed, 4: Thu, 5: Fri, 6: Sat, 7: Sun"
   ::= { sm48tat4xarpPoeChipsetRebootTimeEntry 1 }

sm48tat4xarpPoeChipsetRebootTimeHour OBJECT-TYPE
   SYNTAX      Integer32 (-1..23)
   MAX-ACCESS  read-write
   STATUS      current
   DESCRIPTION
       "PoE Chipset Reboot Time (Hour). Range: 0-23.
	   -1:disable"
   ::= { sm48tat4xarpPoeChipsetRebootTimeEntry 2 }

sm48tat4xarpPoeChipsetRebootTimeMinute OBJECT-TYPE
   SYNTAX      Integer32 (-1..55)
   MAX-ACCESS  read-write
   STATUS      current
   DESCRIPTION
       "PoE Chipset Reboot Time (Minute). Range:0,5,10,...,55.
	   -1:disable"
   ::= { sm48tat4xarpPoeChipsetRebootTimeEntry 3 }

-- =======================================================================================================================
-- RowStatus Info:  createAndWait, notReady, notInService not supported.
-- =======================================================================================================================
-- Textual Conventions for the sm48tat4xarp AAA Mib
-- =======================================================================================================================
--
sm48tat4xarpAAAMIB                   OBJECT IDENTIFIER  ::= { sm48tat4xarpConfiguration 15 }
    sm48tat4xarpAAA                  OBJECT IDENTIFIER  ::= { sm48tat4xarpAAAMIB 1 }
    sm48tat4xarpRADIUS               OBJECT IDENTIFIER  ::= { sm48tat4xarpAAA 1 }
    sm48tat4xarpRADIUSGlobalConfig   OBJECT IDENTIFIER  ::= { sm48tat4xarpRADIUS 1 }

    sm48tat4xarpTACACS               OBJECT IDENTIFIER  ::= { sm48tat4xarpAAA 2 }

--
-- =======================================================================================================================
-- Start sm48tat4xarpRADIUS group
-- =======================================================================================================================
--sm48tat4xarpRADIUSGlobalConfig

    sm48tat4xarpRADIUSGlobalConfigTimeout OBJECT-TYPE
               SYNTAX      Integer32(1..1000)
               MAX-ACCESS  read-write
               STATUS      current
               DESCRIPTION
                   "Timeout is the number of seconds, to wait for a reply
                    from a RADIUS server before retransmitting the request.
                    range: 1-1000."
               ::= {     sm48tat4xarpRADIUSGlobalConfig 1 }

    sm48tat4xarpRADIUSGlobalConfigRetransmit OBJECT-TYPE
               SYNTAX      Integer32(1..1000)
               MAX-ACCESS  read-write
               STATUS      current
               DESCRIPTION
                   "Retransmit is the number of times,a RADIUS request is
                    retransmitted to a server that is not responding.If the
                    server has not responded after the last retransmit it is
                    considered to be dead.
                    range: 1-1000."
               ::= {     sm48tat4xarpRADIUSGlobalConfig 2 }

    sm48tat4xarpRADIUSGlobalConfigDeadtime OBJECT-TYPE
               SYNTAX      Integer32(0..1440)
               MAX-ACCESS  read-write
               STATUS      current
               DESCRIPTION
                   "This will stop the switch from continually trying to
                    contact a server that it has already determined as dead.
                    range: 0-1440."
               ::= {     sm48tat4xarpRADIUSGlobalConfig 3 }

    sm48tat4xarpRADIUSGlobalConfigKey OBJECT-TYPE
               SYNTAX      DisplayString
               MAX-ACCESS  read-write
               STATUS      current
               DESCRIPTION
                   "The secret key shared between the RADIUS server and
                    the switch."
               ::= {     sm48tat4xarpRADIUSGlobalConfig 4 }

    sm48tat4xarpRADIUSGlobalConfigNASIPv4 OBJECT-TYPE
               SYNTAX      IpAddress
               MAX-ACCESS  read-write
               STATUS      current
               DESCRIPTION
                   "The IPv4 address to be used as attribute 4 in RADIUS
                    Access-Request packets."
               ::= {     sm48tat4xarpRADIUSGlobalConfig 5 }

    sm48tat4xarpRADIUSGlobalConfigNASIPv6 OBJECT-TYPE
               SYNTAX      DisplayString
               MAX-ACCESS  read-write
               STATUS      current
               DESCRIPTION
                   "The IPv6 address to be used as attribute 95 in RADIUS
                    Access-Request packets. "
               ::= {     sm48tat4xarpRADIUSGlobalConfig 6 }

    sm48tat4xarpRADIUSGlobalConfigNASIdentifier OBJECT-TYPE
               SYNTAX      DisplayString
               MAX-ACCESS  read-write
               STATUS      current
               DESCRIPTION
                   "The identifier to be used as attribute 32 in RADIUS
                    Access-Request packets. "
               ::= {     sm48tat4xarpRADIUSGlobalConfig 7 }

--sm48tat4xarpRADIUSServerConfigTable

    sm48tat4xarpRADIUSServerConfigTable OBJECT-TYPE
               SYNTAX      SEQUENCE OF     SM48TAT4XARPRADIUSServerConfigEntry
               MAX-ACCESS  not-accessible
               STATUS      current
               DESCRIPTION
                   "The RADIUS Server Configuration Table."
               ::= {     sm48tat4xarpRADIUS 2 }

    sm48tat4xarpRADIUSServerConfigEntry OBJECT-TYPE
               SYNTAX          SM48TAT4XARPRADIUSServerConfigEntry
               MAX-ACCESS  not-accessible
               STATUS      current
               DESCRIPTION
                   "The RADIUS Server Configuration Entry."
               INDEX    {    sm48tat4xarpRADIUSServerConfServerNo  }
               ::= {     sm48tat4xarpRADIUSServerConfigTable 1 }

    SM48TAT4XARPRADIUSServerConfigEntry             ::= SEQUENCE {
                 sm48tat4xarpRADIUSServerConfServerNo      Integer32,
                 sm48tat4xarpRADIUSServerConfHostname      DisplayString,
                 sm48tat4xarpRADIUSServerConfAuthPort      Integer32,
                 sm48tat4xarpRADIUSServerConfAcctPort      Integer32,
                 sm48tat4xarpRADIUSServerConfTimeout       Integer32,
                 sm48tat4xarpRADIUSServerConfRetransmit    Integer32,
                 sm48tat4xarpRADIUSServerConfKey           DisplayString,
                 sm48tat4xarpRADIUSServerConfRowStatus     RowStatus
                 }

    sm48tat4xarpRADIUSServerConfServerNo OBJECT-TYPE
               SYNTAX      Integer32(1..5)
               MAX-ACCESS  not-accessible
               STATUS      current
               DESCRIPTION
                   "The RADIUS server number.
                    max: 5."
               ::= {     sm48tat4xarpRADIUSServerConfigEntry 1 }

    sm48tat4xarpRADIUSServerConfHostname OBJECT-TYPE
               SYNTAX      DisplayString
               MAX-ACCESS  read-create
               STATUS      current
               DESCRIPTION
                   "The IP address or hostname of the RADIUS server. "
               ::= {     sm48tat4xarpRADIUSServerConfigEntry 2 }

    sm48tat4xarpRADIUSServerConfAuthPort OBJECT-TYPE
               SYNTAX      Integer32(0..65535)
               MAX-ACCESS  read-create
               STATUS      current
               DESCRIPTION
                   "The UDP port to use on the RADIUS server for
                    authentication.
                    range: 0-65535. "
               ::= {     sm48tat4xarpRADIUSServerConfigEntry 3 }

    sm48tat4xarpRADIUSServerConfAcctPort OBJECT-TYPE
               SYNTAX      Integer32(0..65535)
               MAX-ACCESS  read-create
               STATUS      current
               DESCRIPTION
                   "The UDP port to use on the RADIUS server for accounting.
                    range: 0-65535. "
               ::= {     sm48tat4xarpRADIUSServerConfigEntry 4 }

    sm48tat4xarpRADIUSServerConfTimeout OBJECT-TYPE
               SYNTAX      Integer32(1..1000)
               MAX-ACCESS  read-create
               STATUS      current
               DESCRIPTION
                   "This optional setting overrides the global timeout value.
                    Leaving it blank will use the global timeout value.
                    range: 1-1000. "
               ::= {     sm48tat4xarpRADIUSServerConfigEntry 5 }

    sm48tat4xarpRADIUSServerConfRetransmit OBJECT-TYPE
               SYNTAX      Integer32(1..1000)
               MAX-ACCESS  read-create
               STATUS      current
               DESCRIPTION
                   "This optional setting overrides the global retransmit value.
                    Leaving it blank will use the global retransmit value.
                    range: 1-1000. "
               ::= {     sm48tat4xarpRADIUSServerConfigEntry 6 }

    sm48tat4xarpRADIUSServerConfKey OBJECT-TYPE
               SYNTAX      DisplayString
               MAX-ACCESS  read-create
               STATUS      current
               DESCRIPTION
                   "This optional setting overrides the global key. Leaving
                    it blank will use the global key."
               ::= {     sm48tat4xarpRADIUSServerConfigEntry 7 }

    sm48tat4xarpRADIUSServerConfRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sm48tat4xarpRADIUSServerConfigEntry 8 }

--sm48tat4xarpRADIUSDetailTable

    sm48tat4xarpRADIUSDetailTable OBJECT-TYPE
               SYNTAX      SEQUENCE OF     SM48TAT4XARPRADIUSDetailEntry
               MAX-ACCESS  not-accessible
               STATUS      current
               DESCRIPTION
                   "The RADIUS Detail Table."
               ::= {     sm48tat4xarpRADIUS 3 }

    sm48tat4xarpRADIUSDetailEntry OBJECT-TYPE
               SYNTAX          SM48TAT4XARPRADIUSDetailEntry
               MAX-ACCESS  not-accessible
               STATUS      current
               DESCRIPTION
                   "The RADIUS Detail Entry."
               INDEX    {    sm48tat4xarpRADIUSServerConfServerNo  }
               ::= {     sm48tat4xarpRADIUSDetailTable 1 }

    SM48TAT4XARPRADIUSDetailEntry             ::= SEQUENCE {
                 sm48tat4xarpRADIUSAuthIPAddress               DisplayString,
                 sm48tat4xarpRADIUSAuthStatus                  DisplayString,
                 sm48tat4xarpRADIUSAuthRoundTripTime           Integer32,
                 sm48tat4xarpRADIUSAuthRxAccessAccept          Counter32,
                 sm48tat4xarpRADIUSAuthRxAccessReject          Counter32,
                 sm48tat4xarpRADIUSAuthRxAccessChallenge       Counter32,
                 sm48tat4xarpRADIUSAuthRxAccessResponse        Counter32,
                 sm48tat4xarpRADIUSAuthRxBadAuth               Counter32,
                 sm48tat4xarpRADIUSAuthRxUnknownType           Counter32,
                 sm48tat4xarpRADIUSAuthRxPacketsDropped        Counter32,
                 sm48tat4xarpRADIUSAuthTxAccessRequest         Counter32,
                 sm48tat4xarpRADIUSAuthTxAccessRetransmission  Counter32,
                 sm48tat4xarpRADIUSAuthTxPendingRequest        Counter32,
                 sm48tat4xarpRADIUSAuthTxTimeout               Counter32,
                 sm48tat4xarpRADIUSAccountIPAddress            IpAddress,
                 sm48tat4xarpRADIUSAccountStatus               DisplayString,
                 sm48tat4xarpRADIUSAccountRoundTripTime        Integer32,
                 sm48tat4xarpRADIUSAccountRxResponses          Counter32,
                 sm48tat4xarpRADIUSAccountRxMalformedResponse  Counter32,
                 sm48tat4xarpRADIUSAccountRxBadAuth            Counter32,
                 sm48tat4xarpRADIUSAccountRxUnknownType        Counter32,
                 sm48tat4xarpRADIUSAccountRxPacketsDrop        Counter32,
                 sm48tat4xarpRADIUSAccountTxRequest            Counter32,
                 sm48tat4xarpRADIUSAccountTxRetransmission     Counter32,
                 sm48tat4xarpRADIUSAccountTxPendingRequest     Counter32,
                 sm48tat4xarpRADIUSAccountTxTimeout            Counter32,
                 sm48tat4xarpRADIUSDetailClearCmd              ActivateCmd
                 }

    sm48tat4xarpRADIUSAuthIPAddress OBJECT-TYPE
               SYNTAX      DisplayString
               MAX-ACCESS  read-only
               STATUS      current
               DESCRIPTION
                   "IP address and UDP port for the authentication
                    server in question."
               ::= {     sm48tat4xarpRADIUSDetailEntry 2 }

    sm48tat4xarpRADIUSAuthStatus OBJECT-TYPE
               SYNTAX      DisplayString
               MAX-ACCESS  read-only
               STATUS      current
               DESCRIPTION
                   "Shows the state of the server."
               ::= {     sm48tat4xarpRADIUSDetailEntry 3 }

    sm48tat4xarpRADIUSAuthRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sm48tat4xarpRADIUSDetailEntry 4 }

    sm48tat4xarpRADIUSAuthRxAccessAccept OBJECT-TYPE
               SYNTAX      Counter32
               MAX-ACCESS  read-only
               STATUS      current
               DESCRIPTION
                   "The number of RADIUS Access-Accept packets
                   (valid or invalid) received from the server."
               ::= {     sm48tat4xarpRADIUSDetailEntry 5 }

    sm48tat4xarpRADIUSAuthRxAccessReject OBJECT-TYPE
               SYNTAX      Counter32
               MAX-ACCESS  read-only
               STATUS      current
               DESCRIPTION
                   "The number of RADIUS Access-Reject packets
                    (valid or invalid) received from the server."
               ::= {     sm48tat4xarpRADIUSDetailEntry 6 }

    sm48tat4xarpRADIUSAuthRxAccessChallenge OBJECT-TYPE
               SYNTAX      Counter32
               MAX-ACCESS  read-only
               STATUS      current
               DESCRIPTION
                   "The number of RADIUS Access-Challenge packets
                    (valid or invalid) received from the server."
               ::= {     sm48tat4xarpRADIUSDetailEntry 7 }

    sm48tat4xarpRADIUSAuthRxAccessResponse OBJECT-TYPE
               SYNTAX      Counter32
               MAX-ACCESS  read-only
               STATUS      current
               DESCRIPTION
                   "The number of malformed RADIUS Access-Response
                    packets received from the server."
               ::= {     sm48tat4xarpRADIUSDetailEntry 8 }

    sm48tat4xarpRADIUSAuthRxBadAuth OBJECT-TYPE
               SYNTAX      Counter32
               MAX-ACCESS  read-only
               STATUS      current
               DESCRIPTION
                   "The number of RADIUS Access-Response packets containing
                    invalid authenticators or Message Authenticator
                    attributes received from the server."
               ::= {     sm48tat4xarpRADIUSDetailEntry 9 }

    sm48tat4xarpRADIUSAuthRxUnknownType OBJECT-TYPE
               SYNTAX      Counter32
               MAX-ACCESS  read-only
               STATUS      current
               DESCRIPTION
                   "The number of RADIUS packets that were received with
                    unknown types from the server on the authentication
                    port and dropped."
               ::= {     sm48tat4xarpRADIUSDetailEntry 10 }

    sm48tat4xarpRADIUSAuthRxPacketsDropped OBJECT-TYPE
               SYNTAX      Counter32
               MAX-ACCESS  read-only
               STATUS      current
               DESCRIPTION
                   "The number of RADIUS packets that were received from
                    the server on the authentication port and dropped for
                    some other reason."
               ::= {     sm48tat4xarpRADIUSDetailEntry 11 }

    sm48tat4xarpRADIUSAuthTxAccessRequest OBJECT-TYPE
               SYNTAX      Counter32
               MAX-ACCESS  read-only
               STATUS      current
               DESCRIPTION
                   "The number of RADIUS Access-Request packets sent to
                    the server. This does not include retransmissions."
               ::= {     sm48tat4xarpRADIUSDetailEntry 12 }

    sm48tat4xarpRADIUSAuthTxAccessRetransmission OBJECT-TYPE
               SYNTAX      Counter32
               MAX-ACCESS  read-only
               STATUS      current
               DESCRIPTION
                   "The number of RADIUS Access-Request packets
                    retransmitted to the RADIUS authentication server."
               ::= {     sm48tat4xarpRADIUSDetailEntry 13 }

    sm48tat4xarpRADIUSAuthTxPendingRequest OBJECT-TYPE
               SYNTAX      Counter32
               MAX-ACCESS  read-only
               STATUS      current
               DESCRIPTION
                   "The number of RADIUS Access-Request packets destined
                    for the server that have not yet timed out or received
                    a response. "
               ::= {     sm48tat4xarpRADIUSDetailEntry 14 }

    sm48tat4xarpRADIUSAuthTxTimeout OBJECT-TYPE
               SYNTAX      Counter32
               MAX-ACCESS  read-only
               STATUS      current
               DESCRIPTION
                   "The number of authentication timeouts to the server.
                    After a timeout, the client may retry to the same server,
                    send to a different server, or give up."
               ::= {     sm48tat4xarpRADIUSDetailEntry 15 }

    sm48tat4xarpRADIUSAccountIPAddress OBJECT-TYPE
               SYNTAX      IpAddress
               MAX-ACCESS  read-only
               STATUS      current
               DESCRIPTION
                   "IP address and UDP port for the authentication server
                    in question."
               ::= {     sm48tat4xarpRADIUSDetailEntry 16 }

    sm48tat4xarpRADIUSAccountStatus OBJECT-TYPE
               SYNTAX      DisplayString
               MAX-ACCESS  read-only
               STATUS      current
               DESCRIPTION
                   "Shows the state of the server. "
               ::= {     sm48tat4xarpRADIUSDetailEntry 17 }

    sm48tat4xarpRADIUSAccountRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sm48tat4xarpRADIUSDetailEntry 18 }

    sm48tat4xarpRADIUSAccountRxResponses OBJECT-TYPE
               SYNTAX      Counter32
               MAX-ACCESS  read-only
               STATUS      current
               DESCRIPTION
                   "The number of RADIUS packets (valid or invalid)
                    received from the server."
               ::= {     sm48tat4xarpRADIUSDetailEntry 19 }

    sm48tat4xarpRADIUSAccountRxMalformedResponse OBJECT-TYPE
               SYNTAX      Counter32
               MAX-ACCESS  read-only
               STATUS      current
               DESCRIPTION
                   "The number of malformed RADIUS packets received from
                    the server. "
               ::= {     sm48tat4xarpRADIUSDetailEntry 20 }

    sm48tat4xarpRADIUSAccountRxBadAuth OBJECT-TYPE
               SYNTAX      Counter32
               MAX-ACCESS  read-only
               STATUS      current
               DESCRIPTION
                   "The number of RADIUS packets containing invalid
                    authenticators received from the server."
               ::= {     sm48tat4xarpRADIUSDetailEntry 21 }

    sm48tat4xarpRADIUSAccountRxUnknownType OBJECT-TYPE
               SYNTAX      Counter32
               MAX-ACCESS  read-only
               STATUS      current
               DESCRIPTION
                   "The number of RADIUS packets of unknown types that were
                    received from the server on the accounting port. "
               ::= {     sm48tat4xarpRADIUSDetailEntry 22 }

    sm48tat4xarpRADIUSAccountRxPacketsDrop OBJECT-TYPE
               SYNTAX      Counter32
               MAX-ACCESS  read-only
               STATUS      current
               DESCRIPTION
                   "The number of RADIUS packets that were received from
                    the server on the accounting port and dropped for some
                    other reason."
               ::= {     sm48tat4xarpRADIUSDetailEntry 23 }

    sm48tat4xarpRADIUSAccountTxRequest OBJECT-TYPE
               SYNTAX      Counter32
               MAX-ACCESS  read-only
               STATUS      current
               DESCRIPTION
                   "The number of RADIUS packets sent to the server.
                    This does not include retransmissions."
               ::= {     sm48tat4xarpRADIUSDetailEntry 24 }

    sm48tat4xarpRADIUSAccountTxRetransmission OBJECT-TYPE
               SYNTAX      Counter32
               MAX-ACCESS  read-only
               STATUS      current
               DESCRIPTION
                   "The number of RADIUS packets retransmitted to the RADIUS
                    accounting server."
               ::= {     sm48tat4xarpRADIUSDetailEntry 25 }

    sm48tat4xarpRADIUSAccountTxPendingRequest OBJECT-TYPE
               SYNTAX      Counter32
               MAX-ACCESS  read-only
               STATUS      current
               DESCRIPTION
                   "The number of RADIUS packets destined for the server
                    that have not yet timed out or received a response."
               ::= {     sm48tat4xarpRADIUSDetailEntry 26 }

    sm48tat4xarpRADIUSAccountTxTimeout OBJECT-TYPE
               SYNTAX      Counter32
               MAX-ACCESS  read-only
               STATUS      current
               DESCRIPTION
                   "The number of accounting timeouts to the server.
                    After a timeout, the client may retry to the same
                    server, send to a different server, or give up."
               ::= {     sm48tat4xarpRADIUSDetailEntry 27 }

    sm48tat4xarpRADIUSDetailClearCmd OBJECT-TYPE
               SYNTAX      ActivateCmd
               MAX-ACCESS  read-only
               STATUS      current
               DESCRIPTION
                   "Clears the counters for the selected server."
               ::= {     sm48tat4xarpRADIUSDetailEntry 28 }

--
-- =======================================================================================================================
-- Start sm48tat4xarpTACACS group
-- =======================================================================================================================
--sm48tat4xarpTACACSGlobalConfig

    sm48tat4xarpTACACSGlobalConfigTimeout OBJECT-TYPE
               SYNTAX      Integer32(1..1000)
               MAX-ACCESS  read-write
               STATUS      current
               DESCRIPTION
                   "Timeout is the number of seconds,to wait for a reply
                    from a TACACS+ server before it is considered to be dead.
                    range: 1-1000 seconds,
                    default: 5 seconds."
               ::= {     sm48tat4xarpTACACS 1 }

    sm48tat4xarpTACACSGlobalConfigDeadtime OBJECT-TYPE
               SYNTAX      Integer32(0..1440)
               MAX-ACCESS  read-write
               STATUS      current
               DESCRIPTION
                   "The period during which the switch will not send new
                    requests to a server that has failed to respond to a
                    previous request. This will stop the switch from
                    continually trying to contact a server that it has
                    already determined as dead.
                    range: 0-1440 minutes,
                    default: 0 minutes."
               ::= {     sm48tat4xarpTACACS 2 }

    sm48tat4xarpTACACSGlobalConfigKey OBJECT-TYPE
               SYNTAX      DisplayString
               MAX-ACCESS  read-write
               STATUS      current
               DESCRIPTION
                   "The secret key shared between the TACACS+ server and
                    the switch."
               ::= {     sm48tat4xarpTACACS 3 }

--sm48tat4xarpTACACSServerConfigTable

    sm48tat4xarpTACACSServerConfigTable OBJECT-TYPE
               SYNTAX      SEQUENCE OF     SM48TAT4XARPTACACSServerConfigEntry
               MAX-ACCESS  not-accessible
               STATUS      current
               DESCRIPTION
                   "The TACACS Server configuration Table."
               ::= {     sm48tat4xarpTACACS 4 }

    sm48tat4xarpTACACSServerConfigEntry OBJECT-TYPE
               SYNTAX          SM48TAT4XARPTACACSServerConfigEntry
               MAX-ACCESS  not-accessible
               STATUS      current
               DESCRIPTION
                   "The TACACS Server configuration Entry."
               INDEX    {    sm48tat4xarpTACACSServerConfigServerNo  }
               ::= {     sm48tat4xarpTACACSServerConfigTable 1 }

    SM48TAT4XARPTACACSServerConfigEntry             ::= SEQUENCE {
                 sm48tat4xarpTACACSServerConfigServerNo        Integer32,
                 sm48tat4xarpTACACSServerConfigHostname        DisplayString,
                 sm48tat4xarpTACACSServerConfigPort            Integer32,
                 sm48tat4xarpTACACSServerConfigTimeout         Integer32,
                 sm48tat4xarpTACACSServerConfigKey             DisplayString,
                 sm48tat4xarpTACACSServerConfigRowStatus       RowStatus
                 }

    sm48tat4xarpTACACSServerConfigServerNo OBJECT-TYPE
               SYNTAX      Integer32(1..5)
               MAX-ACCESS  not-accessible
               STATUS      current
               DESCRIPTION
                   "The TACACS server number.
                    max: 5."
               ::= {     sm48tat4xarpTACACSServerConfigEntry 1 }

    sm48tat4xarpTACACSServerConfigHostname OBJECT-TYPE
               SYNTAX      DisplayString
               MAX-ACCESS  read-create
               STATUS      current
               DESCRIPTION
                   "The IP address or hostname of the TACACS+ server."
               ::= {     sm48tat4xarpTACACSServerConfigEntry 2 }

    sm48tat4xarpTACACSServerConfigPort OBJECT-TYPE
               SYNTAX      Integer32(0..65535)
               MAX-ACCESS  read-create
               STATUS      current
               DESCRIPTION
                   "The TCP port to use on the TACACS+ server for
                    authentication."
               ::= {     sm48tat4xarpTACACSServerConfigEntry 3 }

    sm48tat4xarpTACACSServerConfigTimeout OBJECT-TYPE
               SYNTAX      Integer32(1..1000)
               MAX-ACCESS  read-create
               STATUS      current
               DESCRIPTION
                   "This optional setting overrides the global timeout
                    value. Leaving it blank will use the global timeout
                    value.
                    range: 1-1000."
               ::= {     sm48tat4xarpTACACSServerConfigEntry 4 }

    sm48tat4xarpTACACSServerConfigKey OBJECT-TYPE
               SYNTAX      DisplayString
               MAX-ACCESS  read-create
               STATUS      current
               DESCRIPTION
                   "This optional setting overrides the global key.
                    Leaving it blank will use the global key. "
               ::= {     sm48tat4xarpTACACSServerConfigEntry 5 }

    sm48tat4xarpTACACSServerConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sm48tat4xarpTACACSServerConfigEntry 6 }

-- =======================================================================================================================
--
-- =======================================================================================================================
-- Textual Conventions for the sm48tat4xarp Nas Mib
-- =======================================================================================================================
--
sm48tat4xarpNasMIB                   OBJECT IDENTIFIER  ::= { sm48tat4xarpConfiguration 16 }
    sm48tat4xarpNAS                  OBJECT IDENTIFIER  ::= { sm48tat4xarpNasMIB 1 }
    sm48tat4xarpNASConf              OBJECT IDENTIFIER  ::= { sm48tat4xarpNAS 1 }
    sm48tat4xarpNASStatus            OBJECT IDENTIFIER  ::= { sm48tat4xarpNAS 2 }

--
-- =======================================================================================================================
-- Start sm48tat4xarpNAS group
-- =======================================================================================================================
--sm48tat4xarpNASConf

    sm48tat4xarpNASConfMode OBJECT-TYPE
               SYNTAX      AdminMode
               MAX-ACCESS  read-write
               STATUS      current
               DESCRIPTION
                   "Indicates if NAS is globally enabled or disabled on
                    the switch."
               DEFVAL  { disable }
               ::= {     sm48tat4xarpNASConf 1 }

    sm48tat4xarpNASConfReauthenticationEnabled OBJECT-TYPE
               SYNTAX      AdminMode
               MAX-ACCESS  read-write
               STATUS      current
               DESCRIPTION
                   "If enable, successfully authenticated supplicants/clients
                    are reauthenticated after the interval specified by the
                    Reauthentication Period."
               DEFVAL  { disable }
               ::= {     sm48tat4xarpNASConf 2 }

    sm48tat4xarpNASConfReauthenticationPeriod OBJECT-TYPE
               SYNTAX      Integer32(1..3600)
               MAX-ACCESS  read-write
               STATUS      current
               DESCRIPTION
                   "Determines the period, in seconds, after which a
                    connected client must be reauthenticated.
                    default: 3600 sec,
                    range: 1-3600 sec."
               ::= {     sm48tat4xarpNASConf 3 }

    sm48tat4xarpNASConfEAPOLTimeout OBJECT-TYPE
               SYNTAX      Integer32(1..65535)
               MAX-ACCESS  read-write
               STATUS      current
               DESCRIPTION
                   "Determines the time for retransmission of Request
                    Identity EAPOL frames.
                    default: 30 sec,
                    range: 1-65535 sec."
               ::= {     sm48tat4xarpNASConf 4 }

    sm48tat4xarpNASConfAgingPeriod OBJECT-TYPE
               SYNTAX      Integer32(0|10..1000000)
               MAX-ACCESS  read-write
               STATUS      current
               DESCRIPTION
                   "When the NAS module uses the Port Security module to
                    secure MAC addresses, the Port Security module needs to
                    check for activity on the MAC address in question at regular
                    intervals and free resources if no activity is seen within
                    a given period of time.
                    default: 300 sec,
                    0: no support.
                    range: 0,10-1000000 sec."
               ::= {     sm48tat4xarpNASConf 5 }

    sm48tat4xarpNASConfHoldTime OBJECT-TYPE
               SYNTAX      Integer32(0|10..1000000)
               MAX-ACCESS  read-write
               STATUS      current
               DESCRIPTION
                   "If a client is denied access - either because the RADIUS
                    server denies the client access or because the RADIUS server
                    request times out - the client is put on hold in the
                    Unauthorized state.
                    default: 10 sec,
                    0: no support.
                    range: 0,10-1000000 sec."
               ::= {     sm48tat4xarpNASConf 6 }

    sm48tat4xarpNASConfRADIUSQoSEnabled OBJECT-TYPE
               SYNTAX      AdminMode
               MAX-ACCESS  read-write
               STATUS      current
               DESCRIPTION
                   "RADIUS-assigned QoS provides a means to centrally control
                    the traffic class to which traffic coming from a successfully
                    authenticated supplicant is assigned on the switch."
               DEFVAL  { disable }
               ::= {     sm48tat4xarpNASConf 7 }

    sm48tat4xarpNASConfRADIUSVLANEnabled OBJECT-TYPE
               SYNTAX      AdminMode
               MAX-ACCESS  read-write
               STATUS      current
               DESCRIPTION
                   "RADIUS-assigned VLAN provides a means to centrally control
                    the VLAN on which a successfully authenticated supplicant
                    is placed on the switch."
               DEFVAL  { disable }
               ::= {     sm48tat4xarpNASConf 8 }

    sm48tat4xarpNASConfGuestVLANEnabled OBJECT-TYPE
               SYNTAX      AdminMode
               MAX-ACCESS  read-write
               STATUS      current
               DESCRIPTION
                   "A Guest VLAN is a special VLAN - typically with limited
                    network access - on which 802.1X-unaware clients are placed
                    after a network administrator-defined timeout."
               DEFVAL  { disable }
               ::= {     sm48tat4xarpNASConf 9 }

    sm48tat4xarpNASConfGuestVLANID OBJECT-TYPE
               SYNTAX      Integer32(1..4095)
               MAX-ACCESS  read-write
               STATUS      current
               DESCRIPTION
                   "This is the value that a port's Port VLAN ID is set to if
                    a port is moved into the Guest VLAN.
                    default: 1,
                    range: 1-4095."
               ::= {     sm48tat4xarpNASConf 10 }

    sm48tat4xarpNASConfMaxReauthCount OBJECT-TYPE
               SYNTAX      Integer32(1..255)
               MAX-ACCESS  read-write
               STATUS      current
               DESCRIPTION
                   "The number of times the switch transmits an EAPOL Request
                    Identity frame without response before considering entering
                    the Guest VLAN is adjusted with this setting.
                    default: 2,
                    range: 1-255."
               ::= {     sm48tat4xarpNASConf 11 }

    sm48tat4xarpNASConfAllowGuestVLAN OBJECT-TYPE
               SYNTAX      AdminMode
               MAX-ACCESS  read-write
               STATUS      current
               DESCRIPTION
                   "The switch remembers if an EAPOL frame has been received
                    on the port for the life-time of the port."
               DEFVAL  { disable }
               ::= {     sm48tat4xarpNASConf 12 }

--sm48tat4xarpNASPortConfTable

    sm48tat4xarpNASPortConfTable OBJECT-TYPE
               SYNTAX      SEQUENCE OF     SM48TAT4XARPNASPortConfEntry
               MAX-ACCESS  not-accessible
               STATUS      current
               DESCRIPTION
                   "The NAS Port Configuration Table.
                    INDEX for this table is ifIndex which is
                    equivalent to the panel port number."
               ::= {     sm48tat4xarpNASConf 13 }

    sm48tat4xarpNASPortConfEntry OBJECT-TYPE
               SYNTAX          SM48TAT4XARPNASPortConfEntry
               MAX-ACCESS  not-accessible
               STATUS      current
               DESCRIPTION
                   "The NAS Port Configuration Entry."
               INDEX    {    ifIndex  }
               ::= {     sm48tat4xarpNASPortConfTable 1 }

    SM48TAT4XARPNASPortConfEntry             ::= SEQUENCE {
                 sm48tat4xarpNASPortConfAdminState         Integer32,
                 sm48tat4xarpNASPortConfRADIUSQoSEnabled   AdminMode,
                 sm48tat4xarpNASPortConfRADIUSVLANEnabled  AdminMode,
                 sm48tat4xarpNASPortConfGuestVLANEnabled   AdminMode,
                 sm48tat4xarpNASPortConfPortState          DisplayString,
                 sm48tat4xarpNASPortConfReauthenticateCmd  INTEGER,
                 sm48tat4xarpNASPortConfReinitializeCmd    INTEGER
                 }

    sm48tat4xarpNASPortConfAdminState OBJECT-TYPE
               SYNTAX      Integer32(0..5)
               MAX-ACCESS  read-write
               STATUS      current
               DESCRIPTION
                   "This selection controls the port's authentication mode.
                    0: Force Authorized,
                    1: Force Unauthorized,
                    2: Port-based 802.1X,
                    3: Single 802.1X,
                    4: Multi 802.1X,
                    5: MAC-based Auth,
                    range: 0-5."
               ::= {     sm48tat4xarpNASPortConfEntry 2 }

    sm48tat4xarpNASPortConfRADIUSQoSEnabled OBJECT-TYPE
               SYNTAX      AdminMode
               MAX-ACCESS  read-write
               STATUS      current
               DESCRIPTION
                   "When RADIUS-Assigned QoS is both globally enabled and
                    enabled on a given port, the switch reacts to QoS Class
                    information carried in the RADIUS Access-Accept packet
                    transmitted by the RADIUS server when a supplicant is
                    successfully authenticated."
               ::= {     sm48tat4xarpNASPortConfEntry 3 }

    sm48tat4xarpNASPortConfRADIUSVLANEnabled OBJECT-TYPE
               SYNTAX      AdminMode
               MAX-ACCESS  read-write
               STATUS      current
               DESCRIPTION
                   "When RADIUS-Assigned VLAN is both globally enabled and
                    enabled for a given port, the switch reacts to VLAN ID
                    information carried in the RADIUS Access-Accept packet
                    transmitted by the RADIUS server when a supplicant is
                    successfully authenticated."
               ::= {     sm48tat4xarpNASPortConfEntry 4 }

    sm48tat4xarpNASPortConfGuestVLANEnabled OBJECT-TYPE
               SYNTAX      AdminMode
               MAX-ACCESS  read-write
               STATUS      current
               DESCRIPTION
                   "When Guest VLAN is both globally enabled and enabled for
                    a given port, the switch considers moving the port into
                    the Guest VLAN according to the rules."
               ::= {     sm48tat4xarpNASPortConfEntry 5 }

    sm48tat4xarpNASPortConfPortState OBJECT-TYPE
               SYNTAX      DisplayString
               MAX-ACCESS  read-only
               STATUS      current
               DESCRIPTION
                   "The current state of the port."
               ::= {     sm48tat4xarpNASPortConfEntry 6 }

    sm48tat4xarpNASPortConfReauthenticateCmd OBJECT-TYPE
               SYNTAX      ActivateCmd
               MAX-ACCESS  read-write
               STATUS      current
               DESCRIPTION
                   "Schedules a reauthentication whenever the quiet-period of
                    the port runs out (EAPOL-based authentication). For
                    MAC-based authentication, reauthentication will be attempted
                    immediately.The button only has effect for successfully
                    authenticated clients on the port and will not cause the
                    clients to get temporarily unauthorized."
               DEFVAL  { noAction }
               ::= {     sm48tat4xarpNASPortConfEntry 7 }

    sm48tat4xarpNASPortConfReinitializeCmd OBJECT-TYPE
               SYNTAX      ActivateCmd
               MAX-ACCESS  read-write
               STATUS      current
               DESCRIPTION
                   "Forces a reinitialization of the clients on the port and
                    thereby a reauthentication immediately. The clients will
                    transfer to the unauthorized state while the
                    reauthentication is in progress."
               DEFVAL  { noAction }
               ::= {     sm48tat4xarpNASPortConfEntry 8 }

--sm48tat4xarpNASSwitchStatusTable

    sm48tat4xarpNASSwitchStatusTable OBJECT-TYPE
               SYNTAX      SEQUENCE OF     SM48TAT4XARPNASSwitchStatusEntry
               MAX-ACCESS  not-accessible
               STATUS      current
               DESCRIPTION
                   "The NAS Switch Status Table.
                    INDEX for this table is ifIndex which is
                    equivalent to the panel port number."
               ::= {     sm48tat4xarpNASStatus 1 }

    sm48tat4xarpNASSwitchStatusEntry OBJECT-TYPE
               SYNTAX          SM48TAT4XARPNASSwitchStatusEntry
               MAX-ACCESS  not-accessible
               STATUS      current
               DESCRIPTION
                   "The NAS Switch Status Entry."
               INDEX    {    ifIndex  }
               ::= {     sm48tat4xarpNASSwitchStatusTable 1 }

    SM48TAT4XARPNASSwitchStatusEntry             ::= SEQUENCE {
                 sm48tat4xarpNASSwitchStatusAdminState   DisplayString,
                 sm48tat4xarpNASSwitchStatusPortState    DisplayString,
                 sm48tat4xarpNASSwitchStatusLastSource   DisplayString,
                 sm48tat4xarpNASSwitchStatusLastID       DisplayString,
                 sm48tat4xarpNASSwitchStatusQoSClass     DisplayString,
                 sm48tat4xarpNASSwitchStatusPortVLANID   DisplayString
                 }

    sm48tat4xarpNASSwitchStatusAdminState OBJECT-TYPE
               SYNTAX      DisplayString
               MAX-ACCESS  read-only
               STATUS      current
               DESCRIPTION
                   "The port's current administrative state."
               ::= {     sm48tat4xarpNASSwitchStatusEntry 2 }

    sm48tat4xarpNASSwitchStatusPortState OBJECT-TYPE
               SYNTAX      DisplayString
               MAX-ACCESS  read-only
               STATUS      current
               DESCRIPTION
                   "The current state of the port."
               ::= {     sm48tat4xarpNASSwitchStatusEntry 3 }

    sm48tat4xarpNASSwitchStatusLastSource OBJECT-TYPE
               SYNTAX      DisplayString
               MAX-ACCESS  read-only
               STATUS      current
               DESCRIPTION
                   "The source MAC address carried in the most recently
                    received EAPOL frame for EAPOL-based authentication,
                    and the most recently received frame from a new client
                    for MAC-based authentication."
               ::= {     sm48tat4xarpNASSwitchStatusEntry 4 }

    sm48tat4xarpNASSwitchStatusLastID OBJECT-TYPE
               SYNTAX      DisplayString
               MAX-ACCESS  read-only
               STATUS      current
               DESCRIPTION
                   "The user name (supplicant identity) carried in the most
                    recently received Response Identity EAPOL frame for
                    EAPOL-based authentication, and the source MAC address
                    from the most recently received frame from a new client
                    for MAC-based authentication."
               ::= {     sm48tat4xarpNASSwitchStatusEntry 5 }

    sm48tat4xarpNASSwitchStatusQoSClass OBJECT-TYPE
               SYNTAX      DisplayString
               MAX-ACCESS  read-only
               STATUS      current
               DESCRIPTION
                   "QoS Class assigned to the port by the RADIUS server
                    if enabled."
               ::= {     sm48tat4xarpNASSwitchStatusEntry 6 }

    sm48tat4xarpNASSwitchStatusPortVLANID OBJECT-TYPE
               SYNTAX      DisplayString
               MAX-ACCESS  read-only
               STATUS      current
               DESCRIPTION
                   "The VLAN ID that NAS has put the port in."
               ::= {     sm48tat4xarpNASSwitchStatusEntry 7 }

--sm48tat4xarpNASPortCounterTable

    sm48tat4xarpNASPortCounterTable OBJECT-TYPE
               SYNTAX      SEQUENCE OF     SM48TAT4XARPNASPortCounterEntry
               MAX-ACCESS  not-accessible
               STATUS      current
               DESCRIPTION
                   "The NAS Port Counter Table.
                    INDEX for this table is ifIndex which is
                    equivalent to the panel port number."
               ::= {     sm48tat4xarpNASStatus 2 }

    sm48tat4xarpNASPortCounterEntry OBJECT-TYPE
               SYNTAX          SM48TAT4XARPNASPortCounterEntry
               MAX-ACCESS  not-accessible
               STATUS      current
               DESCRIPTION
                   "The NAS Port Counter Entry."
               INDEX    {    ifIndex  }
               ::= {     sm48tat4xarpNASPortCounterTable 1 }

    SM48TAT4XARPNASPortCounterEntry             ::= SEQUENCE {
                 sm48tat4xarpNASReceiveEAPOLTotal          Integer32,
                 sm48tat4xarpNASReceiveEAPOLResponseID     Integer32,
                 sm48tat4xarpNASReceiveEAPOLResponses      Integer32,
                 sm48tat4xarpNASReceiveEAPOLStart          Integer32,
                 sm48tat4xarpNASReceiveEAPOLLogoff         Integer32,
                 sm48tat4xarpNASReceiveEAPOLInvalidType    Integer32,
                 sm48tat4xarpNASReceiveEAPOLInvalidLength  Integer32,
                 sm48tat4xarpNASTransmitEAPOLTotal         Integer32,
                 sm48tat4xarpNASTransmitEAPOLRequestID     Integer32,
                 sm48tat4xarpNASTransmitEAPOLRequests      Integer32,
                 sm48tat4xarpNASPortReceiveBackendServerAccessChallenges    Integer32,
                 sm48tat4xarpNASPortReceiveBackendServerOtherRequests       Integer32,
                 sm48tat4xarpNASPortReceiveBackendServerAuthSuccesses       Integer32,
                 sm48tat4xarpNASPortReceiveBackendServerAuthFailures        Integer32,
                 sm48tat4xarpNASPortTransmitBackendServerResponses          Integer32,
                 sm48tat4xarpNASSupplicantInfoMAC          DisplayString,
                 sm48tat4xarpNASSupplicantInfoVlanID       Integer32,
                 sm48tat4xarpNASSupplicantInfoVersion      Integer32,
                 sm48tat4xarpNASSupplicantInfoIdentity     DisplayString,
                 sm48tat4xarpNASPortCounterClearCmd        ActivateCmd
                 }

    sm48tat4xarpNASReceiveEAPOLTotal OBJECT-TYPE
               SYNTAX      Integer32(-1..1000000)
               MAX-ACCESS  read-only
               STATUS      current
               DESCRIPTION
                   "The number of valid EAPOL frames of any type that have
                    been received by the switch.
                    -1: no support."
               ::= {     sm48tat4xarpNASPortCounterEntry 2 }

    sm48tat4xarpNASReceiveEAPOLResponseID OBJECT-TYPE
               SYNTAX      Integer32(-1..1000000)
               MAX-ACCESS  read-only
               STATUS      current
               DESCRIPTION
                   "The number of valid EAPOL Response Identity frames that
                    have been received by the switch.
                    -1: no support."
               ::= {     sm48tat4xarpNASPortCounterEntry 3 }

    sm48tat4xarpNASReceiveEAPOLResponses OBJECT-TYPE
               SYNTAX      Integer32(-1..1000000)
               MAX-ACCESS  read-only
               STATUS      current
               DESCRIPTION
                   "The number of valid EAPOL response frames (other than
                    Response Identity frames) that have been received by
                    the switch.
                    -1: no support."
               ::= {     sm48tat4xarpNASPortCounterEntry 4 }

    sm48tat4xarpNASReceiveEAPOLStart OBJECT-TYPE
               SYNTAX      Integer32(-1..1000000)
               MAX-ACCESS  read-only
               STATUS      current
               DESCRIPTION
                   "The number of EAPOL Start frames that have been received
                    by the switch.
                    -1: no support."
               ::= {     sm48tat4xarpNASPortCounterEntry 5 }

    sm48tat4xarpNASReceiveEAPOLLogoff OBJECT-TYPE
               SYNTAX      Integer32(-1..1000000)
               MAX-ACCESS  read-only
               STATUS      current
               DESCRIPTION
                   "The number of valid EAPOL Logoff frames that have been
                    received by the switch.
                    -1: no support."
               ::= {     sm48tat4xarpNASPortCounterEntry 6 }

    sm48tat4xarpNASReceiveEAPOLInvalidType OBJECT-TYPE
               SYNTAX      Integer32(-1..1000000)
               MAX-ACCESS  read-only
               STATUS      current
               DESCRIPTION
                   "The number of EAPOL frames that have been received by
                    the switch in which the frame type is not recognized.
                    -1: no support."
               ::= {     sm48tat4xarpNASPortCounterEntry 7 }

    sm48tat4xarpNASReceiveEAPOLInvalidLength OBJECT-TYPE
               SYNTAX      Integer32(-1..1000000)
               MAX-ACCESS  read-only
               STATUS      current
               DESCRIPTION
                   "The number of EAPOL frames that have been received
                    by the switch in which the Packet Body Length field
                    is invalid.
                    -1: no support."
               ::= {     sm48tat4xarpNASPortCounterEntry 8 }

    sm48tat4xarpNASTransmitEAPOLTotal OBJECT-TYPE
               SYNTAX      Integer32(-1..1000000)
               MAX-ACCESS  read-only
               STATUS      current
               DESCRIPTION
                   "The number of EAPOL frames of any type that have been
                    transmitted by the switch.
                    -1: no support."
               ::= {     sm48tat4xarpNASPortCounterEntry 9 }

    sm48tat4xarpNASTransmitEAPOLRequestID OBJECT-TYPE
               SYNTAX      Integer32(-1..1000000)
               MAX-ACCESS  read-only
               STATUS      current
               DESCRIPTION
                   "The number of EAPOL Request Identity frames that have
                    been transmitted by the switch.
                    -1: no support."
               ::= {     sm48tat4xarpNASPortCounterEntry 10 }

    sm48tat4xarpNASTransmitEAPOLRequests OBJECT-TYPE
               SYNTAX      Integer32(-1..1000000)
               MAX-ACCESS  read-only
               STATUS      current
               DESCRIPTION
                   "The number of valid EAPOL Request frames (other than
                    Request Identity frames) that have been transmitted
                    by the switch.
                    -1: no support."
               ::= {     sm48tat4xarpNASPortCounterEntry 11 }

    sm48tat4xarpNASPortReceiveBackendServerAccessChallenges OBJECT-TYPE
               SYNTAX      Integer32(-1..1000000)
               MAX-ACCESS  read-only
               STATUS      current
               DESCRIPTION
                   "802.1X-based: Counts the number of times that the switch
                    receives the first request from the backend server following
                    the first response from the supplicant. Indicates that the
                    backend server has communication with the switch.
                    MAC-based:Counts all Access Challenges received from the
                    backend server for this port (left-most table).
                    -1: no support."
               ::= {     sm48tat4xarpNASPortCounterEntry 12 }

    sm48tat4xarpNASPortReceiveBackendServerOtherRequests OBJECT-TYPE
               SYNTAX      Integer32(-1..1000000)
               MAX-ACCESS  read-only
               STATUS      current
               DESCRIPTION
                   "802.1X-based: Counts the number of times that the switch
                    sends an EAP Request packet following the first to the
                    supplicant. Indicates that the backend server chose an
                    EAP-method.
                    MAC-based: Not applicable.
                    -1: no support."
               ::= {     sm48tat4xarpNASPortCounterEntry 13 }

    sm48tat4xarpNASPortReceiveBackendServerAuthSuccesses OBJECT-TYPE
               SYNTAX      Integer32(-1..1000000)
               MAX-ACCESS  read-only
               STATUS      current
               DESCRIPTION
                   "802.1X- and MAC-based: Counts the number of times that
                    the switch receives a success indication.Indicates that
                    the supplicant has successfully authenticated to
                    the backend server.
                    -1: no support."
               ::= {     sm48tat4xarpNASPortCounterEntry 14 }

    sm48tat4xarpNASPortReceiveBackendServerAuthFailures OBJECT-TYPE
               SYNTAX      Integer32(-1..1000000)
               MAX-ACCESS  read-only
               STATUS      current
               DESCRIPTION
                   "802.1X- and MAC-based:Counts the number of times that the
                    switch receives a failure message.This indicates that the
                    supplicant has not authenticated to the backend
                    server.
                    -1: no support."
               ::= {     sm48tat4xarpNASPortCounterEntry 15 }

    sm48tat4xarpNASPortTransmitBackendServerResponses OBJECT-TYPE
               SYNTAX      Integer32(-1..1000000)
               MAX-ACCESS  read-only
               STATUS      current
               DESCRIPTION
                   "802.1X-based:Counts the number of times that the switch
                    attempts to send a supplicant's first response packet to
                    the backend server. Indicates the switch attempted
                    communication with the backend server. Possible
                    retransmissions are not counted.
                    MAC-based: Counts all the backend server packets sent from
                    the switch towards the backend server for a given port
                    (left-most table). Possible retransmissions are not
                    counted.
                    -1: no support."
               ::= {     sm48tat4xarpNASPortCounterEntry 16 }

    sm48tat4xarpNASSupplicantInfoMAC OBJECT-TYPE
               SYNTAX      DisplayString
               MAX-ACCESS  read-only
               STATUS      current
               DESCRIPTION
                   "The MAC address of the last supplicant. "
               ::= {     sm48tat4xarpNASPortCounterEntry 17 }

    sm48tat4xarpNASSupplicantInfoVlanID OBJECT-TYPE
               SYNTAX      Integer32(-1..1000000)
               MAX-ACCESS  read-only
               STATUS      current
               DESCRIPTION
                   "The VLAN ID on which the last frame from the last
                    supplicant was received.
                    -1: no support."
               ::= {     sm48tat4xarpNASPortCounterEntry 18 }

    sm48tat4xarpNASSupplicantInfoVersion OBJECT-TYPE
               SYNTAX      Integer32(-1..1000000)
               MAX-ACCESS  read-only
               STATUS      current
               DESCRIPTION
                   "802.1X-based:The protocol version number carried in
                    the most recently received EAPOL frame.
                    MAC-based: Not applicable.
                    -1: no support."
               ::= {     sm48tat4xarpNASPortCounterEntry 19 }

    sm48tat4xarpNASSupplicantInfoIdentity OBJECT-TYPE
               SYNTAX      DisplayString
               MAX-ACCESS  read-only
               STATUS      current
               DESCRIPTION
                   "802.1X-based:The user name (supplicant identity) carried
                    in the most recently received Response Identity EAPOL frame.
                    MAC-based: Not applicable. "
               ::= {     sm48tat4xarpNASPortCounterEntry 20 }

    sm48tat4xarpNASPortCounterClearCmd OBJECT-TYPE
               SYNTAX      ActivateCmd
               MAX-ACCESS  read-write
               STATUS      current
               DESCRIPTION
                   "Clear the counters for the selected port."
               ::= {     sm48tat4xarpNASPortCounterEntry 21 }


-- =======================================================================================================================
sm48tat4xarpMACConf 						OBJECT IDENTIFIER ::= { sm48tat4xarpConfiguration 17 }

    sm48tat4xarpMAC                                                    OBJECT IDENTIFIER   ::= { sm48tat4xarpMACConf 1 }

--
-- =======================================================================================================================
-- Start sm48tat4xarpMAC group
-- =======================================================================================================================
    sm48tat4xarpMACDisableAutomaticAging   OBJECT-TYPE
               SYNTAX       AdminMode
               MAX-ACCESS   read-write
               STATUS       current
               DESCRIPTION
                   "Disable the automatic aging of dynamic entries."
                ::= {     sm48tat4xarpMAC 1 }

    sm48tat4xarpMACAgingTime  OBJECT-TYPE
               SYNTAX       Integer32 (-1 | 10..1000000)
               MAX-ACCESS   read-write
               STATUS       current
               DESCRIPTION
                   "Configure aging time by entering a value here in seconds.
                   range: 10-1000000 seconds.
                   -1: Automatic Aging is disable."
                ::= {     sm48tat4xarpMAC 2 }

--sm48tat4xarpMACLearningTable
    sm48tat4xarpMACLearningTable OBJECT-TYPE
               SYNTAX      SEQUENCE OF     SM48TAT4XARPMACLearningEntry
               MAX-ACCESS  not-accessible
               STATUS      current
               DESCRIPTION
                   "The mac learning table.
                    INDEX for this table is ifIndex which is
                    equivalent to the panel port number."
               ::= {     sm48tat4xarpMAC 3 }

    sm48tat4xarpMACLearningEntry OBJECT-TYPE
               SYNTAX          SM48TAT4XARPMACLearningEntry
               MAX-ACCESS  not-accessible
               STATUS      current
               DESCRIPTION
                   "The mac learning entry."
               INDEX    {     ifIndex  }
               ::= {     sm48tat4xarpMACLearningTable 1 }

    SM48TAT4XARPMACLearningEntry             ::= SEQUENCE {
                sm48tat4xarpMACTableLearning     INTEGER
                }

    sm48tat4xarpMACTableLearning OBJECT-TYPE
               SYNTAX      INTEGER{ auto(0), disable(1), secure(2)}
               MAX-ACCESS  read-write
               STATUS      current
               DESCRIPTION
                   "auto(0)   : Learning is done automatically as soon as a
                                frame with unknown SMAC is received.
                    disable(1): Disable, No learning is done.
                    secure(2) : Secure, Only static MAC entries are learned,
                                all other frames are dropped."
               ::= {     sm48tat4xarpMACLearningEntry 2 }

    sm48tat4xarpLearningDisabledVLANs OBJECT-TYPE
               SYNTAX      DisplayString
               MAX-ACCESS  read-write
               STATUS      current
               DESCRIPTION
                   "The Learning Disabled VLANs"
               ::= {     sm48tat4xarpMAC 4 }

--sm48tat4xarpMACStaticConfigTable
    sm48tat4xarpMACStaticConfigTable OBJECT-TYPE
               SYNTAX      SEQUENCE OF     SM48TAT4XARPMACStaticConfigEntry
               MAX-ACCESS  not-accessible
               STATUS      current
               DESCRIPTION
                   "The static Mac config table."
               ::= {     sm48tat4xarpMAC 5 }

    sm48tat4xarpMACStaticConfigEntry OBJECT-TYPE
               SYNTAX          SM48TAT4XARPMACStaticConfigEntry
               MAX-ACCESS  not-accessible
               STATUS      current
               DESCRIPTION
                   "The static Mac config entry."
               INDEX    {     sm48tat4xarpMACStaticConfigIndex  }
               ::= {     sm48tat4xarpMACStaticConfigTable 1 }

    SM48TAT4XARPMACStaticConfigEntry             ::= SEQUENCE {
                sm48tat4xarpMACStaticConfigSwitchIndex Integer32,
                sm48tat4xarpMACStaticConfigIndex       Integer32,
                sm48tat4xarpMACStaticConfigVID         Integer32,
                sm48tat4xarpMACStaticConfigMACaddress  DisplayString,
                sm48tat4xarpMACStaticConfigPortList    DisplayString,
                sm48tat4xarpMACStaticConfigRowStatus   RowStatus
                }

    sm48tat4xarpMACStaticConfigSwitchIndex OBJECT-TYPE
               SYNTAX      Integer32(1..16)
               MAX-ACCESS  not-accessible
               STATUS      current
               DESCRIPTION
                   "Switch Index."
               ::= {     sm48tat4xarpMACStaticConfigEntry 1 }



    sm48tat4xarpMACStaticConfigIndex OBJECT-TYPE
               SYNTAX      Integer32(1..64)
               MAX-ACCESS  not-accessible
               STATUS      current
               DESCRIPTION
                   "The static entries in the MAC table are shown in this table.
                    The static MAC table can contain 64 entries."
               ::= {     sm48tat4xarpMACStaticConfigEntry 2 }

    sm48tat4xarpMACStaticConfigVID OBJECT-TYPE
               SYNTAX      Integer32(1..4095)
               MAX-ACCESS  read-create
               STATUS      current
               DESCRIPTION
                   "The VLAN ID of the entry.
                    range: 1-4095."
               ::= {     sm48tat4xarpMACStaticConfigEntry 3 }

    sm48tat4xarpMACStaticConfigMACaddress OBJECT-TYPE
               SYNTAX      DisplayString
               MAX-ACCESS  read-create
               STATUS      current
               DESCRIPTION
                   "The MAC address of the entry."
               ::= {     sm48tat4xarpMACStaticConfigEntry 4 }

    sm48tat4xarpMACStaticConfigPortList OBJECT-TYPE
               SYNTAX      DisplayString
               MAX-ACCESS  read-create
               STATUS      current
               DESCRIPTION
                   "Checkmarks indicate which ports are members of the entry.
                    Check or uncheck as needed to
                    modify the entry."
               ::= {     sm48tat4xarpMACStaticConfigEntry 5 }

    sm48tat4xarpMACStaticConfigRowStatus OBJECT-TYPE
               SYNTAX      RowStatus
               MAX-ACCESS  read-create
               STATUS      current
               DESCRIPTION
                   "This object indicates the status of this entry,
                    and is used to create/delete entries. Any
                    object in an entry of this table may be modified
                    while the value of the corresponding instance
                    of this object is active(1).
                    createAndGo, notReady not supported."
               ::= {     sm48tat4xarpMACStaticConfigEntry 6 }


-- =======================================================================================================================
sm48tat4xarpSpanningTree 						OBJECT IDENTIFIER ::= { sm48tat4xarpConfiguration 18 }

sm48tat4xarpBridgeSettings                     OBJECT IDENTIFIER ::= { sm48tat4xarpSpanningTree 1 }

sm48tat4xarpSTPProtocolVersion    OBJECT-TYPE
               SYNTAX      Integer32
               MAX-ACCESS  read-write
               STATUS      current
               DESCRIPTION
                   "0:STP
				    2:RSTP
					3:MSTP"
               ::= {     sm48tat4xarpBridgeSettings 1 }

sm48tat4xarpBridgePriority    OBJECT-TYPE
               SYNTAX      Integer32
               MAX-ACCESS  read-write
               STATUS      current
               DESCRIPTION
                   "Bridge Priority, range: 0-61440, multiple of 4096."
               ::= {     sm48tat4xarpBridgeSettings 2 }

sm48tat4xarpBridgeForwardDelay    OBJECT-TYPE
               SYNTAX      Integer32
               MAX-ACCESS  read-write
               STATUS      current
               DESCRIPTION
                   "Bridge Forward Delay, range: 4-30 seconds."
               ::= {     sm48tat4xarpBridgeSettings 3 }

sm48tat4xarpBridgeMaxAge    OBJECT-TYPE
               SYNTAX      Integer32
               MAX-ACCESS  read-write
               STATUS      current
               DESCRIPTION
                   "Bridge MaxAge, range:6-40 seconds."
               ::= {     sm48tat4xarpBridgeSettings 4 }

sm48tat4xarpBridgeMaxHops    OBJECT-TYPE
               SYNTAX      Integer32
               MAX-ACCESS  read-write
               STATUS      current
               DESCRIPTION
                   "Bridge Max Hops, range:6-40 hops."
               ::= {     sm48tat4xarpBridgeSettings 5 }

sm48tat4xarpBridgetxHoldCount    OBJECT-TYPE
               SYNTAX      Integer32
               MAX-ACCESS  read-write
               STATUS      current
               DESCRIPTION
                   "Bridge Transmit Hold Count,range: 1-10 bpdu's per second. "
               ::= {     sm48tat4xarpBridgeSettings 6 }

sm48tat4xarpBridgeBPDUFilter    OBJECT-TYPE
               SYNTAX      Integer32
               MAX-ACCESS  read-write
               STATUS      current
               DESCRIPTION
                   "Bridge BPD UFilter
              		0:disable
                    1:enable					"
               ::= {     sm48tat4xarpBridgeSettings 7 }

sm48tat4xarpBridgeBPDUGuard    OBJECT-TYPE
               SYNTAX      Integer32
               MAX-ACCESS  read-write
               STATUS      current
               DESCRIPTION
                   "Bridge BPDU Guard
              		0:disable
                    1:enable					   "
               ::= {     sm48tat4xarpBridgeSettings 8 }

sm48tat4xarpBridgeerrorRecoveryDelay    OBJECT-TYPE
               SYNTAX      Integer32
               MAX-ACCESS  read-write
               STATUS      current
               DESCRIPTION
                   "Bridge error Recovery Delay
				   range:30-86400 seconds
				   0:disable
				   "
               ::= {     sm48tat4xarpBridgeSettings 9 }

sm48tat4xarpBridgeHelloTime    OBJECT-TYPE
               SYNTAX      Integer32
               MAX-ACCESS  read-write
               STATUS      current
               DESCRIPTION
                   "The interval between sending STP BPDU's. Valid values are in the range 1 to 10 seconds,
				   default:2 seconds."
               ::= {     sm48tat4xarpBridgeSettings 10 }

sm48tat4xarpMSTIMapping                        OBJECT IDENTIFIER ::= { sm48tat4xarpSpanningTree 2 }
sm48tat4xarpConfigName    OBJECT-TYPE
               SYNTAX      DisplayString
               MAX-ACCESS  read-write
               STATUS      current
               DESCRIPTION
                   "Configuration Name, identify the VLAN to MSTI mapping"
               ::= {     sm48tat4xarpMSTIMapping 1 }

sm48tat4xarpConfigRevision    OBJECT-TYPE
               SYNTAX      Integer32
               MAX-ACCESS  read-write
               STATUS      current
               DESCRIPTION
                   "Configuration Revision. range:0-65535 "
               ::= {     sm48tat4xarpMSTIMapping 2 }

sm48tat4xarpMSTIMappingVLAN                    OBJECT IDENTIFIER ::= { sm48tat4xarpSpanningTree 3 }
sm48tat4xarpConfigMstiName1    OBJECT-TYPE
               SYNTAX      DisplayString
               MAX-ACCESS  read-write
               STATUS      current
               DESCRIPTION
                   "The list of VLANs mapped to the MSTI1.
				    The VLANs can be given as a single (xx, xx being between 1 and 4094) VLAN, or a range (xx-yy), each of which must be separated with comma and/or space. "
               ::= {     sm48tat4xarpMSTIMappingVLAN 1 }

sm48tat4xarpConfigMstiName2    OBJECT-TYPE
               SYNTAX      DisplayString
               MAX-ACCESS  read-write
               STATUS      current
               DESCRIPTION
                   "The list of VLANs mapped to the MSTI2.
				    The VLANs can be given as a single (xx, xx being between 1 and 4094) VLAN, or a range (xx-yy), each of which must be separated with comma and/or space.  "
               ::= {     sm48tat4xarpMSTIMappingVLAN 2 }

sm48tat4xarpConfigMstiName3    OBJECT-TYPE
               SYNTAX      DisplayString
               MAX-ACCESS  read-write
               STATUS      current
               DESCRIPTION
                   "The list of VLANs mapped to the MSTI3.
				    The VLANs can be given as a single (xx, xx being between 1 and 4094) VLAN, or a range (xx-yy), each of which must be separated with comma and/or space. "
               ::= {     sm48tat4xarpMSTIMappingVLAN 3 }

sm48tat4xarpConfigMstiName4    OBJECT-TYPE
               SYNTAX      DisplayString
               MAX-ACCESS  read-write
               STATUS      current
               DESCRIPTION
                   "The list of VLANs mapped to the MSTI4.
				    The VLANs can be given as a single (xx, xx being between 1 and 4094) VLAN, or a range (xx-yy), each of which must be separated with comma and/or space. "
               ::= {     sm48tat4xarpMSTIMappingVLAN 4 }

sm48tat4xarpConfigMstiName5    OBJECT-TYPE
               SYNTAX      DisplayString
               MAX-ACCESS  read-write
               STATUS      current
               DESCRIPTION
                   "The list of VLANs mapped to the MSTI5.
				    The VLANs can be given as a single (xx, xx being between 1 and 4094) VLAN, or a range (xx-yy), each of which must be separated with comma and/or space. "
               ::= {     sm48tat4xarpMSTIMappingVLAN 5 }

sm48tat4xarpConfigMstiName6    OBJECT-TYPE
               SYNTAX      DisplayString
               MAX-ACCESS  read-write
               STATUS      current
               DESCRIPTION
                   "The list of VLANs mapped to the MSTI6.
				    The VLANs can be given as a single (xx, xx being between 1 and 4094) VLAN, or a range (xx-yy), each of which must be separated with comma and/or space. "
               ::= {     sm48tat4xarpMSTIMappingVLAN 6 }

sm48tat4xarpConfigMstiName7    OBJECT-TYPE
               SYNTAX      DisplayString
               MAX-ACCESS  read-write
               STATUS      current
               DESCRIPTION
                   "The list of VLANs mapped to the MSTI7.
				    The VLANs can be given as a single (xx, xx being between 1 and 4094) VLAN, or a range (xx-yy), each of which must be separated with comma and/or space. "
               ::= {     sm48tat4xarpMSTIMappingVLAN 7 }

sm48tat4xarpMSTIPriorities                     OBJECT IDENTIFIER ::= { sm48tat4xarpSpanningTree 4 }

sm48tat4xarpCSTIPriority   OBJECT-TYPE
               SYNTAX      Integer32
               MAX-ACCESS  read-write
               STATUS      current
               DESCRIPTION
                   "CSTI Priority. range: 0-61440, multiple of 4096. Lower numeric values have better priority."
               ::= {     sm48tat4xarpMSTIPriorities 1 }

sm48tat4xarpMSTI1Priority   OBJECT-TYPE
               SYNTAX      Integer32
               MAX-ACCESS  read-write
               STATUS      current
               DESCRIPTION
                   "MSTI1 Priority. range: 0-61440, multiple of 4096. Lower numeric values have better priority."
               ::= {     sm48tat4xarpMSTIPriorities 2 }

sm48tat4xarpMSTI2Priority   OBJECT-TYPE
               SYNTAX      Integer32
               MAX-ACCESS  read-write
               STATUS      current
               DESCRIPTION
                   "MSTI2 Priority. range: 0-61440, multiple of 4096. Lower numeric values have better priority."
               ::= {     sm48tat4xarpMSTIPriorities 3 }

sm48tat4xarpMSTI3Priority   OBJECT-TYPE
               SYNTAX      Integer32
               MAX-ACCESS  read-write
               STATUS      current
               DESCRIPTION
                   "MSTI3 Priority. range: 0-61440, multiple of 4096. Lower numeric values have better priority."
               ::= {     sm48tat4xarpMSTIPriorities 4 }
sm48tat4xarpMSTI4Priority   OBJECT-TYPE
               SYNTAX      Integer32
               MAX-ACCESS  read-write
               STATUS      current
               DESCRIPTION
                   "MSTI4 Priority. range: 0-61440, multiple of 4096. Lower numeric values have better priority."
               ::= {     sm48tat4xarpMSTIPriorities 5 }
sm48tat4xarpMSTI5Priority   OBJECT-TYPE
               SYNTAX      Integer32
               MAX-ACCESS  read-write
               STATUS      current
               DESCRIPTION
                   "MSTI5 Priority. range: 0-61440, multiple of 4096. Lower numeric values have better priority."
               ::= {     sm48tat4xarpMSTIPriorities 6 }

sm48tat4xarpMSTI6Priority   OBJECT-TYPE
               SYNTAX      Integer32
               MAX-ACCESS  read-write
               STATUS      current
               DESCRIPTION
                   "MSTI6 Priority. range: 0-61440, multiple of 4096. Lower numeric values have better priority."
               ::= {     sm48tat4xarpMSTIPriorities 7 }
sm48tat4xarpMSTI7Priority   OBJECT-TYPE
               SYNTAX      Integer32
               MAX-ACCESS  read-write
               STATUS      current
               DESCRIPTION
                   "MSTI7 Priority. range: 0-61440, multiple of 4096. Lower numeric values have better priority."
               ::= {     sm48tat4xarpMSTIPriorities 8 }


sm48tat4xarpCISTPorts                          OBJECT IDENTIFIER ::= { sm48tat4xarpSpanningTree 5 }

sm48tat4xarpCISTAggregatedEnable   OBJECT-TYPE
               SYNTAX      Integer32 (0|1)
               MAX-ACCESS  read-write
               STATUS      current
               DESCRIPTION
                   "CIST Port Enable. range: 0-1.
				   0:disable
				   1:enable."
               ::= {     sm48tat4xarpCISTPorts 1 }

sm48tat4xarpCISTAggregatedPathCost   OBJECT-TYPE
               SYNTAX      Integer32 (0..200000000)
               MAX-ACCESS  read-write
               STATUS      current
               DESCRIPTION
                   "CIST Port Path Cost. range: 0-200000000. 0 is Auto."
               ::= {     sm48tat4xarpCISTPorts 2 }

sm48tat4xarpCISTAggregatedPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sm48tat4xarpCISTPorts 3 }

sm48tat4xarpCISTAggregatedAdminEdge   OBJECT-TYPE
               SYNTAX      Integer32 (0|1)
               MAX-ACCESS  read-write
               STATUS      current
               DESCRIPTION
                   "CIST Port Admin Edge. range: 0-1.
				   0:Non-Edge
				   1:Edge."
               ::= {     sm48tat4xarpCISTPorts 4 }

sm48tat4xarpCISTAggregatedAutoEdge   OBJECT-TYPE
               SYNTAX      Integer32 (0|1)
               MAX-ACCESS  read-write
               STATUS      current
               DESCRIPTION
                   "CIST Port Auto Edge. range: 0-1.
				   0:disable
				   1:enable."
               ::= {     sm48tat4xarpCISTPorts 5 }

sm48tat4xarpCISTAggregatedrestrictedRole   OBJECT-TYPE
               SYNTAX      Integer32 (0|1)
               MAX-ACCESS  read-write
               STATUS      current
               DESCRIPTION
                   "CIST Port restricted Role. range: 0-1.
				   0:disable
				   1:enable."
               ::= {     sm48tat4xarpCISTPorts 6 }

sm48tat4xarpCISTAggregatedrestrictedTcn   OBJECT-TYPE
               SYNTAX      Integer32 (0|1)
               MAX-ACCESS  read-write
               STATUS      current
               DESCRIPTION
                   "CIST Port restricted Tcn. range: 0-1.
				   0:disable
				   1:enable."
               ::= {     sm48tat4xarpCISTPorts 7 }

sm48tat4xarpCISTAggregatedbpduGuard   OBJECT-TYPE
               SYNTAX      Integer32 (0|1)
               MAX-ACCESS  read-write
               STATUS      current
               DESCRIPTION
                   "CIST Port bpdu Guard. range: 0-1.
				   0:disable
				   1:enable."
               ::= {     sm48tat4xarpCISTPorts 8 }

sm48tat4xarpCISTAggregatedPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sm48tat4xarpCISTPorts 9 }


sm48tat4xarpCISTPortsTable OBJECT-TYPE
   SYNTAX      SEQUENCE OF SM48TAT4XARPCISTPortsEntry
   MAX-ACCESS  not-accessible
   STATUS      current
   DESCRIPTION
        "CIST port table."
    ::= { sm48tat4xarpCISTPorts 10 }

sm48tat4xarpCISTPortsEntry OBJECT-TYPE
    SYNTAX        SM48TAT4XARPCISTPortsEntry
    MAX-ACCESS    not-accessible
    STATUS        current
    DESCRIPTION
        "An entry in the CIST Ports Table."
    INDEX        { sm48tat4xarpCISTPortIndex }
    ::= { sm48tat4xarpCISTPortsTable 1 }

SM48TAT4XARPCISTPortsEntry ::=
    SEQUENCE {
        sm48tat4xarpCISTPortIndex                 Integer32,
        sm48tat4xarpCISTPortEnable                Integer32,
        sm48tat4xarpCISTPortPathCost              Integer32,
        sm48tat4xarpCISTPortPortPriority          Integer32,
        sm48tat4xarpCISTPortAdminEdge             Integer32,
        sm48tat4xarpCISTPortAutoEdge              Integer32,
        sm48tat4xarpCISTPortrestrictedRole        Integer32,
        sm48tat4xarpCISTPortrestrictedTcn         Integer32,
        sm48tat4xarpCISTPortbpduGuard             Integer32,
        sm48tat4xarpCISTPortPointToPoint          Integer32,
        sm48tat4xarpCISTPortRootGuard             Integer32
    }

sm48tat4xarpCISTPortIndex   OBJECT-TYPE
               SYNTAX      Integer32 (1..53)
               MAX-ACCESS  not-accessible
               STATUS      current
               DESCRIPTION
                   "CIST Port Index. range: 1-53. 53 is Aggregated Port Configuration."
               ::= {     sm48tat4xarpCISTPortsEntry 1 }

sm48tat4xarpCISTPortEnable   OBJECT-TYPE
               SYNTAX      Integer32 (0|1)
               MAX-ACCESS  read-write
               STATUS      current
               DESCRIPTION
                   "CIST Port Enable. range: 0-1.
				   0:disable
				   1:enable."
               ::= {     sm48tat4xarpCISTPortsEntry 2 }

sm48tat4xarpCISTPortPathCost   OBJECT-TYPE
               SYNTAX      Integer32 (0..200000000)
               MAX-ACCESS  read-write
               STATUS      current
               DESCRIPTION
                   "CIST Port Path Cost. range: 0-200000000. 0 is Auto."
               ::= {     sm48tat4xarpCISTPortsEntry 3 }

sm48tat4xarpCISTPortPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sm48tat4xarpCISTPortsEntry 4 }

sm48tat4xarpCISTPortAdminEdge   OBJECT-TYPE
               SYNTAX      Integer32 (0|1)
               MAX-ACCESS  read-write
               STATUS      current
               DESCRIPTION
                   "CIST Port Admin Edge. range: 0-1.
				   0:Non-Edge
				   1:Edge."
               ::= {     sm48tat4xarpCISTPortsEntry 5 }

sm48tat4xarpCISTPortAutoEdge   OBJECT-TYPE
               SYNTAX      Integer32 (0|1)
               MAX-ACCESS  read-write
               STATUS      current
               DESCRIPTION
                   "CIST Port Auto Edge. range: 0-1.
				   0:disable
				   1:enable."
               ::= {     sm48tat4xarpCISTPortsEntry 6 }

sm48tat4xarpCISTPortrestrictedRole   OBJECT-TYPE
               SYNTAX      Integer32 (0|1)
               MAX-ACCESS  read-write
               STATUS      current
               DESCRIPTION
                   "CIST Port restricted Role. range: 0-1.
				   0:disable
				   1:enable."
               ::= {     sm48tat4xarpCISTPortsEntry 7 }

sm48tat4xarpCISTPortrestrictedTcn   OBJECT-TYPE
               SYNTAX      Integer32 (0|1)
               MAX-ACCESS  read-write
               STATUS      current
               DESCRIPTION
                   "CIST Port restricted Tcn. range: 0-1.
				   0:disable
				   1:enable."
               ::= {     sm48tat4xarpCISTPortsEntry 8 }

sm48tat4xarpCISTPortbpduGuard   OBJECT-TYPE
               SYNTAX      Integer32 (0|1)
               MAX-ACCESS  read-write
               STATUS      current
               DESCRIPTION
                   "CIST Port bpdu Guard. range: 0-1.
				   0:disable
				   1:enable."
               ::= {     sm48tat4xarpCISTPortsEntry 9 }

sm48tat4xarpCISTPortPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sm48tat4xarpCISTPortsEntry 10 }

sm48tat4xarpCISTPortRootGuard   OBJECT-TYPE
               SYNTAX      Integer32 (0|1)
               MAX-ACCESS  read-write
               STATUS      current
               DESCRIPTION
                   "CIST Port root guard. range: 0-1.
				   0:disable
				   1:enable."
               ::= {     sm48tat4xarpCISTPortsEntry 11 }

sm48tat4xarpMSTIPorts                          OBJECT IDENTIFIER ::= { sm48tat4xarpSpanningTree 6 }


sm48tat4xarpMSTIAggregatedPortsTable OBJECT-TYPE
   SYNTAX      SEQUENCE OF SM48TAT4XARPMSTIAggregatedPortsEntry
   MAX-ACCESS  not-accessible
   STATUS      current
   DESCRIPTION
       "A table of MSTI ports."
    ::= { sm48tat4xarpMSTIPorts 1 }

sm48tat4xarpMSTIAggregatedPortsEntry OBJECT-TYPE
    SYNTAX        SM48TAT4XARPMSTIAggregatedPortsEntry
    MAX-ACCESS    not-accessible
    STATUS        current
    DESCRIPTION
        "An entry in the MSTI ports Table."
    INDEX        { sm48tat4xarpMSTIAggregatedPortsMSTIndex }
    ::= { sm48tat4xarpMSTIAggregatedPortsTable 1 }

SM48TAT4XARPMSTIAggregatedPortsEntry ::=
    SEQUENCE {
        sm48tat4xarpMSTIAggregatedPortsMSTIndex                        Integer32,
        sm48tat4xarpMSTIAggregatedPortsPathCost                        Integer32,
        sm48tat4xarpMSTIAggregatedPortsPortPriority                    Integer32
    }

sm48tat4xarpMSTIAggregatedPortsMSTIndex OBJECT-TYPE
   SYNTAX      Integer32 (1..7)
   MAX-ACCESS  not-accessible
   STATUS      current
   DESCRIPTION
       "MST index, range:1-7"
   ::= {sm48tat4xarpMSTIAggregatedPortsEntry 1 }

sm48tat4xarpMSTIAggregatedPortsPathCost   OBJECT-TYPE
   SYNTAX      Integer32 (0..200000000)
   MAX-ACCESS  read-write
   STATUS      current
   DESCRIPTION
       "MST Path Cost. range: 0-200000000. 0 is Auto."
   ::= {sm48tat4xarpMSTIAggregatedPortsEntry 3 }

sm48tat4xarpMSTIAggregatedPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sm48tat4xarpMSTIAggregatedPortsEntry 4 }


sm48tat4xarpMSTIPortsTable OBJECT-TYPE
   SYNTAX      SEQUENCE OF SM48TAT4XARPMSTIPortsEntry
   MAX-ACCESS  not-accessible
   STATUS      current
   DESCRIPTION
       "A table of MSTI ports."
    ::= { sm48tat4xarpMSTIPorts 2 }

sm48tat4xarpMSTIPortsEntry OBJECT-TYPE
    SYNTAX        SM48TAT4XARPMSTIPortsEntry
    MAX-ACCESS    not-accessible
    STATUS        current
    DESCRIPTION
        "An entry in the MSTI ports Table."
    INDEX        { sm48tat4xarpMSTIPortsMSTIndex, sm48tat4xarpMSTIPortsPortIndex }
    ::= { sm48tat4xarpMSTIPortsTable 1 }

SM48TAT4XARPMSTIPortsEntry ::=
    SEQUENCE {
        sm48tat4xarpMSTIPortsMSTIndex                        Integer32,
        sm48tat4xarpMSTIPortsPortIndex                       Integer32,
        sm48tat4xarpMSTIPortsPathCost                        Integer32,
        sm48tat4xarpMSTIPortsPortPriority                    Integer32
    }

sm48tat4xarpMSTIPortsMSTIndex OBJECT-TYPE
   SYNTAX      Integer32 (1..7)
   MAX-ACCESS  not-accessible
   STATUS      current
   DESCRIPTION
       "MST index, range:1-7"
   ::= {sm48tat4xarpMSTIPortsEntry 1 }

sm48tat4xarpMSTIPortsPortIndex OBJECT-TYPE
   SYNTAX      Integer32 (1..53)
   MAX-ACCESS  not-accessible
   STATUS      current
   DESCRIPTION
       "Port index, range 1-53, 53 is Aggregated Ports Configuration."
   ::= {sm48tat4xarpMSTIPortsEntry 2 }

sm48tat4xarpMSTIPortsPathCost   OBJECT-TYPE
   SYNTAX      Integer32 (0..200000000)
   MAX-ACCESS  read-write
   STATUS      current
   DESCRIPTION
       "MST Path Cost. range: 0-200000000. 0 is Auto."
   ::= {sm48tat4xarpMSTIPortsEntry 3 }

sm48tat4xarpMSTIPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sm48tat4xarpMSTIPortsEntry 4 }

-- =======================================================================================================================
sm48tat4xarpPrivateVLANs 						OBJECT IDENTIFIER ::= { sm48tat4xarpConfiguration 19 }

sm48tat4xarpPVLANMembershipTable  OBJECT-TYPE
   SYNTAX      SEQUENCE OF SM48TAT4XARPPVLANMembershipEntry
   MAX-ACCESS  not-accessible
   STATUS      current
   DESCRIPTION
       "A table of Private VLAN Membership."
 ::= { sm48tat4xarpPrivateVLANs 1 }

sm48tat4xarpPVLANMembershipEntry OBJECT-TYPE
    SYNTAX        SM48TAT4XARPPVLANMembershipEntry
    MAX-ACCESS    not-accessible
    STATUS        current
    DESCRIPTION
        "An entry in the private VLAN table."
    INDEX        { sm48tat4xarpPVLANMembershipIndex }
    ::= { sm48tat4xarpPVLANMembershipTable 1 }

SM48TAT4XARPPVLANMembershipEntry ::=
    SEQUENCE {
        sm48tat4xarpPVLANMembershipIndex                    Integer32,
        sm48tat4xarpPVLANID                                 Integer32,
        sm48tat4xarpPVLANMembers                            DisplayString,
        sm48tat4xarpPVLANRowStatus                          RowStatus
    }

sm48tat4xarpPVLANMembershipIndex OBJECT-TYPE
   SYNTAX      Integer32 (1..28)
   MAX-ACCESS  not-accessible
   STATUS      current
   DESCRIPTION
       "PVLAN membership index. Range:1-28."
   ::= {sm48tat4xarpPVLANMembershipEntry 1 }

sm48tat4xarpPVLANID OBJECT-TYPE
   SYNTAX      Integer32 (1..28)
   MAX-ACCESS  read-create
   STATUS      current
   DESCRIPTION
       "PVLAN ID. Range:1-28."
   ::= {sm48tat4xarpPVLANMembershipEntry 2 }

sm48tat4xarpPVLANMembers OBJECT-TYPE
   SYNTAX      DisplayString
   MAX-ACCESS  read-create
   STATUS      current
   DESCRIPTION
       "PVLAN Members. Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1',
        then that port is included in the set of ports; the port
        is not included if its bit has a value of '0'."
   ::= {sm48tat4xarpPVLANMembershipEntry 3 }

sm48tat4xarpPVLANRowStatus OBJECT-TYPE
   SYNTAX      RowStatus
   MAX-ACCESS  read-create
   STATUS      current
   DESCRIPTION
       "PVLAN Row Status."
   ::= {sm48tat4xarpPVLANMembershipEntry 4 }

sm48tat4xarpPVLANPortIsolationTable  OBJECT-TYPE
   SYNTAX      SEQUENCE OF SM48TAT4XARPPVLANPortIsolationEntry
   MAX-ACCESS  not-accessible
   STATUS      current
   DESCRIPTION
       "A table of Private VLAN Port Isolation."
 ::= { sm48tat4xarpPrivateVLANs 2 }

sm48tat4xarpPVLANPortIsolationEntry OBJECT-TYPE
    SYNTAX        SM48TAT4XARPPVLANPortIsolationEntry
    MAX-ACCESS    not-accessible
    STATUS        current
    DESCRIPTION
        "An entry in the private VLAN table."
    INDEX        { sm48tat4xarpPVLANPortIsolationIndex }
    ::= { sm48tat4xarpPVLANPortIsolationTable 1 }

SM48TAT4XARPPVLANPortIsolationEntry ::=
    SEQUENCE {
        sm48tat4xarpPVLANPortIsolationIndex                 Integer32,
        sm48tat4xarpPVLANPortIsolationPortMembers           Integer32
    }

sm48tat4xarpPVLANPortIsolationIndex OBJECT-TYPE
   SYNTAX      Integer32 (1..28)
   MAX-ACCESS  not-accessible
   STATUS      current
   DESCRIPTION
       "PVLAN Port Isolation Index. Range:1-28."
   ::= {sm48tat4xarpPVLANPortIsolationEntry 1 }

sm48tat4xarpPVLANPortIsolationPortMembers OBJECT-TYPE
   SYNTAX      Integer32 (0|1)
   MAX-ACCESS  read-write
   STATUS      current
   DESCRIPTION
       "PVLAN Port Isolation Port Members enable/disable. Range:0-1.
	   1:Port Isolation enable  on that port.
	   0:Port Isolation disable on that port."
   ::= {sm48tat4xarpPVLANPortIsolationEntry 2 }

-- =======================================================================================================================


sm48tat4xarpsFlow 						OBJECT IDENTIFIER ::= { sm48tat4xarpConfiguration 20 }

      sm48tat4xarpsFlowVersion OBJECT-TYPE
              SYNTAX      SnmpAdminString
              MAX-ACCESS  read-only
              STATUS      current
              DESCRIPTION "Uniquely identifies the version and implementation of this MIB. The version string must have the following structure: <MIB Version>;<Organization>;<Software Revision> where: <MIB Version>  must be '1.3', the version of this MIB.
                    <Organization> the name of the organization responsible for the agent implementation. <Revision>     the specific software build of this agent.
                 As an example, the string '1.3;InMon Corp.;2.1.1' indicates that this agent implements version '1.2' of the SFLOW MIB, that
                 it was developed by 'InMon Corp.' and that the software build is '2.1.1'.
                 The MIB Version will change with each revision of the SFLOW MIB.
                 Management entities must check the MIB Version and not attempt to manage agents with MIB Versions greater than that for which
                 they were designed.
                 Note: The sFlow Datagram Format has an independent version number which may change independently from <MIB Version>.
                       <MIB Version> applies to the structure and semantics of the SFLOW MIB only." DEFVAL { "1.3;;" }
              ::= { sm48tat4xarpsFlow 1 }

      sm48tat4xarpsFlowAgentAddressType OBJECT-TYPE
              SYNTAX      InetAddressType
              MAX-ACCESS  read-only
              STATUS      current
              DESCRIPTION "The address type of the address associated with this agent. Only ipv4 and ipv6 types are supported. ipv4:1, ipv6:2."
              ::= { sm48tat4xarpsFlow 2 }

      sm48tat4xarpsFlowAgentAddress OBJECT-TYPE
              SYNTAX      IpAddress
              MAX-ACCESS  read-write
              STATUS      current
              DESCRIPTION "The IP address associated with this agent. In the case of a multi-homed agent, this should be the loopback address of the
                 agent. The sFlowAgent address must provide SNMP connectivity to the agent. The address should be an invariant that does not
                 change as interfaces are reconfigured, enabled, disabled, added or removed. A manager should be able to use the
                 sFlowAgentAddress as a unique key that will identify this agent over extended periods of time so that a history can
                 be maintained."
              ::= { sm48tat4xarpsFlow 3 }
      --
      -- Receiver Table
      --
      sm48tat4xarpsFlowRcvrTable OBJECT-TYPE
              SYNTAX      SEQUENCE OF SM48TAT4XARPSFlowRcvrEntry
              MAX-ACCESS  not-accessible
              STATUS      current
              DESCRIPTION "A table of the receivers of sFlow information."
              ::= { sm48tat4xarpsFlow 4 }

      sm48tat4xarpsFlowRcvrEntry OBJECT-TYPE
              SYNTAX SM48TAT4XARPSFlowRcvrEntry
              MAX-ACCESS  not-accessible
              STATUS      current
              DESCRIPTION "Attributes of an sFlow Receiver."
              INDEX { sm48tat4xarpsFlowRcvrIndex }
              ::= { sm48tat4xarpsFlowRcvrTable 1 }

      SM48TAT4XARPSFlowRcvrEntry ::= SEQUENCE {
              sm48tat4xarpsFlowRcvrIndex                    Integer32,
              sm48tat4xarpsFlowRcvrOwner                    OwnerString,
              sm48tat4xarpsFlowRcvrTimeout                  Integer32,
              sm48tat4xarpsFlowRcvrMaximumDatagramSize      Integer32,
              sm48tat4xarpsFlowRcvrAddressType              InetAddressType,
              sm48tat4xarpsFlowRcvrAddress                  IpAddress,
              sm48tat4xarpsFlowRcvrPort                     Integer32,
              sm48tat4xarpsFlowRcvrDatagramVersion          Integer32 }

      sm48tat4xarpsFlowRcvrIndex OBJECT-TYPE
              SYNTAX      Integer32 (1..65535)
              MAX-ACCESS  not-accessible
              STATUS      current
              DESCRIPTION "Index into sFlowReceiverTable."
              ::= { sm48tat4xarpsFlowRcvrEntry 1 }

      sm48tat4xarpsFlowRcvrOwner OBJECT-TYPE
              SYNTAX      OwnerString
              MAX-ACCESS  read-write
              STATUS      current
              DESCRIPTION "The entity making use of this sFlowRcvrTable entry. The empty string indicates that the entry is currently unclaimed.
                 An entity wishing to claim an sFlowRcvrTable entry must ensure that the entry is unclaimed before trying to claim it.
                 The entry is claimed by setting the owner string. The entry must be claimed before any changes can be made to other sampler
                 objects.
                 In order to avoid a race condition, the entity taking control of the sampler must set both the owner and a value for
                 sFlowRcvrTimeout in the same SNMP set request.
                 When a management entity is finished using the sampler, it should set the value of sFlowRcvrOwner back to unclaimed.
                 The agent must restore all other entities this row to their default values when the owner is set to unclaimed. It must
                 also free all other resources associated with this sFlowRcvrTable entry.
                 This mechanism provides no enforcement and relies on the cooperation of management entities in order to ensure that
                 competition for a receiver entry is fairly resolved." DEFVAL { "" }
              ::= { sm48tat4xarpsFlowRcvrEntry 2 }

      sm48tat4xarpsFlowRcvrTimeout OBJECT-TYPE
              SYNTAX      Integer32
              MAX-ACCESS  read-write
              STATUS      current
              DESCRIPTION "The time (in seconds) remaining before the sampler is released and stops sampling. When set, the owner establishes control
                 for the specified period. When read, the remaining time in the interval is returned.
                 A management entity wanting to maintain control of the sampler is responsible for setting a new value before the old one
                 expires.
                 When the interval expires, the agent is responsible for restoring all other entities in this row to their default
                 values. It must also free all other resources associated with this sFlowRcvrTable entry." DEFVAL { 0 }
              ::= { sm48tat4xarpsFlowRcvrEntry 3 }

      sm48tat4xarpsFlowRcvrMaximumDatagramSize OBJECT-TYPE
              SYNTAX      Integer32
              MAX-ACCESS  read-write
              STATUS      current
              DESCRIPTION "The maximum number of data bytes that can be sent in a single sample datagram. The manager should set this value to avoid fragmentation of the sFlow datagrams." DEFVAL { 1400 }
              ::= { sm48tat4xarpsFlowRcvrEntry 4 }

      sm48tat4xarpsFlowRcvrAddressType OBJECT-TYPE
              SYNTAX      InetAddressType
              MAX-ACCESS  read-write
              STATUS      current
              DESCRIPTION "The type of sFlowRcvrCollectorAddress." DEFVAL { ipv4 }
              ::= { sm48tat4xarpsFlowRcvrEntry 5 }

      sm48tat4xarpsFlowRcvrAddress OBJECT-TYPE
              SYNTAX      IpAddress
              MAX-ACCESS  read-write
              STATUS      current
              DESCRIPTION "The IP address of the sFlow collector. If set to 0.0.0.0 not sFlow datagrams will be sent." DEFVAL { '00000000'h }  -- 0.0.0.0
              ::= { sm48tat4xarpsFlowRcvrEntry 6 }

      sm48tat4xarpsFlowRcvrPort OBJECT-TYPE
              SYNTAX      Integer32
              MAX-ACCESS  read-write
              STATUS      current
              DESCRIPTION "The destination port for sFlow datagrams." DEFVAL { 6343 }
              ::= { sm48tat4xarpsFlowRcvrEntry 7 }

      sm48tat4xarpsFlowRcvrDatagramVersion OBJECT-TYPE
              SYNTAX      Integer32
              MAX-ACCESS  read-write
              STATUS      current
              DESCRIPTION "The version of sFlow datagrams that should be sent.
                 When set to a value not support by the agent, the agent should adjust the value to the highest supported value less than the
                 requested value, or return an SNMP bad value error if no such value exists." DEFVAL { 5 }
              ::= { sm48tat4xarpsFlowRcvrEntry 8 }

      --
      -- Flow Sampling Table
      --
      sm48tat4xarpsFlowFsTable OBJECT-TYPE
              SYNTAX      SEQUENCE OF SM48TAT4XARPSFlowFsEntry
              MAX-ACCESS  not-accessible
              STATUS      current
              DESCRIPTION "A table of the flow samplers within a device."
              ::= { sm48tat4xarpsFlow 5 }

      sm48tat4xarpsFlowFsEntry OBJECT-TYPE
              SYNTAX      SM48TAT4XARPSFlowFsEntry
              MAX-ACCESS  not-accessible
              STATUS      current
              DESCRIPTION "Attributes of a flow sampler."
              INDEX { sm48tat4xarpsFlowFsDataSource, sm48tat4xarpsFlowFsInstance }
              ::= { sm48tat4xarpsFlowFsTable 1 }

      SM48TAT4XARPSFlowFsEntry ::= SEQUENCE {
              sm48tat4xarpsFlowFsDataSource               Integer32,
              sm48tat4xarpsFlowFsInstance                 Integer32,
              sm48tat4xarpsFlowFsReceiver                 Integer32,
              sm48tat4xarpsFlowFsPacketSamplingRate       Integer32,
              sm48tat4xarpsFlowFsMaximumHeaderSize        Integer32,
              sm48tat4xarpsFlowFsType                     Integer32
              }

      sm48tat4xarpsFlowFsDataSource OBJECT-TYPE
              SYNTAX      Integer32(1..65535)
              MAX-ACCESS  not-accessible
              STATUS      current
              DESCRIPTION "sFlowDataSource for this flow sampler."
              ::= { sm48tat4xarpsFlowFsEntry 1 }

      sm48tat4xarpsFlowFsInstance OBJECT-TYPE
              SYNTAX      Integer32 (1..65535)
              MAX-ACCESS  not-accessible
              STATUS      current
              DESCRIPTION "The sFlow instance for this flow sampler."
              ::= { sm48tat4xarpsFlowFsEntry 2 }

      sm48tat4xarpsFlowFsReceiver OBJECT-TYPE
              SYNTAX      Integer32
              MAX-ACCESS  read-write
              STATUS      current
              DESCRIPTION "The SFlowReceiver for this flow sampler." DEFVAL { 0 }
              ::= { sm48tat4xarpsFlowFsEntry 3 }

      sm48tat4xarpsFlowFsPacketSamplingRate OBJECT-TYPE
              SYNTAX      Integer32
              MAX-ACCESS  read-write
              STATUS      current
              DESCRIPTION "The statistical sampling rate for packet sampling from this source.
                 Set to N to sample 1/Nth of the packets in the monitored flows. An agent should choose its own algorithm to introduce variance
                 into the sampling so that exactly every Nth packet is not counted. A sampling rate of 1 counts all packets. A sampling
                 rate of 0 disables sampling.
                 The agent is permitted to have minimum and maximum allowable values for the sampling rate. A minimum rate lets the agent
                 designer set an upper bound on the overhead associated with sampling, and a maximum rate may be the result of hardware
                 restrictions (such as counter size). In addition not all values between the maximum and minimum may be realizable as the
                 sampling rate (again because of implementation considerations).
                 When the sampling rate is set the agent is free to adjust the value so that it lies between the maximum and minimum values
                 and has the closest achievable value.
                 When read, the agent must return the actual sampling rate it will be using (after the adjustments previously described). The
                 sampling algorithm must converge so that over time the number of packets sampled approaches 1/Nth of the total number of
                 packets in the monitored flows." DEFVAL { 0 }
              ::= { sm48tat4xarpsFlowFsEntry 4 }

      sm48tat4xarpsFlowFsMaximumHeaderSize OBJECT-TYPE
              SYNTAX      Integer32
              MAX-ACCESS  read-write
              STATUS      current
              DESCRIPTION "The maximum number of bytes that should be copied from a sampled packet. The agent may have an internal maximum and
                 minimum permissible sizes. If an attempt is made to set this value outside the permissible range then the agent should
                 adjust the value to the closest permissible value." DEFVAL { 128 }
              ::= { sm48tat4xarpsFlowFsEntry 5 }

      sm48tat4xarpsFlowFsType OBJECT-TYPE
              SYNTAX      Integer32
              MAX-ACCESS  read-write
              STATUS      current
              DESCRIPTION "Flow Sample Type.
			  1:Rx
			  2:Tx
			  3:All."
			  DEFVAL { 2 }
              ::= { sm48tat4xarpsFlowFsEntry 6 }
      --
      -- Counter Polling Table
      --
      sm48tat4xarpsFlowCpTable OBJECT-TYPE
              SYNTAX      SEQUENCE OF SM48TAT4XARPSFlowCpEntry
              MAX-ACCESS  not-accessible
              STATUS      current
              DESCRIPTION "A table of the counter pollers within a device."
              ::= { sm48tat4xarpsFlow 6 }

      sm48tat4xarpsFlowCpEntry OBJECT-TYPE
              SYNTAX      SM48TAT4XARPSFlowCpEntry
              MAX-ACCESS  not-accessible
              STATUS      current
              DESCRIPTION "Attributes of a counter poller."
              INDEX { sm48tat4xarpsFlowCpDataSource, sm48tat4xarpsFlowCpInstance }
              ::= { sm48tat4xarpsFlowCpTable 1 }

      SM48TAT4XARPSFlowCpEntry ::= SEQUENCE {
              sm48tat4xarpsFlowCpDataSource               Integer32,
              sm48tat4xarpsFlowCpInstance                 Integer32,
              sm48tat4xarpsFlowCpReceiver                 Integer32,
              sm48tat4xarpsFlowCpInterval                 Integer32
              }

      sm48tat4xarpsFlowCpDataSource OBJECT-TYPE
              SYNTAX      Integer32(1..65535)
              MAX-ACCESS  not-accessible
              STATUS      current
              DESCRIPTION "Identifies the source of the data for the counter poller."
              ::= { sm48tat4xarpsFlowCpEntry 1 }

      sm48tat4xarpsFlowCpInstance OBJECT-TYPE
              SYNTAX      Integer32 (1..65535)
              MAX-ACCESS  not-accessible
              STATUS      current
              DESCRIPTION "The sFlowInstance for this counter poller."
              ::= { sm48tat4xarpsFlowCpEntry 2 }

      sm48tat4xarpsFlowCpReceiver OBJECT-TYPE
              SYNTAX      Integer32
              MAX-ACCESS  read-write
              STATUS      current
              DESCRIPTION "The SFlowReciever associated with this counter poller." DEFVAL { 0 }
              ::= { sm48tat4xarpsFlowCpEntry 3 }

      sm48tat4xarpsFlowCpInterval OBJECT-TYPE
              SYNTAX      Integer32
              MAX-ACCESS  read-write
              STATUS      current
              DESCRIPTION "The maximum number of seconds between successive samples of the counters associated with this data source. A sampling interval
                 of 0 disables counter sampling.
                 The agent is permitted to have minimum and maximum allowable values for the counter polling interval. A minimum interval
                 lets the agent designer set an upper bound on the overhead associated with polling, and a maximum interval may be the
                 result of implementation restrictions (such as counter size). In addition not all values between the maximum and minimum may
                 be realizable as the sampling interval (again because of implementation considerations).
                 When the sampling rate is set the agent is free to adjust the value so that it lies between the maximum and minimum values
                 and has the closest achievable value.
                 When read, the agent must return the actual sampling interval it will be using (after the adjustments previously described).
                 The sampling algorithm must converge so that over time the number of packets sampled approaches 1/Nth of the total number
                 of packets in the monitored flows." DEFVAL { 0 }
              ::= { sm48tat4xarpsFlowCpEntry 4 }

sm48tat4xarpLLDP                  OBJECT IDENTIFIER ::= { sm48tat4xarpConfiguration 21 }

    sm48tat4xarpLLDPConfTable OBJECT-TYPE
               SYNTAX      SEQUENCE OF     SM48TAT4XARPLLDPConfEntry
               MAX-ACCESS  not-accessible
               STATUS      current
               DESCRIPTION
                   " "
               ::= {     sm48tat4xarpLLDP 1 }

    sm48tat4xarpLLDPConfEntry OBJECT-TYPE
               SYNTAX          SM48TAT4XARPLLDPConfEntry
               MAX-ACCESS  not-accessible
               STATUS      current
               DESCRIPTION
                   " "
               INDEX    {    sm48tat4xarpLLDPIndex  }
               ::= {     sm48tat4xarpLLDPConfTable 1 }

    SM48TAT4XARPLLDPConfEntry             ::= SEQUENCE {
         sm48tat4xarpLLDPIndex        Integer32,
         sm48tat4xarpLLDPMode         Integer32,
         sm48tat4xarpLLDPCDPAware     Integer32,
         sm48tat4xarpLLDPTrap         Integer32,
         sm48tat4xarpLLDPPortDescr    Integer32,
		 sm48tat4xarpLLDPSysName      Integer32,
		 sm48tat4xarpLLDPSysDescr     Integer32,
		 sm48tat4xarpLLDPSysCapa      Integer32,
		 sm48tat4xarpLLDPMgmtAddr     Integer32
    }

    sm48tat4xarpLLDPIndex OBJECT-TYPE
               SYNTAX      Integer32(1..65535)
               MAX-ACCESS  read-write
               STATUS      current
               DESCRIPTION
                   "LLDP configuration index."
               ::= {     sm48tat4xarpLLDPConfEntry 1 }

    sm48tat4xarpLLDPMode OBJECT-TYPE
               SYNTAX      Integer32
               MAX-ACCESS  read-write
               STATUS      current
               DESCRIPTION
                   "0:Disable
		   1:Tx only
		   2:Rx only
		   3:Enabled"
               ::= {     sm48tat4xarpLLDPConfEntry 2 }

    sm48tat4xarpLLDPCDPAware OBJECT-TYPE
               SYNTAX      Integer32
               MAX-ACCESS  read-write
               STATUS      current
               DESCRIPTION
                   "0:Disable
		   1:Enable"
               ::= {     sm48tat4xarpLLDPConfEntry 3 }

    sm48tat4xarpLLDPTrap OBJECT-TYPE
               SYNTAX      Integer32
               MAX-ACCESS  read-write
               STATUS      current
               DESCRIPTION
               "0:Disable
		        1:Enable"
               ::= {     sm48tat4xarpLLDPConfEntry 4 }

    sm48tat4xarpLLDPPortDescr OBJECT-TYPE
               SYNTAX      Integer32
               MAX-ACCESS  read-write
               STATUS      current
               DESCRIPTION
                   "0:Disable
		   1:Enable"
               ::= {     sm48tat4xarpLLDPConfEntry 5 }

    sm48tat4xarpLLDPSysName OBJECT-TYPE
               SYNTAX      Integer32
               MAX-ACCESS  read-write
               STATUS      current
               DESCRIPTION
                   "0:Disable
		   1:Enable"
               ::= {     sm48tat4xarpLLDPConfEntry 6 }

    sm48tat4xarpLLDPSysDescr OBJECT-TYPE
               SYNTAX      Integer32
               MAX-ACCESS  read-write
               STATUS      current
               DESCRIPTION
                   "0:Disable
		   1:Enable"
               ::= {     sm48tat4xarpLLDPConfEntry 7 }

    sm48tat4xarpLLDPSysCapa OBJECT-TYPE
               SYNTAX      Integer32
               MAX-ACCESS  read-write
               STATUS      current
               DESCRIPTION
                   "0:Disable
		   1:Enable"
               ::= {     sm48tat4xarpLLDPConfEntry 8 }

    sm48tat4xarpLLDPMgmtAddr OBJECT-TYPE
               SYNTAX      Integer32
               MAX-ACCESS  read-write
               STATUS      current
               DESCRIPTION
                   "0:Disable
		   1:Enable"
               ::= {     sm48tat4xarpLLDPConfEntry 9 }

sm48tat4xarpLLDPMEDCoordinatesLocation                          OBJECT IDENTIFIER ::= { sm48tat4xarpLLDP 2 }

sm48tat4xarpLLDPMEDLatitude   OBJECT-TYPE
   SYNTAX      DisplayString
   MAX-ACCESS  read-write
   STATUS      current
   DESCRIPTION
	   "Latitude SHOULD be normalized to within 0-90 degrees with a maximum of 4 digits."
   ::= { sm48tat4xarpLLDPMEDCoordinatesLocation 2 }

sm48tat4xarpLLDPMEDLatitudeDirection OBJECT-TYPE
   SYNTAX      Integer32(0|1)
   MAX-ACCESS  read-write
   STATUS      current
   DESCRIPTION
       "0:North
	    1:South"
   ::= { sm48tat4xarpLLDPMEDCoordinatesLocation 3 }

sm48tat4xarpLLDPMEDLongitude   OBJECT-TYPE
   SYNTAX      DisplayString
   MAX-ACCESS  read-write
   STATUS      current
   DESCRIPTION
	   "Longitude SHOULD be normalized to within 0-180 degrees with a maximum of 4 digits."
   ::= { sm48tat4xarpLLDPMEDCoordinatesLocation 4 }

sm48tat4xarpLLDPMEDLongitudeDirection OBJECT-TYPE
   SYNTAX      Integer32(0|1)
   MAX-ACCESS  read-write
   STATUS      current
   DESCRIPTION
       "0:East
	    1:West"
   ::= { sm48tat4xarpLLDPMEDCoordinatesLocation 5 }

sm48tat4xarpLLDPMEDAltitude   OBJECT-TYPE
   SYNTAX      DisplayString
   MAX-ACCESS  read-write
   STATUS      current
   DESCRIPTION
	   "Altitude SHOULD be normalized to within -2097151.9 to 2097151.9 with a maximum of 1 digits."
   ::= { sm48tat4xarpLLDPMEDCoordinatesLocation 6 }

sm48tat4xarpLLDPMEDAltitudeType OBJECT-TYPE
   SYNTAX      Integer32(1|2)
   MAX-ACCESS  read-write
   STATUS      current
   DESCRIPTION
       "1:Meters
	    2:Floors"
   ::= { sm48tat4xarpLLDPMEDCoordinatesLocation 7 }

sm48tat4xarpLLDPMEDMapDatum OBJECT-TYPE
   SYNTAX      Integer32(0..2)
   MAX-ACCESS  read-write
   STATUS      current
   DESCRIPTION
       "The Map Datum is used for the coordinates given in these options:
	    1:WGS84
	    2:NAD83/NAVD88
	    3:NAD83/MLLW
		"
   ::= { sm48tat4xarpLLDPMEDCoordinatesLocation 8 }

sm48tat4xarpLLDPMEDCivicAddressLocation                          OBJECT IDENTIFIER ::= { sm48tat4xarpLLDP 4 }

sm48tat4xarpLLDPMEDCivicAddressLocationCountryCode   OBJECT-TYPE
   SYNTAX      DisplayString
   MAX-ACCESS  read-write
   STATUS      current
   DESCRIPTION
	   " "
   ::= { sm48tat4xarpLLDPMEDCivicAddressLocation 2 }

sm48tat4xarpLLDPMEDCivicAddressLocationStateProvince   OBJECT-TYPE
   SYNTAX      DisplayString
   MAX-ACCESS  read-write
   STATUS      current
   DESCRIPTION
	   " "
   ::= { sm48tat4xarpLLDPMEDCivicAddressLocation 3 }

sm48tat4xarpLLDPMEDCivicAddressLocationCounty   OBJECT-TYPE
   SYNTAX      DisplayString
   MAX-ACCESS  read-write
   STATUS      current
   DESCRIPTION
	   " "
   ::= { sm48tat4xarpLLDPMEDCivicAddressLocation 4 }

sm48tat4xarpLLDPMEDCivicAddressLocationCity   OBJECT-TYPE
   SYNTAX      DisplayString
   MAX-ACCESS  read-write
   STATUS      current
   DESCRIPTION
	   " "
   ::= { sm48tat4xarpLLDPMEDCivicAddressLocation 5 }

sm48tat4xarpLLDPMEDCivicAddressLocationCityDistrict   OBJECT-TYPE
   SYNTAX      DisplayString
   MAX-ACCESS  read-write
   STATUS      current
   DESCRIPTION
	   " "
   ::= { sm48tat4xarpLLDPMEDCivicAddressLocation 6 }

sm48tat4xarpLLDPMEDCivicAddressLocationBlockNeighborhood   OBJECT-TYPE
   SYNTAX      DisplayString
   MAX-ACCESS  read-write
   STATUS      current
   DESCRIPTION
	   " "
   ::= { sm48tat4xarpLLDPMEDCivicAddressLocation 7 }

sm48tat4xarpLLDPMEDCivicAddressLocationStreet   OBJECT-TYPE
   SYNTAX      DisplayString
   MAX-ACCESS  read-write
   STATUS      current
   DESCRIPTION
	   " "
   ::= { sm48tat4xarpLLDPMEDCivicAddressLocation 8 }

sm48tat4xarpLLDPMEDCivicAddressLocationLeadingStreetDirection   OBJECT-TYPE
   SYNTAX      DisplayString
   MAX-ACCESS  read-write
   STATUS      current
   DESCRIPTION
	   " "
   ::= { sm48tat4xarpLLDPMEDCivicAddressLocation 9 }

sm48tat4xarpLLDPMEDCivicAddressLocationTrailingStreetSuffix   OBJECT-TYPE
   SYNTAX      DisplayString
   MAX-ACCESS  read-write
   STATUS      current
   DESCRIPTION
	   " "
   ::= { sm48tat4xarpLLDPMEDCivicAddressLocation 10 }

sm48tat4xarpLLDPMEDCivicAddressLocationStreetSuffix   OBJECT-TYPE
   SYNTAX      DisplayString
   MAX-ACCESS  read-write
   STATUS      current
   DESCRIPTION
	   " "
   ::= { sm48tat4xarpLLDPMEDCivicAddressLocation 11 }

sm48tat4xarpLLDPMEDCivicAddressLocationHouseNo   OBJECT-TYPE
   SYNTAX      DisplayString
   MAX-ACCESS  read-write
   STATUS      current
   DESCRIPTION
	   " "
   ::= { sm48tat4xarpLLDPMEDCivicAddressLocation 12 }

sm48tat4xarpLLDPMEDCivicAddressLocationHouseNoSuffix   OBJECT-TYPE
   SYNTAX      DisplayString
   MAX-ACCESS  read-write
   STATUS      current
   DESCRIPTION
	   " "
   ::= { sm48tat4xarpLLDPMEDCivicAddressLocation 13 }

sm48tat4xarpLLDPMEDCivicAddressLocationLandmark   OBJECT-TYPE
   SYNTAX      DisplayString
   MAX-ACCESS  read-write
   STATUS      current
   DESCRIPTION
	   " "
   ::= { sm48tat4xarpLLDPMEDCivicAddressLocation 14 }

sm48tat4xarpLLDPMEDCivicAddressLocationAdditionalLocationInfo   OBJECT-TYPE
   SYNTAX      DisplayString
   MAX-ACCESS  read-write
   STATUS      current
   DESCRIPTION
	   " "
   ::= { sm48tat4xarpLLDPMEDCivicAddressLocation 15 }

sm48tat4xarpLLDPMEDCivicAddressLocationName   OBJECT-TYPE
   SYNTAX      DisplayString
   MAX-ACCESS  read-write
   STATUS      current
   DESCRIPTION
	   " "
   ::= { sm48tat4xarpLLDPMEDCivicAddressLocation 16 }

sm48tat4xarpLLDPMEDCivicAddressLocationZipCode   OBJECT-TYPE
   SYNTAX      DisplayString
   MAX-ACCESS  read-write
   STATUS      current
   DESCRIPTION
	   " "
   ::= { sm48tat4xarpLLDPMEDCivicAddressLocation 17 }

sm48tat4xarpLLDPMEDCivicAddressLocationBuilding   OBJECT-TYPE
   SYNTAX      DisplayString
   MAX-ACCESS  read-write
   STATUS      current
   DESCRIPTION
	   " "
   ::= { sm48tat4xarpLLDPMEDCivicAddressLocation 18 }

sm48tat4xarpLLDPMEDCivicAddressLocationApartment   OBJECT-TYPE
   SYNTAX      DisplayString
   MAX-ACCESS  read-write
   STATUS      current
   DESCRIPTION
	   " "
   ::= { sm48tat4xarpLLDPMEDCivicAddressLocation 19 }

sm48tat4xarpLLDPMEDCivicAddressLocationFloor   OBJECT-TYPE
   SYNTAX      DisplayString
   MAX-ACCESS  read-write
   STATUS      current
   DESCRIPTION
	   " "
   ::= { sm48tat4xarpLLDPMEDCivicAddressLocation 20 }

sm48tat4xarpLLDPMEDCivicAddressLocationRoomNo   OBJECT-TYPE
   SYNTAX      DisplayString
   MAX-ACCESS  read-write
   STATUS      current
   DESCRIPTION
	   " "
   ::= { sm48tat4xarpLLDPMEDCivicAddressLocation 21 }

sm48tat4xarpLLDPMEDCivicAddressLocationPlaceType   OBJECT-TYPE
   SYNTAX      DisplayString
   MAX-ACCESS  read-write
   STATUS      current
   DESCRIPTION
	   " "
   ::= { sm48tat4xarpLLDPMEDCivicAddressLocation 22 }

sm48tat4xarpLLDPMEDCivicAddressLocationPostalCommunityName   OBJECT-TYPE
   SYNTAX      DisplayString
   MAX-ACCESS  read-write
   STATUS      current
   DESCRIPTION
	   " "
   ::= { sm48tat4xarpLLDPMEDCivicAddressLocation 23 }

sm48tat4xarpLLDPMEDCivicAddressLocationPOBox   OBJECT-TYPE
   SYNTAX      DisplayString
   MAX-ACCESS  read-write
   STATUS      current
   DESCRIPTION
	   " "
   ::= { sm48tat4xarpLLDPMEDCivicAddressLocation 24 }

sm48tat4xarpLLDPMEDCivicAddressLocationAdditionalCode   OBJECT-TYPE
   SYNTAX      DisplayString
   MAX-ACCESS  read-write
   STATUS      current
   DESCRIPTION
	   " "
   ::= { sm48tat4xarpLLDPMEDCivicAddressLocation 25 }


sm48tat4xarpLLDPMEDPoliciesTable OBJECT-TYPE
   SYNTAX      SEQUENCE OF SM48TAT4XARPLLDPMEDPoliciesEntry
   MAX-ACCESS  not-accessible
   STATUS      current
   DESCRIPTION
       " "
   ::= { sm48tat4xarpLLDP 5 }

sm48tat4xarpLLDPMEDPoliciesEntry OBJECT-TYPE
   SYNTAX      SM48TAT4XARPLLDPMEDPoliciesEntry
   MAX-ACCESS  not-accessible
   STATUS      current
   DESCRIPTION
       " "
   INDEX    { sm48tat4xarpLLDPMEDPoliciesIndex  }
   ::= { sm48tat4xarpLLDPMEDPoliciesTable 1 }

SM48TAT4XARPLLDPMEDPoliciesEntry ::= SEQUENCE {
   sm48tat4xarpLLDPMEDPoliciesIndex            Integer32,
   sm48tat4xarpLLDPMEDPoliciesPolicyID         Integer32,
   sm48tat4xarpLLDPMEDPoliciesApplicationType  Integer32,
   sm48tat4xarpLLDPMEDPoliciesTag              Integer32,
   sm48tat4xarpLLDPMEDPoliciesVLANID           Integer32,
   sm48tat4xarpLLDPMEDPoliciesL2Priority       Integer32,
   sm48tat4xarpLLDPMEDPoliciesDSCP             Integer32,
   sm48tat4xarpLLDPMEDPoliciesRowStatus        RowStatus
}

sm48tat4xarpLLDPMEDPoliciesIndex OBJECT-TYPE
   SYNTAX      Integer32(1..65535)
   MAX-ACCESS  not-accessible
   STATUS      current
   DESCRIPTION
       "Index"
   ::= { sm48tat4xarpLLDPMEDPoliciesEntry 1 }

sm48tat4xarpLLDPMEDPoliciesPolicyID OBJECT-TYPE
   SYNTAX      Integer32
   MAX-ACCESS  read-only
   STATUS      current
   DESCRIPTION
       " "
   ::= { sm48tat4xarpLLDPMEDPoliciesEntry 2 }

sm48tat4xarpLLDPMEDPoliciesApplicationType OBJECT-TYPE
   SYNTAX      Integer32 (1..8)
   MAX-ACCESS  read-write
   STATUS      current
   DESCRIPTION
       "1:Voice
		2:Voice Signalling
		3:Guest Voice
		4:Guest Voice Signalling
		5:Softphone Voice
		6:Video Conferencing
		7:Streaming Video
		8:Video Signalling"
   ::= { sm48tat4xarpLLDPMEDPoliciesEntry 3 }

sm48tat4xarpLLDPMEDPoliciesTag OBJECT-TYPE
   SYNTAX      Integer32 (0|1)
   MAX-ACCESS  read-write
   STATUS      current
   DESCRIPTION
       "0:Untagged
	    1:Tagged"
   ::= { sm48tat4xarpLLDPMEDPoliciesEntry 4 }

sm48tat4xarpLLDPMEDPoliciesVLANID OBJECT-TYPE
   SYNTAX      Integer32 (1..4095)
   MAX-ACCESS  read-write
   STATUS      current
   DESCRIPTION
       "Range:1-4095"
   ::= { sm48tat4xarpLLDPMEDPoliciesEntry 5 }

sm48tat4xarpLLDPMEDPoliciesL2Priority OBJECT-TYPE
   SYNTAX      Integer32 (0..7)
   MAX-ACCESS  read-write
   STATUS      current
   DESCRIPTION
       "Range:0-7"
   ::= { sm48tat4xarpLLDPMEDPoliciesEntry 6 }

sm48tat4xarpLLDPMEDPoliciesDSCP OBJECT-TYPE
   SYNTAX      Integer32 (0..63)
   MAX-ACCESS  read-write
   STATUS      current
   DESCRIPTION
       "Range:0-63"
   ::= { sm48tat4xarpLLDPMEDPoliciesEntry 7 }

sm48tat4xarpLLDPMEDPoliciesRowStatus OBJECT-TYPE
   SYNTAX      RowStatus
   MAX-ACCESS  read-create
   STATUS      current
   DESCRIPTION
       "Row Status."
   ::= { sm48tat4xarpLLDPMEDPoliciesEntry 8 }

sm48tat4xarpLLDPMEDPolicyPortConfTable OBJECT-TYPE
   SYNTAX      SEQUENCE OF SM48TAT4XARPLLDPMEDPolicyPortConfEntry
   MAX-ACCESS  not-accessible
   STATUS      current
   DESCRIPTION
       " "
   ::= { sm48tat4xarpLLDP 6 }

sm48tat4xarpLLDPMEDPolicyPortConfEntry OBJECT-TYPE
   SYNTAX      SM48TAT4XARPLLDPMEDPolicyPortConfEntry
   MAX-ACCESS  not-accessible
   STATUS      current
   DESCRIPTION
       " "
   INDEX    { sm48tat4xarpLLDPMEDPolicyPortConfPort  }
   ::= { sm48tat4xarpLLDPMEDPolicyPortConfTable 1 }

SM48TAT4XARPLLDPMEDPolicyPortConfEntry ::= SEQUENCE {
   sm48tat4xarpLLDPMEDPolicyPortConfPort        Integer32,
   sm48tat4xarpLLDPMEDPolicyPortConf            Integer32
}

sm48tat4xarpLLDPMEDPolicyPortConfPort OBJECT-TYPE
   SYNTAX      Integer32(1..65535)
   MAX-ACCESS  not-accessible
   STATUS      current
   DESCRIPTION
       "Index"
   ::= { sm48tat4xarpLLDPMEDPolicyPortConfEntry 1 }

sm48tat4xarpLLDPMEDPolicyPortConf OBJECT-TYPE
   SYNTAX      Integer32 (0|1)
   MAX-ACCESS  read-write
   STATUS      current
   DESCRIPTION
       "0:Disable
	    1:Enable"
   ::= { sm48tat4xarpLLDPMEDPolicyPortConfEntry 2 }

sm48tat4xarpLLDPMEDFastStartRepeatCount OBJECT-TYPE
   SYNTAX      Integer32 (1..10)
   MAX-ACCESS  read-write
   STATUS      current
   DESCRIPTION
       "Range:1-10"
   ::= { sm48tat4xarpLLDP 7 }

sm48tat4xarpLLDPMEDEmergencyCallService OBJECT-TYPE
   SYNTAX      DisplayString
   MAX-ACCESS  read-write
   STATUS      current
   DESCRIPTION
       " "
   ::= { sm48tat4xarpLLDP 8 }

sm48tat4xarpUDLD    OBJECT IDENTIFIER ::= { sm48tat4xarpConfiguration 22 }

sm48tat4xarpUDLDPortConfigTable OBJECT-TYPE
   SYNTAX      SEQUENCE OF SM48TAT4XARPUDLDPortConfigEntry
   MAX-ACCESS  not-accessible
   STATUS      current
   DESCRIPTION
       " "
   ::= { sm48tat4xarpUDLD 1 }

sm48tat4xarpUDLDPortConfigEntry OBJECT-TYPE
   SYNTAX      SM48TAT4XARPUDLDPortConfigEntry
   MAX-ACCESS  not-accessible
   STATUS      current
   DESCRIPTION
       " "
   INDEX    { sm48tat4xarpUDLDPort  }
   ::= { sm48tat4xarpUDLDPortConfigTable 1 }

SM48TAT4XARPUDLDPortConfigEntry ::= SEQUENCE {
   sm48tat4xarpUDLDPort                       Integer32,
   sm48tat4xarpUDLDPortMode                   Integer32,
   sm48tat4xarpUDLDPortMessageInterval        Integer32
}

sm48tat4xarpUDLDPort OBJECT-TYPE
   SYNTAX      Integer32(1..65535)
   MAX-ACCESS  not-accessible
   STATUS      current
   DESCRIPTION
       " "
   ::= { sm48tat4xarpUDLDPortConfigEntry 1 }

sm48tat4xarpUDLDPortMode OBJECT-TYPE
   SYNTAX      Integer32 (0|1|2)
   MAX-ACCESS  read-write
   STATUS      current
   DESCRIPTION
       "default: 0
       0: disable
       1: Normal
	   2: Aggressive"
   ::= { sm48tat4xarpUDLDPortConfigEntry 2 }

sm48tat4xarpUDLDPortMessageInterval OBJECT-TYPE
   SYNTAX      Integer32(7..90)
   MAX-ACCESS  read-write
   STATUS      current
   DESCRIPTION
       "default: 7, range: 7-90"
   ::= { sm48tat4xarpUDLDPortConfigEntry 3 }


sm48tat4xarpUDLDPortStatusTable OBJECT-TYPE
   SYNTAX      SEQUENCE OF SM48TAT4XARPUDLDPortStatusEntry
   MAX-ACCESS  not-accessible
   STATUS      current
   DESCRIPTION
       " "
   ::= { sm48tat4xarpUDLD 2 }

sm48tat4xarpUDLDPortStatusEntry OBJECT-TYPE
   SYNTAX      SM48TAT4XARPUDLDPortStatusEntry
   MAX-ACCESS  not-accessible
   STATUS      current
   DESCRIPTION
       " "
   INDEX    { sm48tat4xarpUDLDPortStatusPort  }
   ::= { sm48tat4xarpUDLDPortStatusTable 1 }

SM48TAT4XARPUDLDPortStatusEntry ::= SEQUENCE {
   sm48tat4xarpUDLDPortStatusPort                   Integer32,
   sm48tat4xarpUDLDStatusAdminState                 Integer32,
   sm48tat4xarpUDLDStatusDeviceIDLocal          DisplayString,
   sm48tat4xarpUDLDStatusDeviceNameLocal        DisplayString,
   sm48tat4xarpUDLDStatusBidirectionalState     DisplayString
}

sm48tat4xarpUDLDPortStatusPort OBJECT-TYPE
   SYNTAX      Integer32(1..65535)
   MAX-ACCESS  not-accessible
   STATUS      current
   DESCRIPTION
       "Port index"
   ::= { sm48tat4xarpUDLDPortStatusEntry 1 }

sm48tat4xarpUDLDStatusAdminState OBJECT-TYPE
   SYNTAX      Integer32
   MAX-ACCESS  read-only
   STATUS      current
   DESCRIPTION
       "0:disable
	   1:enable"
   ::= { sm48tat4xarpUDLDPortStatusEntry 2 }

sm48tat4xarpUDLDStatusDeviceIDLocal OBJECT-TYPE
   SYNTAX      DisplayString
   MAX-ACCESS  read-only
   STATUS      current
   DESCRIPTION
       " "
   ::= { sm48tat4xarpUDLDPortStatusEntry 3 }

sm48tat4xarpUDLDStatusDeviceNameLocal OBJECT-TYPE
   SYNTAX      DisplayString
   MAX-ACCESS  read-only
   STATUS      current
   DESCRIPTION
       " "
   ::= { sm48tat4xarpUDLDPortStatusEntry 4 }

sm48tat4xarpUDLDStatusBidirectionalState OBJECT-TYPE
   SYNTAX      DisplayString
   MAX-ACCESS  read-only
   STATUS      current
   DESCRIPTION
       " "
   ::= { sm48tat4xarpUDLDPortStatusEntry 5 }


sm48tat4xarpUDLDStatusPort OBJECT-TYPE
   SYNTAX      Integer32
   MAX-ACCESS  read-write
   STATUS      current
   DESCRIPTION
       "Specify port number for check neighbour status"
   ::= { sm48tat4xarpUDLD 3 }

sm48tat4xarpUDLDPortNeighbourStatusTable OBJECT-TYPE
   SYNTAX      SEQUENCE OF SM48TAT4XARPUDLDPortNeighbourStatusEntry
   MAX-ACCESS  not-accessible
   STATUS      current
   DESCRIPTION
       " "
   ::= { sm48tat4xarpUDLD 4 }

sm48tat4xarpUDLDPortNeighbourStatusEntry OBJECT-TYPE
   SYNTAX      SM48TAT4XARPUDLDPortNeighbourStatusEntry
   MAX-ACCESS  not-accessible
   STATUS      current
   DESCRIPTION
       " "
   INDEX    { sm48tat4xarpUDLDNeighbourPort  }
   ::= { sm48tat4xarpUDLDPortNeighbourStatusTable 1 }

SM48TAT4XARPUDLDPortNeighbourStatusEntry ::= SEQUENCE {
   sm48tat4xarpUDLDNeighbourPort                 Integer32,
   sm48tat4xarpUDLDNeighbourStatusPort           DisplayString,
   sm48tat4xarpUDLDNeighbourStatusDeviceId       DisplayString,
   sm48tat4xarpUDLDNeighbourStatusLinkStatus     DisplayString,
   sm48tat4xarpUDLDNeighbourStatusDeviceName     DisplayString
}

sm48tat4xarpUDLDNeighbourPort OBJECT-TYPE
   SYNTAX      Integer32(1..65535)
   MAX-ACCESS  not-accessible
   STATUS      current
   DESCRIPTION
       "Index"
   ::= { sm48tat4xarpUDLDPortNeighbourStatusEntry 1 }

sm48tat4xarpUDLDNeighbourStatusPort OBJECT-TYPE
   SYNTAX      DisplayString
   MAX-ACCESS  read-only
   STATUS      current
   DESCRIPTION
       " "
   ::= { sm48tat4xarpUDLDPortNeighbourStatusEntry 2 }

sm48tat4xarpUDLDNeighbourStatusDeviceId OBJECT-TYPE
   SYNTAX      DisplayString
   MAX-ACCESS  read-only
   STATUS      current
   DESCRIPTION
       " "
   ::= { sm48tat4xarpUDLDPortNeighbourStatusEntry 3 }

sm48tat4xarpUDLDNeighbourStatusLinkStatus OBJECT-TYPE
   SYNTAX      DisplayString
   MAX-ACCESS  read-only
   STATUS      current
   DESCRIPTION
       " "
   ::= { sm48tat4xarpUDLDPortNeighbourStatusEntry 4 }

sm48tat4xarpUDLDNeighbourStatusDeviceName OBJECT-TYPE
   SYNTAX      DisplayString
   MAX-ACCESS  read-only
   STATUS      current
   DESCRIPTION
       " "
   ::= { sm48tat4xarpUDLDPortNeighbourStatusEntry 5 }
-- =======================================================================================================================
sm48tat4xarpEPS    OBJECT IDENTIFIER ::= { sm48tat4xarpConfiguration 23 }

sm48tat4xarpEPSTable  OBJECT-TYPE
   SYNTAX      SEQUENCE OF SM48TAT4XARPEPSEntry
   MAX-ACCESS  not-accessible
   STATUS      current
   DESCRIPTION
       "A table of EPS."
 ::= { sm48tat4xarpEPS 1 }

sm48tat4xarpEPSEntry OBJECT-TYPE
    SYNTAX        SM48TAT4XARPEPSEntry
    MAX-ACCESS    not-accessible
    STATUS        current
    DESCRIPTION
        ""
    INDEX        { sm48tat4xarpEPSIndex }
    ::= { sm48tat4xarpEPSTable 1 }

SM48TAT4XARPEPSEntry ::=
    SEQUENCE {
        sm48tat4xarpEPSIndex                                Integer32,
        sm48tat4xarpEpsID                                   Integer32,
		sm48tat4xarpEpsDomain                               Integer32,
        sm48tat4xarpEpsArchitecture                         Integer32,
        sm48tat4xarpEpsWFlow                                Integer32,
        sm48tat4xarpEpsPFlow                                Integer32,
        sm48tat4xarpEpsWSFMEP                               Integer32,
        sm48tat4xarpEpsPSFMEP                               Integer32,
        sm48tat4xarpEpsAPSMEP                               Integer32,
        sm48tat4xarpEpsAlarm                                Integer32,
        sm48tat4xarpEpsRowStatus                            RowStatus
    }

sm48tat4xarpEPSIndex OBJECT-TYPE
   SYNTAX      Integer32(1..65535)
   MAX-ACCESS  not-accessible
   STATUS      current
   DESCRIPTION
       "Index"
   ::= { sm48tat4xarpEPSEntry 1 }

sm48tat4xarpEpsID OBJECT-TYPE
   SYNTAX      Integer32 (1..100)
   MAX-ACCESS  read-create
   STATUS      current
   DESCRIPTION
       "EPS ID. Range:1-100."
   ::= {sm48tat4xarpEPSEntry 2 }

sm48tat4xarpEpsDomain OBJECT-TYPE
   SYNTAX      Integer32
   MAX-ACCESS  read-create
   STATUS      current
   DESCRIPTION
       "EPS Domain. Range:0.
	   0:Domain is Port"
   ::= {sm48tat4xarpEPSEntry 3 }

sm48tat4xarpEpsArchitecture OBJECT-TYPE
   SYNTAX      Integer32
   MAX-ACCESS  read-create
   STATUS      current
   DESCRIPTION
       "EPS Architecture. Range:0-1.
	   0:Architecture is 1+1
	   1:Architecture is 1:1"
   ::= {sm48tat4xarpEPSEntry 4 }

sm48tat4xarpEpsWFlow OBJECT-TYPE
   SYNTAX      Integer32
   MAX-ACCESS  read-create
   STATUS      current
   DESCRIPTION
       "The working flow for the EPS."
   ::= {sm48tat4xarpEPSEntry 5 }

sm48tat4xarpEpsPFlow OBJECT-TYPE
   SYNTAX      Integer32
   MAX-ACCESS  read-create
   STATUS      current
   DESCRIPTION
       "The protecting flow for the EPS"
   ::= {sm48tat4xarpEPSEntry 6 }

sm48tat4xarpEpsWSFMEP OBJECT-TYPE
   SYNTAX      Integer32
   MAX-ACCESS  read-create
   STATUS      current
   DESCRIPTION
       "The working Signal Fail reporting MEP."
   ::= {sm48tat4xarpEPSEntry 7 }

sm48tat4xarpEpsPSFMEP OBJECT-TYPE
   SYNTAX      Integer32
   MAX-ACCESS  read-create
   STATUS      current
   DESCRIPTION
       "The protecting Signal Fail reporting MEP."
   ::= {sm48tat4xarpEPSEntry 8 }

sm48tat4xarpEpsAPSMEP OBJECT-TYPE
   SYNTAX      Integer32
   MAX-ACCESS  read-create
   STATUS      current
   DESCRIPTION
       "The APS PDU handling MEP."
   ::= {sm48tat4xarpEPSEntry 9 }

sm48tat4xarpEpsAlarm OBJECT-TYPE
   SYNTAX      Integer32
   MAX-ACCESS  read-only
   STATUS      current
   DESCRIPTION
       "There is an active alarm on the EPS."
   ::= {sm48tat4xarpEPSEntry 10 }

sm48tat4xarpEpsRowStatus OBJECT-TYPE
   SYNTAX      RowStatus
   MAX-ACCESS  read-create
   STATUS      current
   DESCRIPTION
       "EPS Row Status."
   ::= {sm48tat4xarpEPSEntry 11 }

sm48tat4xarpEpsConfigInstanceEpsID   OBJECT-TYPE
   SYNTAX      Integer32
   MAX-ACCESS  read-write
   STATUS      current
   DESCRIPTION
	   "Specify EPS ID for table uesd."
   ::= {sm48tat4xarpEPS 2 }


sm48tat4xarpEPSConfigInstanceEntry    OBJECT IDENTIFIER ::= { sm48tat4xarpEPS 3 }

sm48tat4xarpEpsConfigInstanceProtectionType OBJECT-TYPE
   SYNTAX      Integer32
   MAX-ACCESS  read-write
   STATUS      current
   DESCRIPTION
       "Range:0-1.
	   0:Unidirectional: EPS in the two ends can select traffic from different working/protecting flow. This is only possible in case of 1+1.
       1:Bidirectional: EPS in the two ends is selecting traffic from the same working/protecting flow. This requires APS enabled. This is mandatory for 1:1"
   ::= { sm48tat4xarpEPSConfigInstanceEntry 2 }

sm48tat4xarpEpsConfigInstanceAPS OBJECT-TYPE
   SYNTAX      Integer32
   MAX-ACCESS  read-write
   STATUS      current
   DESCRIPTION
       "Range:0-1.
	    0:disable
	    1:enable
	    The Automatic Protection Switching protocol can be enabled/disabled. This is mandatory for 1:1."
   ::= { sm48tat4xarpEPSConfigInstanceEntry 3 }

sm48tat4xarpEpsConfigInstanceRevertive OBJECT-TYPE
   SYNTAX      Integer32
   MAX-ACCESS  read-write
   STATUS      current
   DESCRIPTION
       "Range:0-1.
	    0:disable
	    1:enable
		The revertive switching to working flow can be enabled/disabled.
		"
   ::= { sm48tat4xarpEPSConfigInstanceEntry 4 }

sm48tat4xarpEpsConfigInstanceWTRTime OBJECT-TYPE
   SYNTAX      Integer32
   MAX-ACCESS  read-write
   STATUS      current
   DESCRIPTION
       "The Wait To Restore timing value to be used in revertive switching. Range is 1 to 720 seconds.
		"
   ::= { sm48tat4xarpEPSConfigInstanceEntry 5 }

sm48tat4xarpEpsConfigInstanceHoldOffTime OBJECT-TYPE
   SYNTAX      Integer32
   MAX-ACCESS  read-write
   STATUS      current
   DESCRIPTION
       "The timing value to be used to make persistent check on Signal Fail before switching. This is in 100 ms. and the max value is 100 (10 sec)."
   ::= { sm48tat4xarpEPSConfigInstanceEntry 6 }

sm48tat4xarpEpsConfigInstanceCommand OBJECT-TYPE
   SYNTAX      Integer32
   MAX-ACCESS  read-write
   STATUS      current
   DESCRIPTION
       "0:None
	    1:Clear
		2:Lock Out
		3:Forced switch
		4:Manual switch P
		5:Manual switch W
		6:Exercise
		7:Freeze
		8:Lock Out Local
	   "
   ::= { sm48tat4xarpEPSConfigInstanceEntry 7 }

sm48tat4xarpEpsStatusProtectionState OBJECT-TYPE
   SYNTAX      DisplayString
   MAX-ACCESS  read-only
   STATUS      current
   DESCRIPTION
       "EPS state according to State Transition Tables in G.8031.
	   "
   ::= { sm48tat4xarpEPSConfigInstanceEntry 8 }

sm48tat4xarpEpsStatusWorkingFlowState OBJECT-TYPE
   SYNTAX      DisplayString
   MAX-ACCESS  read-only
   STATUS      current
   DESCRIPTION
       "OK: State of working flow is ok
        SF: State of working flow is Signal Fail
		SD: State of working flow is Signal Degrade (for future use)
	   "
   ::= { sm48tat4xarpEPSConfigInstanceEntry 9 }

sm48tat4xarpEpsStatusProtectingFlowState OBJECT-TYPE
   SYNTAX      DisplayString
   MAX-ACCESS  read-only
   STATUS      current
   DESCRIPTION
       "OK: State of protecting flow is ok
        SF: State of protecting flow is Signal Fail
        SD: State of protecting flow is Signal Degrade (for future use)
	   "
   ::= { sm48tat4xarpEPSConfigInstanceEntry 10 }

sm48tat4xarpEpsStatusTransmittedApsRequest OBJECT-TYPE
   SYNTAX      DisplayString
   MAX-ACCESS  read-only
   STATUS      current
   DESCRIPTION
       "The transmitted APS according to State Transition Tables in G.8031.
	   "
   ::= { sm48tat4xarpEPSConfigInstanceEntry 11 }

sm48tat4xarpEpsStatusTransmittedApsReSignal OBJECT-TYPE
   SYNTAX      Integer32
   MAX-ACCESS  read-only
   STATUS      current
   DESCRIPTION
       "The transmitted APS according to State Transition Tables in G.8031.
	   "
   ::= { sm48tat4xarpEPSConfigInstanceEntry 12 }

sm48tat4xarpEpsStatusTransmittedApsBrSignal OBJECT-TYPE
   SYNTAX      Integer32
   MAX-ACCESS  read-only
   STATUS      current
   DESCRIPTION
       "The transmitted APS according to State Transition Tables in G.8031.
	   "
   ::= { sm48tat4xarpEPSConfigInstanceEntry 13 }

sm48tat4xarpEpsStatusReceivedApsRequest OBJECT-TYPE
   SYNTAX      DisplayString
   MAX-ACCESS  read-only
   STATUS      current
   DESCRIPTION
       "The received APS according to State Transition Tables in G.8031.
	   "
   ::= { sm48tat4xarpEPSConfigInstanceEntry 14 }

sm48tat4xarpEpsStatusReceivedApsReSignal OBJECT-TYPE
   SYNTAX      Integer32
   MAX-ACCESS  read-only
   STATUS      current
   DESCRIPTION
       "The received APS according to State Transition Tables in G.8031.
	   "
   ::= { sm48tat4xarpEPSConfigInstanceEntry 15 }

sm48tat4xarpEpsStatusReceivedApsBrSignal OBJECT-TYPE
   SYNTAX      Integer32
   MAX-ACCESS  read-only
   STATUS      current
   DESCRIPTION
       "The received APS according to State Transition Tables in G.8031.
	   "
   ::= { sm48tat4xarpEPSConfigInstanceEntry 16 }

sm48tat4xarpEpsStatusArchitectureMismatch OBJECT-TYPE
   SYNTAX      DisplayString
   MAX-ACCESS  read-only
   STATUS      current
   DESCRIPTION
       "The architecture indicated in the received APS does not match the locally configured.
	   "
   ::= { sm48tat4xarpEPSConfigInstanceEntry 17 }

sm48tat4xarpEpsStatusAPSOnWorking OBJECT-TYPE
   SYNTAX      DisplayString
   MAX-ACCESS  read-only
   STATUS      current
   DESCRIPTION
       "APS is received on the working flow.
	   "
   ::= { sm48tat4xarpEPSConfigInstanceEntry 18 }

sm48tat4xarpEpsStatusSwitchingIncomplete OBJECT-TYPE
   SYNTAX      DisplayString
   MAX-ACCESS  read-only
   STATUS      current
   DESCRIPTION
       "Traffic is not selected from the same flow instance in the two ends.
	   "
   ::= { sm48tat4xarpEPSConfigInstanceEntry 19 }

sm48tat4xarpEpsStatusNoApsReceived OBJECT-TYPE
   SYNTAX      DisplayString
   MAX-ACCESS  read-only
   STATUS      current
   DESCRIPTION
       "APS PDU is not received from the other end.
	   "
   ::= { sm48tat4xarpEPSConfigInstanceEntry 20 }

-- =======================================================================================================================

sm48tat4xarpERPS    OBJECT IDENTIFIER ::= { sm48tat4xarpConfiguration 24 }

sm48tat4xarpERPSTable  OBJECT-TYPE
   SYNTAX      SEQUENCE OF SM48TAT4XARPERPSEntry
   MAX-ACCESS  not-accessible
   STATUS      current
   DESCRIPTION
       "A table of ERPS."
 ::= { sm48tat4xarpERPS 1 }

sm48tat4xarpERPSEntry OBJECT-TYPE
    SYNTAX        SM48TAT4XARPERPSEntry
    MAX-ACCESS    not-accessible
    STATUS        current
    DESCRIPTION
        ""
    INDEX        { sm48tat4xarpErpsIndex }
    ::= { sm48tat4xarpERPSTable 1 }

SM48TAT4XARPERPSEntry ::=
    SEQUENCE {
        sm48tat4xarpErpsIndex                                Integer32,
        sm48tat4xarpErpsID                                   Integer32,
		sm48tat4xarpErpsPort0                                Integer32,
		sm48tat4xarpErpsPort1                                Integer32,
		sm48tat4xarpErpsPort0APSMEP                          Integer32,
        sm48tat4xarpErpsPort1APSMEP                          Integer32,
        sm48tat4xarpErpsPort0SFMEP                           Integer32,
        sm48tat4xarpErpsPort1SFMEP                           Integer32,
        sm48tat4xarpErpsRingType                             Integer32,
        sm48tat4xarpErpsInterconnectedNode                   Integer32,
        sm48tat4xarpErpsVirtualChannel                       Integer32,
        sm48tat4xarpErpsMajorRingID                          Integer32,
        sm48tat4xarpErpsAlarm		                          Integer32,
        sm48tat4xarpErpsRowStatus                            RowStatus
    }

sm48tat4xarpErpsIndex OBJECT-TYPE
   SYNTAX      Integer32(1..65535)
   MAX-ACCESS  not-accessible
   STATUS      current
   DESCRIPTION
       "Index"
   ::= { sm48tat4xarpERPSEntry 1 }

sm48tat4xarpErpsID OBJECT-TYPE
   SYNTAX      Integer32 (1..64)
   MAX-ACCESS  read-create
   STATUS      current
   DESCRIPTION
       "ERPS ID. Range:1-64."
   ::= {sm48tat4xarpERPSEntry 2 }

sm48tat4xarpErpsPort0 OBJECT-TYPE
   SYNTAX      Integer32
   MAX-ACCESS  read-create
   STATUS      current
   DESCRIPTION
       "This will create a Port 0 of the switch in the ring."
   ::= {sm48tat4xarpERPSEntry 3 }

sm48tat4xarpErpsPort1 OBJECT-TYPE
   SYNTAX      Integer32
   MAX-ACCESS  read-create
   STATUS      current
   DESCRIPTION
       "This will create Port 1 of the switch in the Ring.
	   As interconnected sub-ring will have only one ring port, Port 1 is configured as 0 for interconnected sub-ring.
	   0 in this field indicates that no Port 1 is associated with this instance"
   ::= {sm48tat4xarpERPSEntry 4 }

sm48tat4xarpErpsPort0APSMEP OBJECT-TYPE
   SYNTAX      Integer32
   MAX-ACCESS  read-create
   STATUS      current
   DESCRIPTION
       "The Port 0 APS PDU handling MEP.
	   Range: 1-100."
   ::= {sm48tat4xarpERPSEntry 5 }

sm48tat4xarpErpsPort1APSMEP OBJECT-TYPE
   SYNTAX      Integer32
   MAX-ACCESS  read-create
   STATUS      current
   DESCRIPTION
       "The Port 1 APS PDU handling MEP.
	   Range: 1-100."
   ::= {sm48tat4xarpERPSEntry 6 }

sm48tat4xarpErpsPort0SFMEP OBJECT-TYPE
   SYNTAX      Integer32
   MAX-ACCESS  read-create
   STATUS      current
   DESCRIPTION
       "The Port 0 Signal Fail reporting MEP.
	   Range: 1-100."
   ::= {sm48tat4xarpERPSEntry 7 }

 sm48tat4xarpErpsPort1SFMEP OBJECT-TYPE
   SYNTAX      Integer32
   MAX-ACCESS  read-create
   STATUS      current
   DESCRIPTION
       "The Port 1 Signal Fail reporting MEP.
	   Range: 1-100."
   ::= {sm48tat4xarpERPSEntry 8 }

sm48tat4xarpErpsRingType OBJECT-TYPE
   SYNTAX      Integer32
   MAX-ACCESS  read-create
   STATUS      current
   DESCRIPTION
       "Type of Protecting ring. It can be either major ring or sub-ring.
	   0:Major
	   1:Sub"
   ::= {sm48tat4xarpERPSEntry 9 }

sm48tat4xarpErpsInterconnectedNode OBJECT-TYPE
   SYNTAX      Integer32
   MAX-ACCESS  read-create
   STATUS      current
   DESCRIPTION
       "Interconnected Node indicates that the ring instance is interconnected.
	   0: not interconnected
	   1: interconnected"
   ::= {sm48tat4xarpERPSEntry 10 }

sm48tat4xarpErpsVirtualChannel OBJECT-TYPE
   SYNTAX      Integer32
   MAX-ACCESS  read-create
   STATUS      current
   DESCRIPTION
       "1: indicates it is a sub-ring with virtual channel.
	    0: indicates, sub-ring doesn't have virtual channel."
   ::= {sm48tat4xarpERPSEntry 11 }

sm48tat4xarpErpsMajorRingID OBJECT-TYPE
   SYNTAX      Integer32
   MAX-ACCESS  read-create
   STATUS      current
   DESCRIPTION
       "Major ring group ID for the interconnected sub-ring.
	   Range:1-64"
   ::= {sm48tat4xarpERPSEntry 12 }

sm48tat4xarpErpsAlarm OBJECT-TYPE
   SYNTAX      Integer32
   MAX-ACCESS  read-create
   STATUS      current
   DESCRIPTION
       "There is an active alarm on the ERPS."
   ::= {sm48tat4xarpERPSEntry 13 }

sm48tat4xarpErpsRowStatus OBJECT-TYPE
   SYNTAX      RowStatus
   MAX-ACCESS  read-create
   STATUS      current
   DESCRIPTION
       "ERPS Row Status."
   ::= {sm48tat4xarpERPSEntry 14 }


sm48tat4xarpErpsConfigInstanceErpsID   OBJECT-TYPE
   SYNTAX      Integer32
   MAX-ACCESS  read-write
   STATUS      current
   DESCRIPTION
	   "Specify ERPS ID for ERPSConfigInstanceEntry and ErpsConfigInstanceVLANConfigTable uesd."
   ::= {sm48tat4xarpERPS 2 }


sm48tat4xarpERPSConfigInstanceEntry    OBJECT IDENTIFIER ::= { sm48tat4xarpERPS 3 }

sm48tat4xarpErpsConfigInstanceConfigured OBJECT-TYPE
   SYNTAX      DisplayString
   MAX-ACCESS  read-only
   STATUS      current
   DESCRIPTION
       "Down: This ERPS is only created and has not yet been configured - is not active.
        Up: This ERPS is configured - is active."
   ::= { sm48tat4xarpERPSConfigInstanceEntry 2 }

sm48tat4xarpErpsConfigInstanceGuardTime OBJECT-TYPE
   SYNTAX      Integer32
   MAX-ACCESS  read-write
   STATUS      current
   DESCRIPTION
       "The period of the guard timer can be configured in 10 ms steps between 10 ms and 2 seconds, with a default value of 500 ms.
	    Guard timeout value to be used to prevent ring nodes from receiving outdated R-APS messages."
   ::= { sm48tat4xarpERPSConfigInstanceEntry 3 }

sm48tat4xarpErpsConfigInstanceWTRTime OBJECT-TYPE
   SYNTAX      Integer32
   MAX-ACCESS  read-write
   STATUS      current
   DESCRIPTION
       "The Wait To Restore timing value to be used in revertive switching.
        The period of the WTR time can be configured by the operator in 1 minute steps between 5 and 12 minutes with a default value of 5 minutes.
		"
   ::= { sm48tat4xarpERPSConfigInstanceEntry 4 }

sm48tat4xarpErpsConfigInstanceHoldOffTime OBJECT-TYPE
   SYNTAX      Integer32
   MAX-ACCESS  read-write
   STATUS      current
   DESCRIPTION
       "The timing value to be used to make persistent check on Signal Fail before switching.
        The range of the hold off timer is 0 to 10 seconds in steps of 100 ms
		"
   ::= { sm48tat4xarpERPSConfigInstanceEntry 5 }

sm48tat4xarpErpsConfigInstanceVersion OBJECT-TYPE
   SYNTAX      Integer32
   MAX-ACCESS  read-write
   STATUS      current
   DESCRIPTION
       "ERPS Protocol Version - v1 or v2
	   1:v1
	   2:v2"
   ::= { sm48tat4xarpERPSConfigInstanceEntry 6 }

sm48tat4xarpErpsConfigInstanceRevertive OBJECT-TYPE
   SYNTAX      Integer32
   MAX-ACCESS  read-write
   STATUS      current
   DESCRIPTION
       "1:Revertive mode
	    0:Non-Revertive mode"
   ::= { sm48tat4xarpERPSConfigInstanceEntry 7 }

sm48tat4xarpErpsConfigInstanceRPLRole OBJECT-TYPE
   SYNTAX      Integer32
   MAX-ACCESS  read-write
   STATUS      current
   DESCRIPTION
       "It can be either RPL owner or RPL Neighbor.
	   0:None
	   1:RPL owner
	   2:RPL Neighbor
	   Please set RPLPort first.
	   "
   ::= { sm48tat4xarpERPSConfigInstanceEntry 8 }

sm48tat4xarpErpsConfigInstanceRPLPort OBJECT-TYPE
   SYNTAX      Integer32
   MAX-ACCESS  read-write
   STATUS      current
   DESCRIPTION
       "This allows to select the east port or west port as the RPL block.
	   0:None
	   1:Port0
	   2:Port1
	   Please set RPLRole after specify RPLPort.
	   "
   ::= { sm48tat4xarpERPSConfigInstanceEntry 9 }

sm48tat4xarpErpsConfigInstanceClear OBJECT-TYPE
   SYNTAX      Integer32
   MAX-ACCESS  read-write
   STATUS      current
   DESCRIPTION
       "If the owner has to be changed, then the clear check box allows to clear the RPL owner for that ERPS ring.
	   0: no clear
	   1: clear
	   "
   ::= { sm48tat4xarpERPSConfigInstanceEntry 10 }

sm48tat4xarpErpsConfigInstanceTopologyChange OBJECT-TYPE
   SYNTAX      Integer32
   MAX-ACCESS  read-write
   STATUS      current
   DESCRIPTION
       "1: indicates that the topology changes in the sub-ring are propagated in the major ring.
	    0: indicates that the topology changes in the sub-ring are not propagated in the major ring.
	   "
   ::= { sm48tat4xarpERPSConfigInstanceEntry 11 }

sm48tat4xarpErpsConfigInstanceCommand OBJECT-TYPE
   SYNTAX      Integer32
   MAX-ACCESS  read-write
   STATUS      current
   DESCRIPTION
       "0:None
	    1:Manual Switch
		2:Forced Switch
		3:Clear
		Please set InstancePort first.
	   "
   ::= { sm48tat4xarpERPSConfigInstanceEntry 12 }

sm48tat4xarpErpsConfigInstancePort OBJECT-TYPE
   SYNTAX      Integer32
   MAX-ACCESS  read-write
   STATUS      current
   DESCRIPTION
       "0:None
	   1:Port0
	   2:Port1
	   Please set InstanceCommand after specify InstancePort.
	   "
   ::= { sm48tat4xarpERPSConfigInstanceEntry 13 }

sm48tat4xarpErpsStatusProtectionState OBJECT-TYPE
   SYNTAX      DisplayString
   MAX-ACCESS  read-only
   STATUS      current
   DESCRIPTION
       "ERPS state according to State Transition Tables in G.8032.
	   "
   ::= { sm48tat4xarpERPSConfigInstanceEntry 14 }

sm48tat4xarpErpsStatusPort0 OBJECT-TYPE
   SYNTAX      DisplayString
   MAX-ACCESS  read-only
   STATUS      current
   DESCRIPTION
       "OK: State of East port is ok
        SF: State of East port is Signal Fail
	   "
   ::= { sm48tat4xarpERPSConfigInstanceEntry 15 }

sm48tat4xarpErpsStatusPort1 OBJECT-TYPE
   SYNTAX      DisplayString
   MAX-ACCESS  read-only
   STATUS      current
   DESCRIPTION
       "OK: State of West port is ok
        SF: State of West port is Signal Fail
	   "
   ::= { sm48tat4xarpERPSConfigInstanceEntry 16 }

sm48tat4xarpErpsStatusTransmitAPS OBJECT-TYPE
   SYNTAX      DisplayString
   MAX-ACCESS  read-only
   STATUS      current
   DESCRIPTION
       "The transmitted APS according to State Transition Tables in G.8032.
	   "
   ::= { sm48tat4xarpERPSConfigInstanceEntry 17 }

sm48tat4xarpErpsStatusPort0ReceiveAPS OBJECT-TYPE
   SYNTAX      DisplayString
   MAX-ACCESS  read-only
   STATUS      current
   DESCRIPTION
       "The received APS on Port 0 according to State Transition Tables in G.8032.
	   "
   ::= { sm48tat4xarpERPSConfigInstanceEntry 18 }

sm48tat4xarpErpsStatusPort1ReceiveAPS OBJECT-TYPE
   SYNTAX      DisplayString
   MAX-ACCESS  read-only
   STATUS      current
   DESCRIPTION
       "The received APS on Port 1 according to State Transition Tables in G.8032.
	   "
   ::= { sm48tat4xarpERPSConfigInstanceEntry 19 }

sm48tat4xarpErpsStatusWTRRemaining OBJECT-TYPE
   SYNTAX      Integer32
   MAX-ACCESS  read-only
   STATUS      current
   DESCRIPTION
       "Remaining WTR timeout in milliseconds.
	   "
   ::= { sm48tat4xarpERPSConfigInstanceEntry 20 }

sm48tat4xarpErpsStatusRPLUnblocked OBJECT-TYPE
   SYNTAX      DisplayString
   MAX-ACCESS  read-only
   STATUS      current
   DESCRIPTION
       "APS is received on the working flow.
	   "
   ::= { sm48tat4xarpERPSConfigInstanceEntry 21 }

sm48tat4xarpErpsStatusNoAPSReceived OBJECT-TYPE
   SYNTAX      DisplayString
   MAX-ACCESS  read-only
   STATUS      current
   DESCRIPTION
       "RAPS PDU is not received from the other end.
	   "
   ::= { sm48tat4xarpERPSConfigInstanceEntry 22 }

sm48tat4xarpErpsStatusPort0BlockStatus OBJECT-TYPE
   SYNTAX      DisplayString
   MAX-ACCESS  read-only
   STATUS      current
   DESCRIPTION
       "Block status for Port 0 (Both traffic and R-APS block status). R-APS channel is never blocked on sub-rings without virtual channel.
	   "
   ::= { sm48tat4xarpERPSConfigInstanceEntry 23 }

sm48tat4xarpErpsStatusPort1BlockStatus OBJECT-TYPE
   SYNTAX      DisplayString
   MAX-ACCESS  read-only
   STATUS      current
   DESCRIPTION
       "Block status for Port 1 (Both traffic and R-APS block status). R-APS channel is never blocked on sub-rings without virtual channel.
	   "
   ::= { sm48tat4xarpERPSConfigInstanceEntry 24 }

sm48tat4xarpErpsStatusFOPAlarm OBJECT-TYPE
   SYNTAX      DisplayString
   MAX-ACCESS  read-only
   STATUS      current
   DESCRIPTION
       "Failure of Protocol Defect(FOP) status:
	   FOP is not detected
	   FOP is detected
	   "
   ::= { sm48tat4xarpERPSConfigInstanceEntry 25 }

sm48tat4xarpErpsConfigInstanceVLANConfigTable  OBJECT-TYPE
   SYNTAX      SEQUENCE OF SM48TAT4XARPErpsConfigInstanceVLANConfigEntry
   MAX-ACCESS  not-accessible
   STATUS      current
   DESCRIPTION
       "A table of ERPS VLANConfig."
 ::= { sm48tat4xarpERPS 4 }

sm48tat4xarpErpsConfigInstanceVLANConfigEntry OBJECT-TYPE
    SYNTAX        SM48TAT4XARPErpsConfigInstanceVLANConfigEntry
    MAX-ACCESS    not-accessible
    STATUS        current
    DESCRIPTION
        ""
    INDEX        { sm48tat4xarpErpsConfigInstanceVLANConfigIndex }
    ::= { sm48tat4xarpErpsConfigInstanceVLANConfigTable 1 }

SM48TAT4XARPErpsConfigInstanceVLANConfigEntry ::=
    SEQUENCE {
        sm48tat4xarpErpsConfigInstanceVLANConfigIndex            Integer32,
        sm48tat4xarpErpsConfigInstanceVLANConfigVLANID           Integer32,
        sm48tat4xarpErpsConfigInstanceVLANConfigRowStatus        RowStatus
    }

sm48tat4xarpErpsConfigInstanceVLANConfigIndex OBJECT-TYPE
   SYNTAX      Integer32(1..65535)
   MAX-ACCESS  not-accessible
   STATUS      current
   DESCRIPTION
       "Index"
   ::= { sm48tat4xarpErpsConfigInstanceVLANConfigEntry 1 }

sm48tat4xarpErpsConfigInstanceVLANConfigVLANID OBJECT-TYPE
   SYNTAX      Integer32 (1..4095)
   MAX-ACCESS  read-create
   STATUS      current
   DESCRIPTION
       "ERPS VLAN Config ID. Range:1-4095."
   ::= {sm48tat4xarpErpsConfigInstanceVLANConfigEntry 2 }

sm48tat4xarpErpsConfigInstanceVLANConfigRowStatus OBJECT-TYPE
   SYNTAX      RowStatus
   MAX-ACCESS  read-create
   STATUS      current
   DESCRIPTION
       "ERPS VLAN Config Row Status."
   ::= {sm48tat4xarpErpsConfigInstanceVLANConfigEntry 3 }
-- =======================================================================================================================

sm48tat4xarpVLANTranslation    OBJECT IDENTIFIER ::= { sm48tat4xarpConfiguration 25 }

sm48tat4xarpVLANTranslationPortTable  OBJECT-TYPE
   SYNTAX      SEQUENCE OF SM48TAT4XARPVLANTranslationPortEntry
   MAX-ACCESS  not-accessible
   STATUS      current
   DESCRIPTION
       "A table of VLANTranslationPort."
 ::= { sm48tat4xarpVLANTranslation 1 }

sm48tat4xarpVLANTranslationPortEntry OBJECT-TYPE
    SYNTAX        SM48TAT4XARPVLANTranslationPortEntry
    MAX-ACCESS    not-accessible
    STATUS        current
    DESCRIPTION
        "An entry in the VLANTranslationPort table."
    INDEX        { sm48tat4xarpVLANTranslationPortIndex }
    ::= { sm48tat4xarpVLANTranslationPortTable 1 }

SM48TAT4XARPVLANTranslationPortEntry ::=
    SEQUENCE {
        sm48tat4xarpVLANTranslationPortIndex                Integer32,
        sm48tat4xarpVLANTranslationPortDefault              Integer32,
        sm48tat4xarpVLANTranslationPortGroupID              Integer32
    }

sm48tat4xarpVLANTranslationPortIndex OBJECT-TYPE
   SYNTAX      Integer32(1..65535)
   MAX-ACCESS  not-accessible
   STATUS      current
   DESCRIPTION
       "VLANTranslationPort index."
   ::= {sm48tat4xarpVLANTranslationPortEntry 1 }

sm48tat4xarpVLANTranslationPortDefault OBJECT-TYPE
   SYNTAX      Integer32
   MAX-ACCESS  read-write
   STATUS      current
   DESCRIPTION
       "Set the switch port to use the default VLAN Translation Group.
	   1:set
	   0:not set"
   ::= {sm48tat4xarpVLANTranslationPortEntry 2 }

sm48tat4xarpVLANTranslationPortGroupID OBJECT-TYPE
   SYNTAX      Integer32
   MAX-ACCESS  read-write
   STATUS      current
   DESCRIPTION
       "The VLAN Translation mappings are organized into Groups, identified by the Group ID."
   ::= {sm48tat4xarpVLANTranslationPortEntry 3 }



sm48tat4xarpVLANTranslationMappingTable  OBJECT-TYPE
   SYNTAX      SEQUENCE OF SM48TAT4XARPVLANTranslationMappingEntry
   MAX-ACCESS  not-accessible
   STATUS      current
   DESCRIPTION
       "A table of VLANTranslationMapping."
 ::= { sm48tat4xarpVLANTranslation 2 }

sm48tat4xarpVLANTranslationMappingEntry OBJECT-TYPE
    SYNTAX        SM48TAT4XARPVLANTranslationMappingEntry
    MAX-ACCESS    not-accessible
    STATUS        current
    DESCRIPTION
        "An entry in the VLANTranslationMapping table."
    INDEX        { sm48tat4xarpVLANTranslationMappingIndex }
    ::= { sm48tat4xarpVLANTranslationMappingTable 1 }

SM48TAT4XARPVLANTranslationMappingEntry ::=
    SEQUENCE {
        sm48tat4xarpVLANTranslationMappingIndex                Integer32,
        sm48tat4xarpVLANTranslationMappingGroupID              Integer32,
        sm48tat4xarpVLANTranslationMappingVID                  Integer32,
		sm48tat4xarpVLANTranslationMappingTVID                 Integer32,
		sm48tat4xarpVLANTranslationMappingRowStatus            RowStatus
    }

sm48tat4xarpVLANTranslationMappingIndex OBJECT-TYPE
   SYNTAX      Integer32(1..65535)
   MAX-ACCESS  not-accessible
   STATUS      current
   DESCRIPTION
       "VLANTranslationMapping index."
   ::= {sm48tat4xarpVLANTranslationMappingEntry 1 }

sm48tat4xarpVLANTranslationMappingGroupID OBJECT-TYPE
   SYNTAX      Integer32
   MAX-ACCESS  read-create
   STATUS      current
   DESCRIPTION
       "The VLAN Translation mappings are organized into Groups, identified by the Group ID."
   ::= {sm48tat4xarpVLANTranslationMappingEntry 2 }

sm48tat4xarpVLANTranslationMappingVID OBJECT-TYPE
   SYNTAX      Integer32
   MAX-ACCESS  read-create
   STATUS      current
   DESCRIPTION
       "Range:1-4095"
   ::= {sm48tat4xarpVLANTranslationMappingEntry 3 }

sm48tat4xarpVLANTranslationMappingTVID OBJECT-TYPE
   SYNTAX      Integer32
   MAX-ACCESS  read-create
   STATUS      current
   DESCRIPTION
       "Range:1-4095"
   ::= {sm48tat4xarpVLANTranslationMappingEntry 4 }

sm48tat4xarpVLANTranslationMappingRowStatus OBJECT-TYPE
   SYNTAX      RowStatus
   MAX-ACCESS  read-create
   STATUS      current
   DESCRIPTION
       "VLANTranslationMapping Row Status."
   ::= {sm48tat4xarpVLANTranslationMappingEntry 5 }
-- ========================================================================================================
sm48tat4xarpMEP    OBJECT IDENTIFIER ::= { sm48tat4xarpConfiguration 26 }

sm48tat4xarpMEPTable  OBJECT-TYPE
   SYNTAX      SEQUENCE OF SM48TAT4XARPMEPEntry
   MAX-ACCESS  not-accessible
   STATUS      current
   DESCRIPTION
       "A table of MEP."
 ::= { sm48tat4xarpMEP 1 }

sm48tat4xarpMEPEntry OBJECT-TYPE
    SYNTAX        SM48TAT4XARPMEPEntry
    MAX-ACCESS    not-accessible
    STATUS        current
    DESCRIPTION
        "An entry in the MEP table."
    INDEX        { sm48tat4xarpMEPIndex }
    ::= { sm48tat4xarpMEPTable 1 }

SM48TAT4XARPMEPEntry ::=
    SEQUENCE {
        sm48tat4xarpMEPIndex                         Integer32,
        sm48tat4xarpMepInstance                      Integer32,
        sm48tat4xarpMepDomain                        Integer32,
        sm48tat4xarpMepMode                          Integer32,
		sm48tat4xarpMepDirection                     Integer32,
		sm48tat4xarpMepResidencePort                 Integer32,
		sm48tat4xarpMepLevel                         Integer32,
		sm48tat4xarpMepFlowInstance                  Integer32,
		sm48tat4xarpMepTaggedVID                     Integer32,
		sm48tat4xarpMepEPSInstance                   DisplayString,
		sm48tat4xarpMepThisMAC                       DisplayString,
		sm48tat4xarpMepAlarm                         DisplayString,
        sm48tat4xarpMepRowStatus                     RowStatus
    }

sm48tat4xarpMEPIndex OBJECT-TYPE
   SYNTAX      Integer32(1..65535)
   MAX-ACCESS  not-accessible
   STATUS      current
   DESCRIPTION
       "MEP Table index."
   ::= {sm48tat4xarpMEPEntry 1 }

sm48tat4xarpMepInstance OBJECT-TYPE
   SYNTAX      Integer32
   MAX-ACCESS  read-create
   STATUS      current
   DESCRIPTION
       ""
   ::= {sm48tat4xarpMEPEntry 2 }

sm48tat4xarpMepDomain OBJECT-TYPE
   SYNTAX      Integer32
   MAX-ACCESS  read-create
   STATUS      current
   DESCRIPTION
       ""
   ::= {sm48tat4xarpMEPEntry 3 }

sm48tat4xarpMepMode OBJECT-TYPE
   SYNTAX      Integer32
   MAX-ACCESS  read-create
   STATUS      current
   DESCRIPTION
       ""
   ::= {sm48tat4xarpMEPEntry 4 }

sm48tat4xarpMepDirection OBJECT-TYPE
   SYNTAX      Integer32
   MAX-ACCESS  read-create
   STATUS      current
   DESCRIPTION
       ""
   ::= {sm48tat4xarpMEPEntry 5 }

sm48tat4xarpMepResidencePort OBJECT-TYPE
   SYNTAX      Integer32
   MAX-ACCESS  read-create
   STATUS      current
   DESCRIPTION
       ""
   ::= {sm48tat4xarpMEPEntry 6 }

sm48tat4xarpMepLevel OBJECT-TYPE
   SYNTAX      Integer32
   MAX-ACCESS  read-create
   STATUS      current
   DESCRIPTION
       ""
   ::= {sm48tat4xarpMEPEntry 7 }

sm48tat4xarpMepFlowInstance OBJECT-TYPE
   SYNTAX      Integer32
   MAX-ACCESS  read-create
   STATUS      current
   DESCRIPTION
       ""
   ::= {sm48tat4xarpMEPEntry 8 }

sm48tat4xarpMepTaggedVID OBJECT-TYPE
   SYNTAX      Integer32
   MAX-ACCESS  read-create
   STATUS      current
   DESCRIPTION
       ""
   ::= {sm48tat4xarpMEPEntry 9 }

sm48tat4xarpMepEPSInstance OBJECT-TYPE
   SYNTAX      DisplayString
   MAX-ACCESS  read-only
   STATUS      current
   DESCRIPTION
       ""
   ::= {sm48tat4xarpMEPEntry 10 }

sm48tat4xarpMepThisMAC OBJECT-TYPE
   SYNTAX      DisplayString
   MAX-ACCESS  read-only
   STATUS      current
   DESCRIPTION
       ""
   ::= {sm48tat4xarpMEPEntry 11 }

sm48tat4xarpMepAlarm OBJECT-TYPE
   SYNTAX      DisplayString
   MAX-ACCESS  read-only
   STATUS      current
   DESCRIPTION
       ""
   ::= {sm48tat4xarpMEPEntry 12 }

sm48tat4xarpMepRowStatus OBJECT-TYPE
   SYNTAX      RowStatus
   MAX-ACCESS  read-create
   STATUS      current
   DESCRIPTION
       "MEP Row Status."
   ::= {sm48tat4xarpMEPEntry 13 }

sm48tat4xarpMepInstanceID   OBJECT-TYPE
   SYNTAX      Integer32
   MAX-ACCESS  read-write
   STATUS      current
   DESCRIPTION
	   "Specify MEP Instance ID for the following item and table uesd."
   ::= {sm48tat4xarpMEP 2 }


sm48tat4xarpMepInstanceConfEntry    OBJECT IDENTIFIER ::= { sm48tat4xarpMEP 3 }

sm48tat4xarpMepInstanceConfLevel OBJECT-TYPE
   SYNTAX      Integer32
   MAX-ACCESS  read-write
   STATUS      current
   DESCRIPTION
       ""
   ::= {sm48tat4xarpMepInstanceConfEntry 2 }

sm48tat4xarpMepInstanceConfFormat OBJECT-TYPE
   SYNTAX      Integer32
   MAX-ACCESS  read-write
   STATUS      current
   DESCRIPTION
       ""
   ::= {sm48tat4xarpMepInstanceConfEntry 3 }

sm48tat4xarpMepInstanceConfDomainName OBJECT-TYPE
   SYNTAX      DisplayString
   MAX-ACCESS  read-write
   STATUS      current
   DESCRIPTION
       ""
   ::= {sm48tat4xarpMepInstanceConfEntry 4 }

sm48tat4xarpMepInstanceConfMEGid OBJECT-TYPE
   SYNTAX      DisplayString
   MAX-ACCESS  read-write
   STATUS      current
   DESCRIPTION
       ""
   ::= {sm48tat4xarpMepInstanceConfEntry 5 }

sm48tat4xarpMepInstanceConfMEPid OBJECT-TYPE
   SYNTAX      Integer32
   MAX-ACCESS  read-write
   STATUS      current
   DESCRIPTION
       ""
   ::= {sm48tat4xarpMepInstanceConfEntry 6 }

sm48tat4xarpMepInstanceConfTaggedVID OBJECT-TYPE
   SYNTAX      Integer32
   MAX-ACCESS  read-write
   STATUS      current
   DESCRIPTION
       ""
   ::= {sm48tat4xarpMepInstanceConfEntry 7 }

sm48tat4xarpMepInstanceConfSyslog OBJECT-TYPE
   SYNTAX      Integer32
   MAX-ACCESS  read-write
   STATUS      current
   DESCRIPTION
       ""
   ::= {sm48tat4xarpMepInstanceConfEntry 8 }

sm48tat4xarpMepInstanceConfcLevel OBJECT-TYPE
   SYNTAX      DisplayString
   MAX-ACCESS  read-only
   STATUS      current
   DESCRIPTION
       ""
   ::= {sm48tat4xarpMepInstanceConfEntry 9 }

sm48tat4xarpMepInstanceConfcMEG OBJECT-TYPE
   SYNTAX      DisplayString
   MAX-ACCESS  read-only
   STATUS      current
   DESCRIPTION
       ""
   ::= {sm48tat4xarpMepInstanceConfEntry 10 }

sm48tat4xarpMepInstanceConfcMEP OBJECT-TYPE
   SYNTAX      DisplayString
   MAX-ACCESS  read-only
   STATUS      current
   DESCRIPTION
       ""
   ::= {sm48tat4xarpMepInstanceConfEntry 11 }

sm48tat4xarpMepInstanceConfcAIS OBJECT-TYPE
   SYNTAX      DisplayString
   MAX-ACCESS  read-only
   STATUS      current
   DESCRIPTION
       ""
   ::= {sm48tat4xarpMepInstanceConfEntry 12 }

sm48tat4xarpMepInstanceConfcLCK OBJECT-TYPE
   SYNTAX      DisplayString
   MAX-ACCESS  read-only
   STATUS      current
   DESCRIPTION
       ""
   ::= {sm48tat4xarpMepInstanceConfEntry 13 }

sm48tat4xarpMepInstanceConfcLoop OBJECT-TYPE
   SYNTAX      DisplayString
   MAX-ACCESS  read-only
   STATUS      current
   DESCRIPTION
       ""
   ::= {sm48tat4xarpMepInstanceConfEntry 14 }

sm48tat4xarpMepInstanceConfcConfig OBJECT-TYPE
   SYNTAX      DisplayString
   MAX-ACCESS  read-only
   STATUS      current
   DESCRIPTION
       ""
   ::= {sm48tat4xarpMepInstanceConfEntry 15 }

sm48tat4xarpMepInstanceConfcDEG OBJECT-TYPE
   SYNTAX      DisplayString
   MAX-ACCESS  read-only
   STATUS      current
   DESCRIPTION
       ""
   ::= {sm48tat4xarpMepInstanceConfEntry 16 }

sm48tat4xarpMepInstanceConfcSSF OBJECT-TYPE
   SYNTAX      DisplayString
   MAX-ACCESS  read-only
   STATUS      current
   DESCRIPTION
       ""
   ::= {sm48tat4xarpMepInstanceConfEntry 17 }

sm48tat4xarpMepInstanceConfaBLK OBJECT-TYPE
   SYNTAX      DisplayString
   MAX-ACCESS  read-only
   STATUS      current
   DESCRIPTION
       ""
   ::= {sm48tat4xarpMepInstanceConfEntry 18 }

sm48tat4xarpMepInstanceConfaTSD OBJECT-TYPE
   SYNTAX      DisplayString
   MAX-ACCESS  read-only
   STATUS      current
   DESCRIPTION
       ""
   ::= {sm48tat4xarpMepInstanceConfEntry 19 }

sm48tat4xarpMepInstanceConfaTSF OBJECT-TYPE
   SYNTAX      DisplayString
   MAX-ACCESS  read-only
   STATUS      current
   DESCRIPTION
       ""
   ::= {sm48tat4xarpMepInstanceConfEntry 20 }


sm48tat4xarpPeerMepConfTable  OBJECT-TYPE
   SYNTAX      SEQUENCE OF SM48TAT4XARPPeerMepConfEntry
   MAX-ACCESS  not-accessible
   STATUS      current
   DESCRIPTION
       "A table of MEP."
 ::= { sm48tat4xarpMEP 4 }

sm48tat4xarpPeerMepConfEntry OBJECT-TYPE
    SYNTAX        SM48TAT4XARPPeerMepConfEntry
    MAX-ACCESS    not-accessible
    STATUS        current
    DESCRIPTION
        ""
    INDEX        { sm48tat4xarpPeerMepConfIndex }
    ::= { sm48tat4xarpPeerMepConfTable 1 }

SM48TAT4XARPPeerMepConfEntry ::=
    SEQUENCE {
        sm48tat4xarpPeerMepConfIndex                       Integer32,
        sm48tat4xarpPeerMepConfPeerMEPID                   Integer32,
		sm48tat4xarpPeerMepConfUnicastPeerMAC              DisplayString,
        sm48tat4xarpPeerMepConfcLOC                        DisplayString,
        sm48tat4xarpPeerMepConfcRDI                        DisplayString,
        sm48tat4xarpPeerMepConfcPeriod                     DisplayString,
        sm48tat4xarpPeerMepConfcPriority                   DisplayString,
        sm48tat4xarpPeerMepConfRowStatus                   RowStatus
    }

sm48tat4xarpPeerMepConfIndex OBJECT-TYPE
   SYNTAX      Integer32(1..65535)
   MAX-ACCESS  not-accessible
   STATUS      current
   DESCRIPTION
       "Index"
   ::= { sm48tat4xarpPeerMepConfEntry 1 }

sm48tat4xarpPeerMepConfPeerMEPID OBJECT-TYPE
   SYNTAX      Integer32
   MAX-ACCESS  read-create
   STATUS      current
   DESCRIPTION
       "Peer MEP ID"
   ::= {sm48tat4xarpPeerMepConfEntry 2 }

sm48tat4xarpPeerMepConfUnicastPeerMAC OBJECT-TYPE
   SYNTAX      DisplayString
   MAX-ACCESS  read-create
   STATUS      current
   DESCRIPTION
       ""
   ::= {sm48tat4xarpPeerMepConfEntry 3 }

sm48tat4xarpPeerMepConfcLOC OBJECT-TYPE
   SYNTAX      DisplayString
   MAX-ACCESS  read-create
   STATUS      current
   DESCRIPTION
       ""
   ::= {sm48tat4xarpPeerMepConfEntry 4 }

sm48tat4xarpPeerMepConfcRDI OBJECT-TYPE
   SYNTAX      DisplayString
   MAX-ACCESS  read-create
   STATUS      current
   DESCRIPTION
       ""
   ::= {sm48tat4xarpPeerMepConfEntry 5 }

sm48tat4xarpPeerMepConfcPeriod OBJECT-TYPE
   SYNTAX      DisplayString
   MAX-ACCESS  read-create
   STATUS      current
   DESCRIPTION
       ""
   ::= {sm48tat4xarpPeerMepConfEntry 6 }

sm48tat4xarpPeerMepConfcPriority OBJECT-TYPE
   SYNTAX      DisplayString
   MAX-ACCESS  read-create
   STATUS      current
   DESCRIPTION
       ""
   ::= {sm48tat4xarpPeerMepConfEntry 7 }

sm48tat4xarpPeerMepConfRowStatus OBJECT-TYPE
   SYNTAX      RowStatus
   MAX-ACCESS  read-create
   STATUS      current
   DESCRIPTION
       "Peer Mep Conf Row Status."
   ::= {sm48tat4xarpPeerMepConfEntry 8 }

sm48tat4xarpFunctionalConf    OBJECT IDENTIFIER ::= { sm48tat4xarpMEP 5 }

sm48tat4xarpFunctionalConfContinuityCheckEnable OBJECT-TYPE
   SYNTAX      Integer32
   MAX-ACCESS  read-write
   STATUS      current
   DESCRIPTION
       "0:disable
	   1:enable"
   ::= {sm48tat4xarpFunctionalConf 2 }

sm48tat4xarpFunctionalConfContinuityCheckPriority OBJECT-TYPE
   SYNTAX      Integer32
   MAX-ACCESS  read-write
   STATUS      current
   DESCRIPTION
       "range:0-7"
   ::= {sm48tat4xarpFunctionalConf 3 }

sm48tat4xarpFunctionalConfContinuityCheckFrameRate OBJECT-TYPE
   SYNTAX      Integer32
   MAX-ACCESS  read-write
   STATUS      current
   DESCRIPTION
       "range:1-7
	   1: 300 f/sec
	   2: 100 f/sec
	   3: 10 f/sec
	   4: 1 f/sec
	   5: 6 f/min
	   6: 1 f/min
	   7: 6 f/hour"
   ::= {sm48tat4xarpFunctionalConf 4 }

sm48tat4xarpFunctionalConfContinuityCheckTLV OBJECT-TYPE
   SYNTAX      Integer32
   MAX-ACCESS  read-write
   STATUS      current
   DESCRIPTION
       "0:disable
	   1:enable"
   ::= {sm48tat4xarpFunctionalConf 5 }

sm48tat4xarpFunctionalConfAPSProtocolEnable OBJECT-TYPE
   SYNTAX      Integer32
   MAX-ACCESS  read-write
   STATUS      current
   DESCRIPTION
       "0:disable
	   1:enable"
   ::= {sm48tat4xarpFunctionalConf 6 }

sm48tat4xarpFunctionalConfAPSProtocolPriority OBJECT-TYPE
   SYNTAX      Integer32
   MAX-ACCESS  read-write
   STATUS      current
   DESCRIPTION
       "range:0-7"
   ::= {sm48tat4xarpFunctionalConf 7 }

sm48tat4xarpFunctionalConfAPSProtocolCast OBJECT-TYPE
   SYNTAX      Integer32
   MAX-ACCESS  read-write
   STATUS      current
   DESCRIPTION
       "0: Unicast destination address
	   1: Multicast destination address"
   ::= {sm48tat4xarpFunctionalConf 8 }

sm48tat4xarpFunctionalConfAPSProtocolType OBJECT-TYPE
   SYNTAX      Integer32
   MAX-ACCESS  read-write
   STATUS      current
   DESCRIPTION
       "1: Linear protection APS
	   2: Ring protection APS"
   ::= {sm48tat4xarpFunctionalConf 9 }

sm48tat4xarpFunctionalConfAPSProtocolLastOctet OBJECT-TYPE
   SYNTAX      Integer32
   MAX-ACCESS  read-write
   STATUS      current
   DESCRIPTION
       "range:0-255"
   ::= {sm48tat4xarpFunctionalConf 10 }

sm48tat4xarpTLVConf    OBJECT IDENTIFIER ::= { sm48tat4xarpMEP 6 }

sm48tat4xarpTLVConfOUIFirst OBJECT-TYPE
   SYNTAX      Integer32
   MAX-ACCESS  read-write
   STATUS      current
   DESCRIPTION
       "range:0-255"
   ::= {sm48tat4xarpTLVConf 2 }

sm48tat4xarpTLVConfOUISecond OBJECT-TYPE
   SYNTAX      Integer32
   MAX-ACCESS  read-write
   STATUS      current
   DESCRIPTION
       "range:0-255"
   ::= {sm48tat4xarpTLVConf 3 }

sm48tat4xarpTLVConfOUIThird OBJECT-TYPE
   SYNTAX      Integer32
   MAX-ACCESS  read-write
   STATUS      current
   DESCRIPTION
       "range:0-255"
   ::= {sm48tat4xarpTLVConf 4 }

sm48tat4xarpTLVConfSubType OBJECT-TYPE
   SYNTAX      Integer32
   MAX-ACCESS  read-write
   STATUS      current
   DESCRIPTION
       "range:0-255"
   ::= {sm48tat4xarpTLVConf 5 }

sm48tat4xarpTLVConfValue OBJECT-TYPE
   SYNTAX      Integer32
   MAX-ACCESS  read-write
   STATUS      current
   DESCRIPTION
       "range:0-255"
   ::= {sm48tat4xarpTLVConf 6 }


sm48tat4xarpTLVConfStateTable OBJECT-TYPE
   SYNTAX      SEQUENCE OF SM48TAT4XARPTLVConfStateEntry
   MAX-ACCESS  not-accessible
   STATUS      current
   DESCRIPTION
       "TLV Conf State Table"
   ::= { sm48tat4xarpMEP 7 }

sm48tat4xarpTLVConfStateEntry OBJECT-TYPE
   SYNTAX      SM48TAT4XARPTLVConfStateEntry
   MAX-ACCESS  not-accessible
   STATUS      current
   DESCRIPTION
       "TLV Conf State Entry"
   INDEX    { sm48tat4xarpTLVConfStateIndex  }
   ::= { sm48tat4xarpTLVConfStateTable 1 }

SM48TAT4XARPTLVConfStateEntry ::= SEQUENCE {
   sm48tat4xarpTLVConfStateIndex                                Integer32,
   sm48tat4xarpTLVConfStatePeerMEPID                            Integer32,
   sm48tat4xarpTLVConfStateCCOrganizationSpecificOUIFirst       Integer32,
   sm48tat4xarpTLVConfStateCCOrganizationSpecificOUISecond      Integer32,
   sm48tat4xarpTLVConfStateCCOrganizationSpecificOUIThird       Integer32,
   sm48tat4xarpTLVConfStateCCOrganizationSpecificSubType        Integer32,
   sm48tat4xarpTLVConfStateCCOrganizationSpecificValue          Integer32,
   sm48tat4xarpTLVConfStateCCOrganizationSpecificLastRX         DisplayString,
   sm48tat4xarpTLVConfStateCCPortStatusValue                    Integer32,
   sm48tat4xarpTLVConfStateCCPortStatusLastRX                   DisplayString,
   sm48tat4xarpTLVConfStateCCInterfaceStatusValue               Integer32,
   sm48tat4xarpTLVConfStateCCInterfaceStatusLastRX              DisplayString
}

sm48tat4xarpTLVConfStateIndex OBJECT-TYPE
   SYNTAX      Integer32(1..65535)
   MAX-ACCESS  not-accessible
   STATUS      current
   DESCRIPTION
       "Index"
   ::= { sm48tat4xarpTLVConfStateEntry 1 }

sm48tat4xarpTLVConfStatePeerMEPID OBJECT-TYPE
   SYNTAX      Integer32
   MAX-ACCESS  read-only
   STATUS      current
   DESCRIPTION
       "Peer MEP ID"
   ::= { sm48tat4xarpTLVConfStateEntry 2 }

sm48tat4xarpTLVConfStateCCOrganizationSpecificOUIFirst OBJECT-TYPE
   SYNTAX      Integer32
   MAX-ACCESS  read-only
   STATUS      current
   DESCRIPTION
       "The last received first value in the OUI field."
   ::= { sm48tat4xarpTLVConfStateEntry 3 }

sm48tat4xarpTLVConfStateCCOrganizationSpecificOUISecond OBJECT-TYPE
   SYNTAX      Integer32
   MAX-ACCESS  read-only
   STATUS      current
   DESCRIPTION
       "The last received second value in the OS TLV OUI field."
   ::= { sm48tat4xarpTLVConfStateEntry 4 }

sm48tat4xarpTLVConfStateCCOrganizationSpecificOUIThird OBJECT-TYPE
   SYNTAX      Integer32
   MAX-ACCESS  read-only
   STATUS      current
   DESCRIPTION
       "The last received third value in the OS TLV OUI field."
   ::= { sm48tat4xarpTLVConfStateEntry 5 }

sm48tat4xarpTLVConfStateCCOrganizationSpecificSubType OBJECT-TYPE
   SYNTAX      Integer32
   MAX-ACCESS  read-only
   STATUS      current
   DESCRIPTION
       "The last received value in the OS TLV Sub-Type field."
   ::= { sm48tat4xarpTLVConfStateEntry 6 }

sm48tat4xarpTLVConfStateCCOrganizationSpecificValue OBJECT-TYPE
   SYNTAX      Integer32
   MAX-ACCESS  read-only
   STATUS      current
   DESCRIPTION
       "The last received value in the OS TLV Value field."
   ::= { sm48tat4xarpTLVConfStateEntry 7 }

sm48tat4xarpTLVConfStateCCOrganizationSpecificLastRX OBJECT-TYPE
   SYNTAX      DisplayString
   MAX-ACCESS  read-only
   STATUS      current
   DESCRIPTION
       "OS TLV was received in the last received CCM PDU."
   ::= { sm48tat4xarpTLVConfStateEntry 8 }

sm48tat4xarpTLVConfStateCCPortStatusValue OBJECT-TYPE
   SYNTAX      Integer32
   MAX-ACCESS  read-only
   STATUS      current
   DESCRIPTION
       "The last received value in the PS TLV Value field."
   ::= { sm48tat4xarpTLVConfStateEntry 9 }

sm48tat4xarpTLVConfStateCCPortStatusLastRX OBJECT-TYPE
   SYNTAX      DisplayString
   MAX-ACCESS  read-only
   STATUS      current
   DESCRIPTION
       "PS TLV was received in the last received CCM PDU."
   ::= { sm48tat4xarpTLVConfStateEntry 10 }

sm48tat4xarpTLVConfStateCCInterfaceStatusValue OBJECT-TYPE
   SYNTAX      Integer32
   MAX-ACCESS  read-only
   STATUS      current
   DESCRIPTION
       "The last received value in the IS TLV Value field."
   ::= { sm48tat4xarpTLVConfStateEntry 11 }

sm48tat4xarpTLVConfStateCCInterfaceStatusLastRX OBJECT-TYPE
   SYNTAX      DisplayString
   MAX-ACCESS  read-only
   STATUS      current
   DESCRIPTION
       "IS TLV was received in the last received CCM PDU."
   ::= { sm48tat4xarpTLVConfStateEntry 12 }

sm48tat4xarpLinkStateTracking OBJECT-TYPE
   SYNTAX      Integer32
   MAX-ACCESS  read-write
   STATUS      current
   DESCRIPTION
       "0:disable
	   1:enable"
   ::= { sm48tat4xarpMEP 8 }


sm48tat4xarpFaultManagement    OBJECT IDENTIFIER ::= { sm48tat4xarpMEP 9 }

sm48tat4xarpFaultMgmtLoopBackConfEnable OBJECT-TYPE
   SYNTAX      Integer32
   MAX-ACCESS  read-write
   STATUS      current
   DESCRIPTION
       "0:disable
	   1:enable"
   ::= { sm48tat4xarpFaultManagement 2 }

sm48tat4xarpFaultMgmtLoopBackConfDEI OBJECT-TYPE
   SYNTAX      Integer32
   MAX-ACCESS  read-write
   STATUS      current
   DESCRIPTION
       "0:disable
	   1:enable"
   ::= { sm48tat4xarpFaultManagement 3 }

sm48tat4xarpFaultMgmtLoopBackConfPriority OBJECT-TYPE
   SYNTAX      Integer32
   MAX-ACCESS  read-write
   STATUS      current
   DESCRIPTION
       "range:0-7"
   ::= { sm48tat4xarpFaultManagement 4 }

sm48tat4xarpFaultMgmtLoopBackConfCast OBJECT-TYPE
   SYNTAX      Integer32
   MAX-ACCESS  read-write
   STATUS      current
   DESCRIPTION
       "0:Unicast destination address
	   1:Multicast destination address"
   ::= { sm48tat4xarpFaultManagement 5 }

sm48tat4xarpFaultMgmtLoopBackConfPeerMEP OBJECT-TYPE
   SYNTAX      Integer32
   MAX-ACCESS  read-write
   STATUS      current
   DESCRIPTION
       "This is only used if the 'Unicast MAC' is configured to all zero.
	   The LBM unicast MAC will be taken from the 'Unicast Peer MAC' configuration of this peer."
   ::= { sm48tat4xarpFaultManagement 6 }

sm48tat4xarpFaultMgmtLoopBackConfUnicastMAC OBJECT-TYPE
   SYNTAX      DisplayString
   MAX-ACCESS  read-write
   STATUS      current
   DESCRIPTION
       "This is only used if NOT configured to all zero.
	   This will be used as the LBM PDU unicast MAC.
	   This is the only way to configure Loop Back to-wards a MIP. "
   ::= { sm48tat4xarpFaultManagement 7 }

sm48tat4xarpFaultMgmtLoopBackConfToSend OBJECT-TYPE
   SYNTAX      Integer32
   MAX-ACCESS  read-write
   STATUS      current
   DESCRIPTION
       "The number of LBM PDU to send in one loop test.
	   The value 0 indicate infinite transmission (test behaviour).
	   This is HW based LBM/LBR and Requires VOE."
   ::= { sm48tat4xarpFaultManagement 8 }

sm48tat4xarpFaultMgmtLoopBackConfSize OBJECT-TYPE
   SYNTAX      Integer32
   MAX-ACCESS  read-write
   STATUS      current
   DESCRIPTION
       "The LBM frame size."
   ::= { sm48tat4xarpFaultManagement 9 }

sm48tat4xarpFaultMgmtLoopBackConfInterval OBJECT-TYPE
   SYNTAX      Integer32
   MAX-ACCESS  read-write
   STATUS      current
   DESCRIPTION
       "The interval between transmitting LBM PDU."
   ::= { sm48tat4xarpFaultManagement 10 }


sm48tat4xarpFaultManagementState    OBJECT IDENTIFIER ::= { sm48tat4xarpMEP 10 }


sm48tat4xarpFaultMgmtStateTransactionID OBJECT-TYPE
   SYNTAX      Integer32
   MAX-ACCESS  read-only
   STATUS      current
   DESCRIPTION
       "The transaction id of the first LBM transmitted.
	   For each LBM transmitted the transaction id in the PDU is incremented."
   ::= { sm48tat4xarpFaultManagementState 1 }


sm48tat4xarpFaultMgmtStateTransmitted OBJECT-TYPE
   SYNTAX      Integer32
   MAX-ACCESS  read-only
   STATUS      current
   DESCRIPTION
       "The total number of LBM PDU transmitted."
   ::= { sm48tat4xarpFaultManagementState 2 }


sm48tat4xarpFaultMgmtStateTable OBJECT-TYPE
   SYNTAX      SEQUENCE OF SM48TAT4XARPFaultMgmtStateEntry
   MAX-ACCESS  not-accessible
   STATUS      current
   DESCRIPTION
       " "
   ::= { sm48tat4xarpFaultManagementState 3 }

sm48tat4xarpFaultMgmtStateEntry OBJECT-TYPE
   SYNTAX      SM48TAT4XARPFaultMgmtStateEntry
   MAX-ACCESS  not-accessible
   STATUS      current
   DESCRIPTION
       " "
   INDEX    { sm48tat4xarpFaultMgmtStateIndex  }
   ::= { sm48tat4xarpFaultMgmtStateTable 1 }

SM48TAT4XARPFaultMgmtStateEntry ::= SEQUENCE {
   sm48tat4xarpFaultMgmtStateIndex               Integer32,
   sm48tat4xarpFaultMgmtStateReplyMAC            DisplayString,
   sm48tat4xarpFaultMgmtStateReceived            Integer32,
   sm48tat4xarpFaultMgmtStateOutOfOrder          Integer32
}

sm48tat4xarpFaultMgmtStateIndex OBJECT-TYPE
   SYNTAX      Integer32(1..65535)
   MAX-ACCESS  not-accessible
   STATUS      current
   DESCRIPTION
       "Index"
   ::= { sm48tat4xarpFaultMgmtStateEntry 1 }

sm48tat4xarpFaultMgmtStateReplyMAC OBJECT-TYPE
   SYNTAX      DisplayString
   MAX-ACCESS  read-only
   STATUS      current
   DESCRIPTION
       "The MAC of the replying MEP/MIP.
	   In case of multi-cast LBM, replies can be received from all peer MEP in the group.
	   This MAC is not shown in case of 'To Send' == 0."
   ::= { sm48tat4xarpFaultMgmtStateEntry 2 }

sm48tat4xarpFaultMgmtStateReceived OBJECT-TYPE
   SYNTAX      Integer32
   MAX-ACCESS  read-only
   STATUS      current
   DESCRIPTION
       "The total number of LBR PDU received from this 'Reply MAC'."
   ::= { sm48tat4xarpFaultMgmtStateEntry 3 }

sm48tat4xarpFaultMgmtStateOutOfOrder OBJECT-TYPE
   SYNTAX      Integer32
   MAX-ACCESS  read-only
   STATUS      current
   DESCRIPTION
       "The number of LBR PDU received from this 'Reply MAC' with incorrect 'Transaction ID'."
   ::= { sm48tat4xarpFaultMgmtStateEntry 4 }

sm48tat4xarpFaultMgmtTestSignal    OBJECT IDENTIFIER ::= { sm48tat4xarpMEP 11 }

sm48tat4xarpFaultMgmtTestSignalTx OBJECT-TYPE
   SYNTAX      Integer32
   MAX-ACCESS  read-write
   STATUS      current
   DESCRIPTION
       "Test Signal based on transmitting TST PDU can be enabled/disabled.
	   0:disable
	   1:enable"
   ::= { sm48tat4xarpFaultMgmtTestSignal 2 }

sm48tat4xarpFaultMgmtTestSignalRx OBJECT-TYPE
   SYNTAX      Integer32
   MAX-ACCESS  read-write
   STATUS      current
   DESCRIPTION
       "Test Signal based on transmitting TST PDU can be enabled/disabled.
	   0:disable
	   1:enable"
   ::= { sm48tat4xarpFaultMgmtTestSignal 3 }

sm48tat4xarpFaultMgmtTestSignalDEI OBJECT-TYPE
   SYNTAX      Integer32
   MAX-ACCESS  read-write
   STATUS      current
   DESCRIPTION
       "The DEI to be inserted as PCP bits in TAG (if any).
	   0:disable
	   1:enable"
   ::= { sm48tat4xarpFaultMgmtTestSignal 4 }

sm48tat4xarpFaultMgmtTestSignalPriority OBJECT-TYPE
   SYNTAX      Integer32
   MAX-ACCESS  read-write
   STATUS      current
   DESCRIPTION
       "The priority to be inserted as PCP bits in TAG (if any).
       Range:0-7"
   ::= { sm48tat4xarpFaultMgmtTestSignal 5 }

sm48tat4xarpFaultMgmtTestSignalPeerMEP OBJECT-TYPE
   SYNTAX      Integer32
   MAX-ACCESS  read-write
   STATUS      current
   DESCRIPTION
       "The TST frame destination MAC will be taken from the 'Unicast Peer MAC' configuration of this peer."
   ::= { sm48tat4xarpFaultMgmtTestSignal 6 }

sm48tat4xarpFaultMgmtTestSignalRate OBJECT-TYPE
   SYNTAX      Integer32
   MAX-ACCESS  read-write
   STATUS      current
   DESCRIPTION
       "The TST frame transmission bit rate - in Mega bits pr. second.
	   Limit is 400 Mbps. This is the bit rate of a standard frame without any encapsulation.
	   If 1 Mbps rate is selected in a EVC MEP, the added tag will give a higher bitrate on the wire."
   ::= { sm48tat4xarpFaultMgmtTestSignal 7 }

sm48tat4xarpFaultMgmtTestSignalSize OBJECT-TYPE
   SYNTAX      Integer32
   MAX-ACCESS  read-write
   STATUS      current
   DESCRIPTION
       "The TST frame size. This is entered as the wanted size (in bytes) of a un-tagged frame containing TST OAM PDU - including CRC (four bytes)."
   ::= { sm48tat4xarpFaultMgmtTestSignal 8 }

sm48tat4xarpFaultMgmtTestSignalPattern OBJECT-TYPE
   SYNTAX      Integer32
   MAX-ACCESS  read-write
   STATUS      current
   DESCRIPTION
       "The 'empty' TST PDU has the size of 12 bytes.
	   In order to achieve the configured frame size a data TLV will be added with a pattern.
	   0:All Zero
	   1:All One
	   2:10101010"
   ::= { sm48tat4xarpFaultMgmtTestSignal 9 }

sm48tat4xarpFaultMgmtTestSignalSequenceNumber OBJECT-TYPE
   SYNTAX      Integer32
   MAX-ACCESS  read-write
   STATUS      current
   DESCRIPTION
       "0:disable
	   1:enable"
   ::= { sm48tat4xarpFaultMgmtTestSignal 10 }

sm48tat4xarpFaultMgmtTestSignalState    OBJECT IDENTIFIER ::= { sm48tat4xarpMEP 12 }

sm48tat4xarpFaultMgmtTestSignalStateTXFrameCount OBJECT-TYPE
   SYNTAX      Integer32
   MAX-ACCESS  read-only
   STATUS      current
   DESCRIPTION
       "The number of transmitted TST frames since last 'Clear'."
   ::= { sm48tat4xarpFaultMgmtTestSignalState 2 }

sm48tat4xarpFaultMgmtTestSignalStateRXFrameCount OBJECT-TYPE
   SYNTAX      Integer32
   MAX-ACCESS  read-only
   STATUS      current
   DESCRIPTION
       "The number of received TST frames since last 'Clear'."
   ::= { sm48tat4xarpFaultMgmtTestSignalState 3 }

sm48tat4xarpFaultMgmtTestSignalStateRXRate OBJECT-TYPE
   SYNTAX      Integer32
   MAX-ACCESS  read-only
   STATUS      current
   DESCRIPTION
       "The current received TST frame bit rate in Kbps.
	   This is calculated on a 1 s. basis, starting when first TST frame is received after 'Clear'.
	   The frame size used for this calculation is the first received after 'Clear'"
   ::= { sm48tat4xarpFaultMgmtTestSignalState 4 }

sm48tat4xarpFaultMgmtTestSignalStateTestTime OBJECT-TYPE
   SYNTAX      Integer32
   MAX-ACCESS  read-only
   STATUS      current
   DESCRIPTION
       "The number of seconds passed since first TST frame received after last 'Clear'."
   ::= { sm48tat4xarpFaultMgmtTestSignalState 5 }


sm48tat4xarpFaultMgmtTestSignalStateClear OBJECT-TYPE
   SYNTAX      Integer32
   MAX-ACCESS  read-write
   STATUS      current
   DESCRIPTION
       "This will clear all Test Signal State.
	   Transmission of TST frame will be restarted.
	   Calculation of 'Rx frame count', 'RX rate' and 'Test time' will be started when receiving first TST frame."
   ::= { sm48tat4xarpFaultMgmtTestSignalState 6 }


sm48tat4xarpFaultMgmtClientConfigFlow    OBJECT IDENTIFIER ::= { sm48tat4xarpMEP 13 }

sm48tat4xarpFaultMgmtClientConfigFlowTable OBJECT-TYPE
   SYNTAX      SEQUENCE OF SM48TAT4XARPFaultMgmtClientConfigFlowEntry
   MAX-ACCESS  not-accessible
   STATUS      current
   DESCRIPTION
       " "
   ::= { sm48tat4xarpFaultMgmtClientConfigFlow 1 }

sm48tat4xarpFaultMgmtClientConfigFlowEntry OBJECT-TYPE
   SYNTAX      SM48TAT4XARPFaultMgmtClientConfigFlowEntry
   MAX-ACCESS  not-accessible
   STATUS      current
   DESCRIPTION
       " "
   INDEX    { sm48tat4xarpFaultMgmtClientConfigFlowIndex  }
   ::= { sm48tat4xarpFaultMgmtClientConfigFlowTable 1 }

SM48TAT4XARPFaultMgmtClientConfigFlowEntry ::= SEQUENCE {
   sm48tat4xarpFaultMgmtClientConfigFlowIndex     Integer32,
   sm48tat4xarpFaultMgmtClientConfigFlowDomain    Integer32,
   sm48tat4xarpFaultMgmtClientConfigFlowInstance  Integer32,
   sm48tat4xarpFaultMgmtClientConfigFlowLevel     Integer32,
   sm48tat4xarpFaultMgmtClientConfigFlowAISprio   Integer32,
   sm48tat4xarpFaultMgmtClientConfigFlowLCKprio   Integer32,
   sm48tat4xarpFaultMgmtClientConfigFlowRowStatus RowStatus
}

sm48tat4xarpFaultMgmtClientConfigFlowIndex OBJECT-TYPE
   SYNTAX      Integer32(1..65535)
   MAX-ACCESS  not-accessible
   STATUS      current
   DESCRIPTION
       "Index"
   ::= { sm48tat4xarpFaultMgmtClientConfigFlowEntry 1 }

sm48tat4xarpFaultMgmtClientConfigFlowDomain OBJECT-TYPE
   SYNTAX      Integer32
   MAX-ACCESS  read-create
   STATUS      current
   DESCRIPTION
       "The domain of the client layer flow.
	   Ranfew:0-6
	   0:Port
	   1:EVC
	   2:VLAN
	   3:MPLS_LINK
	   4:MPLS_TUNNEL
	   5:MPLS_PW
	   6:MPLS_LSP"
   ::= { sm48tat4xarpFaultMgmtClientConfigFlowEntry 2 }

sm48tat4xarpFaultMgmtClientConfigFlowInstance OBJECT-TYPE
   SYNTAX      Integer32
   MAX-ACCESS  read-create
   STATUS      current
   DESCRIPTION
       "Client layer flow instance numbers."
   ::= { sm48tat4xarpFaultMgmtClientConfigFlowEntry 3 }

sm48tat4xarpFaultMgmtClientConfigFlowLevel OBJECT-TYPE
   SYNTAX      Integer32
   MAX-ACCESS  read-create
   STATUS      current
   DESCRIPTION
       "Client layer level - AIS and LCK PDU transmitted in this client layer flow will be on this level."
   ::= { sm48tat4xarpFaultMgmtClientConfigFlowEntry 4 }

sm48tat4xarpFaultMgmtClientConfigFlowAISprio OBJECT-TYPE
   SYNTAX      Integer32
   MAX-ACCESS  read-create
   STATUS      current
   DESCRIPTION
       "The priority to be used when transmitting AIS in each client flow.
	   Priority resulting in highest possible PCP can be selected.
	   Range:0-7. 255 indicate highest possible is requested"
   ::= { sm48tat4xarpFaultMgmtClientConfigFlowEntry 5 }

sm48tat4xarpFaultMgmtClientConfigFlowLCKprio OBJECT-TYPE
   SYNTAX      Integer32
   MAX-ACCESS  read-create
   STATUS      current
   DESCRIPTION
       "The priority to be used when transmitting LCK in each client flow.
	   Priority resulting in highest possible PCP can be selected.
	   Range:0-7. 255 indicate highest possible is requested"
   ::= { sm48tat4xarpFaultMgmtClientConfigFlowEntry 6 }

sm48tat4xarpFaultMgmtClientConfigFlowRowStatus OBJECT-TYPE
   SYNTAX      RowStatus
   MAX-ACCESS  read-create
   STATUS      current
   DESCRIPTION
       "FaultMgmtClientConfigFlow Row Status."
   ::= {sm48tat4xarpFaultMgmtClientConfigFlowEntry 7 }


sm48tat4xarpFaultMgmtAISLOCK    OBJECT IDENTIFIER ::= { sm48tat4xarpMEP 14 }

sm48tat4xarpFaultMgmtAISEnable OBJECT-TYPE
   SYNTAX      Integer32
   MAX-ACCESS  read-write
   STATUS      current
   DESCRIPTION
       "Insertion of AIS signal (AIS PDU transmission) in client layer flows, can be enable/disabled.
	   0:disable
	   1:enable"
   ::= { sm48tat4xarpFaultMgmtAISLOCK 2 }

sm48tat4xarpFaultMgmtAISFrameRate OBJECT-TYPE
   SYNTAX      Integer32
   MAX-ACCESS  read-write
   STATUS      current
   DESCRIPTION
       "Selecting the frame rate of AIS PDU.
	   This is the inverse of transmission period as described in Y.1731.
       1: 300 frames per second
	   2: 100 frames per second
	   3: 10 frames per second
	   4: 1 frames per second
	   5: 6 frames per minute
	   6: 1 frames per minute
	   7: 6 frames per hour"
   ::= { sm48tat4xarpFaultMgmtAISLOCK 3 }

sm48tat4xarpFaultMgmtAISProtection OBJECT-TYPE
   SYNTAX      Integer32
   MAX-ACCESS  read-write
   STATUS      current
   DESCRIPTION
       "Selecting this means that the first 3 AIS PDU is transmitted as fast as possible - in case of using this for protection in the end point.
	   0:disable
	   1:enable"
   ::= { sm48tat4xarpFaultMgmtAISLOCK 4 }


sm48tat4xarpFaultMgmtLOCKEnable OBJECT-TYPE
   SYNTAX      Integer32
   MAX-ACCESS  read-write
   STATUS      current
   DESCRIPTION
       "Insertion of LOCK signal (LCK PDU transmission) in client layer flows, can be enable/disabled.
	   0:disable
	   1:enable"
   ::= { sm48tat4xarpFaultMgmtAISLOCK 5 }

sm48tat4xarpFaultMgmtLOCKFrameRate OBJECT-TYPE
   SYNTAX      Integer32
   MAX-ACCESS  read-write
   STATUS      current
   DESCRIPTION
       "Selecting the frame rate of LCK PDU. This is the inverse of transmission period as described in Y.1731.
       1: 300 frames per second
	   2: 100 frames per second
	   3: 10 frames per second
	   4: 1 frames per second
	   5: 6 frames per minute
	   6: 1 frames per minute
	   7: 6 frames per hour"
   ::= { sm48tat4xarpFaultMgmtAISLOCK 6 }

sm48tat4xarpPerformanceMonitor  OBJECT IDENTIFIER ::= { sm48tat4xarpMEP 15 }

sm48tat4xarpDataSetEnable OBJECT-TYPE
   SYNTAX      Integer32
   MAX-ACCESS  read-write
   STATUS      current
   DESCRIPTION
       "
	   When enabled this MEP instance will contribute to the 'PM Data Set' gathered by the PM Session.
	   0:disable
	   1:enable"
   ::= { sm48tat4xarpPerformanceMonitor 2 }

sm48tat4xarpLossMeasureEnable OBJECT-TYPE
   SYNTAX      Integer32
   MAX-ACCESS  read-write
   STATUS      current
   DESCRIPTION
       "
	   Loss Measurement based on transmitting/receiving CCM or LMM/LMR PDU can be enabled/disabled - see 'Ended'.
	   This is only valid with one Peer MEP configured.
	   0:disable
	   1:enable"
   ::= { sm48tat4xarpPerformanceMonitor 3 }

sm48tat4xarpLossMeasurePriority OBJECT-TYPE
   SYNTAX      Integer32
   MAX-ACCESS  read-write
   STATUS      current
   DESCRIPTION
       "
	   The priority to be inserted as PCP bits in TAG (if any).
	   In case of enable of Continuity Check and Loss Measurement both implemented on SW based CCM, 'Priority' has to be the same.
	   range:0-7"
   ::= { sm48tat4xarpPerformanceMonitor 4 }

sm48tat4xarpLossMeasureFrameRate OBJECT-TYPE
   SYNTAX      Integer32
   MAX-ACCESS  read-write
   STATUS      current
   DESCRIPTION
       "
	   1: 300 frames per second
	   2: 100 frames per second
	   3: 10 frames per second
	   4: 1 frames per second
	   5: 6 frames per minute
	   6: 1 frames per minute
	   7: 6 frames per hour"
   ::= { sm48tat4xarpPerformanceMonitor 5 }

sm48tat4xarpLossMeasureCast OBJECT-TYPE
   SYNTAX      Integer32
   MAX-ACCESS  read-write
   STATUS      current
   DESCRIPTION
       "
	   0: Unicast destination address
	   1: Multicast destination address
	   "
   ::= { sm48tat4xarpPerformanceMonitor 6 }

sm48tat4xarpLossMeasureEnded OBJECT-TYPE
   SYNTAX      Integer32
   MAX-ACCESS  read-write
   STATUS      current
   DESCRIPTION
       "
	   0: Single ended LM based on LMM/LMR or DM based on DMM/DMR
	   1: Dual ended LM based on CCM or DM based on 1DM
	   "
   ::= { sm48tat4xarpPerformanceMonitor 7 }

sm48tat4xarpLossMeasureFLRInterval OBJECT-TYPE
   SYNTAX      Integer32
   MAX-ACCESS  read-write
   STATUS      current
   DESCRIPTION
       "
       This is the interval in seconds where the Frame Loss Ratio is calculated.
	   "
   ::= { sm48tat4xarpPerformanceMonitor 8 }

sm48tat4xarpLossMeasureLossThreshold OBJECT-TYPE
   SYNTAX      Integer32
   MAX-ACCESS  read-write
   STATUS      current
   DESCRIPTION
       "
       Far end loss threshold count is incremented if a loss measurement is above this threshold.
	   "
   ::= { sm48tat4xarpPerformanceMonitor 9 }

sm48tat4xarpLossMeasureStateTx OBJECT-TYPE
   SYNTAX      Integer32
   MAX-ACCESS  read-only
   STATUS      current
   DESCRIPTION
       "
	   "
   ::= { sm48tat4xarpPerformanceMonitor 10 }

sm48tat4xarpLossMeasureStateRx OBJECT-TYPE
   SYNTAX      Integer32
   MAX-ACCESS  read-only
   STATUS      current
   DESCRIPTION
       "
	   "
   ::= { sm48tat4xarpPerformanceMonitor 11 }

sm48tat4xarpLossMeasureStateNearEndLossCount OBJECT-TYPE
   SYNTAX      Integer32
   MAX-ACCESS  read-only
   STATUS      current
   DESCRIPTION
       "The accumulated near end frame loss count - since last 'clear'.
	   "
   ::= { sm48tat4xarpPerformanceMonitor 12 }

sm48tat4xarpLossMeasureStateFarEndLossCount OBJECT-TYPE
   SYNTAX      Integer32
   MAX-ACCESS  read-only
   STATUS      current
   DESCRIPTION
       "The accumulated far end frame loss count - since last 'clear'.
	   "
   ::= { sm48tat4xarpPerformanceMonitor 13 }

sm48tat4xarpLossMeasureStateNearEndLossRatio OBJECT-TYPE
   SYNTAX      Integer32
   MAX-ACCESS  read-only
   STATUS      current
   DESCRIPTION
       "The near end frame loss ratio calculated based on the near end frame loss count and far end frame transmitted - in the latest 'FLR Interval'.
	   The result is given in percent.
	   "
   ::= { sm48tat4xarpPerformanceMonitor 14 }

sm48tat4xarpLossMeasureStateFarEndLossRatio OBJECT-TYPE
   SYNTAX      Integer32
   MAX-ACCESS  read-only
   STATUS      current
   DESCRIPTION
       "The far end frame loss ratio calculated based on the far end frame loss count and near end frame transmitted - in the latest 'FLR Interval'.
	   The result is given in percent.
	   "
   ::= { sm48tat4xarpPerformanceMonitor 15 }

sm48tat4xarpLossMeasureStateClear OBJECT-TYPE
   SYNTAX      Integer32
   MAX-ACCESS  read-write
   STATUS      current
   DESCRIPTION
       "Set of this check and save will clear the accumulated counters and restart ratio calculation.
	   "
   ::= { sm48tat4xarpPerformanceMonitor 16 }

sm48tat4xarpLossMeasureAvailabilityEnable OBJECT-TYPE
   SYNTAX      Integer32
   MAX-ACCESS  read-write
   STATUS      current
   DESCRIPTION
       "Enable/disable of loss measurement availability.
	   0:disable
	   1:enable
	   "
   ::= { sm48tat4xarpPerformanceMonitor 17 }

sm48tat4xarpLossMeasureAvailabilityInterval OBJECT-TYPE
   SYNTAX      Integer32
   MAX-ACCESS  read-write
   STATUS      current
   DESCRIPTION
       "Availability interval - number of measurements with same availability in order to change availability state.

	   "
   ::= { sm48tat4xarpPerformanceMonitor 18 }

sm48tat4xarpLossMeasureAvailabilityFLRThreshold OBJECT-TYPE
   SYNTAX      Integer32
   MAX-ACCESS  read-write
   STATUS      current
   DESCRIPTION
       "Availability frame loss ratio threshold in per mille.
	   "
   ::= { sm48tat4xarpPerformanceMonitor 19 }

sm48tat4xarpLossMeasureAvailabilityMaintenance OBJECT-TYPE
   SYNTAX      Integer32
   MAX-ACCESS  read-write
   STATUS      current
   DESCRIPTION
       "Enable/disable of loss measurement availability maintenance.
	   "
   ::= { sm48tat4xarpPerformanceMonitor 20 }


sm48tat4xarpLossMeasureAvailabilityStateNearAvailabilityCount OBJECT-TYPE
   SYNTAX      Integer32
   MAX-ACCESS  read-only
   STATUS      current
   DESCRIPTION
       "Near end availability count.
	   "
   ::= { sm48tat4xarpPerformanceMonitor 21 }

sm48tat4xarpLossMeasureAvailabilityStateFarAvailabilityCount OBJECT-TYPE
   SYNTAX      Integer32
   MAX-ACCESS  read-only
   STATUS      current
   DESCRIPTION
       "Far end availability count.
	   "
   ::= { sm48tat4xarpPerformanceMonitor 22 }

sm48tat4xarpLossMeasureAvailStateNearUnavailabilityCount OBJECT-TYPE
   SYNTAX      Integer32
   MAX-ACCESS  read-only
   STATUS      current
   DESCRIPTION
       "Near end unavailability count.
	   "
   ::= { sm48tat4xarpPerformanceMonitor 23 }

sm48tat4xarpLossMeasureAvailabilityStateFarUnavailabilityCount OBJECT-TYPE
   SYNTAX      Integer32
   MAX-ACCESS  read-only
   STATUS      current
   DESCRIPTION
       "Far end unavailability count.
	   "
   ::= { sm48tat4xarpPerformanceMonitor 24 }

sm48tat4xarpLossMeasureAvailabilityStateNearState OBJECT-TYPE
   SYNTAX      Integer32
   MAX-ACCESS  read-only
   STATUS      current
   DESCRIPTION
       "Near end availability state.
	   "
   ::= { sm48tat4xarpPerformanceMonitor 25 }

sm48tat4xarpLossMeasureAvailabilityStateFarState OBJECT-TYPE
   SYNTAX      Integer32
   MAX-ACCESS  read-only
   STATUS      current
   DESCRIPTION
       "Far end availability state.
	   "
   ::= { sm48tat4xarpPerformanceMonitor 26 }

sm48tat4xarpLossMeasureHighLossIntervalEnable OBJECT-TYPE
   SYNTAX      Integer32
   MAX-ACCESS  read-write
   STATUS      current
   DESCRIPTION
       "Enable/disable of loss measurement high loss interval.
	   0:disable
	   1:enable
	   "
   ::= { sm48tat4xarpPerformanceMonitor 27 }

sm48tat4xarpLossMeasureHighLossIntervalFLRThreshold OBJECT-TYPE
   SYNTAX      Integer32
   MAX-ACCESS  read-write
   STATUS      current
   DESCRIPTION
       "High Loss Interval frame loss ratio threshold in per mille.
	   "
   ::= { sm48tat4xarpPerformanceMonitor 28 }

sm48tat4xarpLossMeasureHighLossIntervalConsecutiveInterval OBJECT-TYPE
   SYNTAX      Integer32
   MAX-ACCESS  read-write
   STATUS      current
   DESCRIPTION
       "High Loss Interval consecutive interval (number of measurements).
	   "
   ::= { sm48tat4xarpPerformanceMonitor 29 }

sm48tat4xarpLossMeasureHighLossIntervalStateNearCount OBJECT-TYPE
   SYNTAX      Integer32
   MAX-ACCESS  read-only
   STATUS      current
   DESCRIPTION
       "Near end high loss interval count (number of measurements where availability state is available and FLR is above high loss interval FLR threshold.
	   "
   ::= { sm48tat4xarpPerformanceMonitor 30 }

sm48tat4xarpLossMeasureHighLossIntervalStateFarCount OBJECT-TYPE
   SYNTAX      Integer32
   MAX-ACCESS  read-only
   STATUS      current
   DESCRIPTION
       "Far end high loss interval count (number of measurements where availability state is available and FLR is above high loss interval FLR threshold.
	   "
   ::= { sm48tat4xarpPerformanceMonitor 31 }

sm48tat4xarpLossMeasureIntervalStateNearConsecutiveCount OBJECT-TYPE
   SYNTAX      Integer32
   MAX-ACCESS  read-only
   STATUS      current
   DESCRIPTION
       "Near end high loss interval consecutive count.
	   "
   ::= { sm48tat4xarpPerformanceMonitor 32 }

sm48tat4xarpLossMeasureIntervalStateFarConsecutiveCount OBJECT-TYPE
   SYNTAX      Integer32
   MAX-ACCESS  read-only
   STATUS      current
   DESCRIPTION
       "Far end high loss interval consecutive count.
	   "
   ::= { sm48tat4xarpPerformanceMonitor 33 }

sm48tat4xarpLossMeasureSignalDegradeEnable OBJECT-TYPE
   SYNTAX      Integer32
   MAX-ACCESS  read-write
   STATUS      current
   DESCRIPTION
       "Enable/disable of loss measurement signal degrade.
	   0:disable
	   1:enable
	   "
   ::= { sm48tat4xarpPerformanceMonitor 34 }

sm48tat4xarpLossMeasureSignalDegradeTXMinimum OBJECT-TYPE
   SYNTAX      Integer32
   MAX-ACCESS  read-write
   STATUS      current
   DESCRIPTION
       "Minimum number of frames that must be transmitted in a measurement before frame loss ratio is tested against loss ratio threshold.

	   "
   ::= { sm48tat4xarpPerformanceMonitor 35 }

sm48tat4xarpLossMeasureSignalDegradeFLRThreshold OBJECT-TYPE
   SYNTAX      Integer32
   MAX-ACCESS  read-write
   STATUS      current
   DESCRIPTION
       "Signal Degraded frame loss ratio threshold in per mille.
	   "
   ::= { sm48tat4xarpPerformanceMonitor 36 }

sm48tat4xarpLossMeasureSignalDegradeBadThreshold OBJECT-TYPE
   SYNTAX      Integer32
   MAX-ACCESS  read-write
   STATUS      current
   DESCRIPTION
       "Number of consecutive bad interval measurements required to set degrade state.
	   "
   ::= { sm48tat4xarpPerformanceMonitor 37 }

sm48tat4xarpLossMeasureSignalDegradeGoodThreshold OBJECT-TYPE
   SYNTAX      Integer32
   MAX-ACCESS  read-write
   STATUS      current
   DESCRIPTION
       "Number of consecutive good interval measurements required to clear degrade state.
	   "
   ::= { sm48tat4xarpPerformanceMonitor 38 }

sm48tat4xarpDelayMeasureEnable OBJECT-TYPE
   SYNTAX      Integer32
   MAX-ACCESS  read-write
   STATUS      current
   DESCRIPTION
       "Delay Measurement based on transmitting 1DM/DMM PDU can be enabled/disabled.
	   Delay Measurement based on receiving and handling 1DM/DMR PDU is always enabled.
	   0:disable
	   1:enable
	   "
   ::= { sm48tat4xarpPerformanceMonitor 39 }

sm48tat4xarpDelayMeasurePriority OBJECT-TYPE
   SYNTAX      Integer32
   MAX-ACCESS  read-write
   STATUS      current
   DESCRIPTION
       "The priority to be inserted as PCP bits in TAG (if any).
       Range:0-7
	   "
   ::= { sm48tat4xarpPerformanceMonitor 40 }

sm48tat4xarpDelayMeasureCast OBJECT-TYPE
   SYNTAX      Integer32
   MAX-ACCESS  read-write
   STATUS      current
   DESCRIPTION
       "Selection of 1DM/DMM PDU transmitted unicast or multicast.
	   The unicast MAC will be configured through 'Peer MEP'.
	   0: Unicast destination address
	   1: Multicast destination address
	   "
   ::= { sm48tat4xarpPerformanceMonitor 41 }

sm48tat4xarpDelayMeasurePeerMEP OBJECT-TYPE
   SYNTAX      Integer32
   MAX-ACCESS  read-write
   STATUS      current
   DESCRIPTION
       "This is only used if the 'Cast' is configured to Uni.
	   The 1DM/DMR unicast MAC will be taken from the 'Unicast Peer MAC' configuration of this peer.
	   "
   ::= { sm48tat4xarpPerformanceMonitor 42 }

sm48tat4xarpDelayMeasureEnded OBJECT-TYPE
   SYNTAX      Integer32
   MAX-ACCESS  read-write
   STATUS      current
   DESCRIPTION
       "0:One-Way: One-Way Delay Measurement implemented on 1DM.
        1:Two-Way: Two-Way Delay Measurement implemented on DMM/DMR.
	   "
   ::= { sm48tat4xarpPerformanceMonitor 43 }

sm48tat4xarpDelayMeasureTxMode OBJECT-TYPE
   SYNTAX      Integer32
   MAX-ACCESS  read-write
   STATUS      current
   DESCRIPTION
       "0:Standardize: Y.1731 standardize way to transmit 1DM/DMR.
        1:Proprietary: Vitesse proprietary way with follow-up packets to transmit 1DM/DMR.
	   "
   ::= { sm48tat4xarpPerformanceMonitor 44 }

sm48tat4xarpDelayMeasureCalc OBJECT-TYPE
   SYNTAX      Integer32
   MAX-ACCESS  read-write
   STATUS      current
   DESCRIPTION
       "This is only used if the 'Way' is configured to Two-way.
        0:Round trip: The frame delay calculated by the transmitting and receiving timestamps of initiators.
		    Frame Delay = RxTimeb-TxTimeStampf
        1:Flow: The frame delay calculated by the transmitting and receiving timestamps of initiators and remotes.
		    Frame Delay = (RxTimeb-TxTimeStampf)-(TxTimeStampb-RxTimeStampf)
	   "
   ::= { sm48tat4xarpPerformanceMonitor 45 }

sm48tat4xarpDelayMeasureGap OBJECT-TYPE
   SYNTAX      Integer32
   MAX-ACCESS  read-write
   STATUS      current
   DESCRIPTION
       "The gap between transmitting 1DM/DMM PDU in 10ms. The range is 10 to 65535.
	   "
   ::= { sm48tat4xarpPerformanceMonitor 46 }

sm48tat4xarpDelayMeasureCount OBJECT-TYPE
   SYNTAX      Integer32
   MAX-ACCESS  read-write
   STATUS      current
   DESCRIPTION
       "The number of last records to calculate. The range is 10 to 2000.
	   "
   ::= { sm48tat4xarpPerformanceMonitor 47 }

sm48tat4xarpDelayMeasureUnit OBJECT-TYPE
   SYNTAX      Integer32
   MAX-ACCESS  read-write
   STATUS      current
   DESCRIPTION
       "The time resolution.
	   0:us
	   1:ns
	   "
   ::= { sm48tat4xarpPerformanceMonitor 48 }

sm48tat4xarpDelayMeasureD2forD1 OBJECT-TYPE
   SYNTAX      Integer32
   MAX-ACCESS  read-write
   STATUS      current
   DESCRIPTION
       "Enable to use DMM/DMR packet to calculate one-way DM.
	   0:disable
	   1:enable
	   "
   ::= { sm48tat4xarpPerformanceMonitor 49 }

sm48tat4xarpDelayMeasureCounterOverflowAction OBJECT-TYPE
   SYNTAX      Integer32
   MAX-ACCESS  read-write
   STATUS      current
   DESCRIPTION
       "The action to counter when overflow happens.
	   0: Keep:When internal total delay counter overflow, DM is disabled automatically
	   1: Reset:When internal total delay counter overflow, counter is reset and DM continues running
	   "
   ::= { sm48tat4xarpPerformanceMonitor 50 }

sm48tat4xarpDelayMeasureStateOnewayTx OBJECT-TYPE
   SYNTAX      DisplayString
   MAX-ACCESS  read-only
   STATUS      current
   DESCRIPTION
       "The accumulated transmit count - since last 'clear'.
	   "
   ::= { sm48tat4xarpPerformanceMonitor 51 }

sm48tat4xarpDelayMeasureStateOnewayRx OBJECT-TYPE
   SYNTAX      DisplayString
   MAX-ACCESS  read-only
   STATUS      current
   DESCRIPTION
       "The accumulated receive count - since last 'clear'.
	   "
   ::= { sm48tat4xarpPerformanceMonitor 52 }

sm48tat4xarpDelayMeasureStateOnewayRxTimeout OBJECT-TYPE
   SYNTAX      DisplayString
   MAX-ACCESS  read-only
   STATUS      current
   DESCRIPTION
       "The accumulated receive timeout count for two-way only - since last 'clear'.
	   "
   ::= { sm48tat4xarpPerformanceMonitor 53 }

sm48tat4xarpDelayMeasureStateOnewayRxError OBJECT-TYPE
   SYNTAX      DisplayString
   MAX-ACCESS  read-only
   STATUS      current
   DESCRIPTION
       "The accumulated receive error count - since last 'clear'.
	   This is counting if the frame delay is larger than 1 second or if far end residence time is larger than the round trip time.
	   "
   ::= { sm48tat4xarpPerformanceMonitor 54 }

sm48tat4xarpDelayMeasureStateOnewayAvDelayTot OBJECT-TYPE
   SYNTAX      DisplayString
   MAX-ACCESS  read-only
   STATUS      current
   DESCRIPTION
       "The average total delay - since last 'clear'.
	   "
   ::= { sm48tat4xarpPerformanceMonitor 55 }

sm48tat4xarpDelayMeasureStateOnewayAvDelaylastN OBJECT-TYPE
   SYNTAX      DisplayString
   MAX-ACCESS  read-only
   STATUS      current
   DESCRIPTION
       "The average delay of the last n packets - since last 'clear'.
	   "
   ::= { sm48tat4xarpPerformanceMonitor 56 }

sm48tat4xarpDelayMeasureStateOnewayDelayMin OBJECT-TYPE
   SYNTAX      DisplayString
   MAX-ACCESS  read-only
   STATUS      current
   DESCRIPTION
       "The minimum delay - since last 'clear'.
	   "
   ::= { sm48tat4xarpPerformanceMonitor 57 }

sm48tat4xarpDelayMeasureStateOnewayDelayMax OBJECT-TYPE
   SYNTAX      DisplayString
   MAX-ACCESS  read-only
   STATUS      current
   DESCRIPTION
       "The maximum delay - since last 'clear'.
	   "
   ::= { sm48tat4xarpPerformanceMonitor 58 }

sm48tat4xarpDelayMeasureStateOnewayAvDelayVarTot OBJECT-TYPE
   SYNTAX      DisplayString
   MAX-ACCESS  read-only
   STATUS      current
   DESCRIPTION
       "The average total delay variation - since last 'clear'.
	   "
   ::= { sm48tat4xarpPerformanceMonitor 59 }

sm48tat4xarpDelayMeasureStateOnewayAvDelayVarlastN OBJECT-TYPE
   SYNTAX      DisplayString
   MAX-ACCESS  read-only
   STATUS      current
   DESCRIPTION
       "The average delay variation of the last n packets - since last 'clear'.
	   "
   ::= { sm48tat4xarpPerformanceMonitor 60 }

sm48tat4xarpDelayMeasureStateOnewayDelayVarMin OBJECT-TYPE
   SYNTAX      DisplayString
   MAX-ACCESS  read-only
   STATUS      current
   DESCRIPTION
       "The minimum delay variation - since last 'clear'.
	   "
   ::= { sm48tat4xarpPerformanceMonitor 61 }

sm48tat4xarpDelayMeasureStateOnewayDelayVarMax OBJECT-TYPE
   SYNTAX      DisplayString
   MAX-ACCESS  read-only
   STATUS      current
   DESCRIPTION
       "The maximum delay variation - since last 'clear'.
	   "
   ::= { sm48tat4xarpPerformanceMonitor 62 }

sm48tat4xarpDelayMeasureStateOnewayOverflow OBJECT-TYPE
   SYNTAX      DisplayString
   MAX-ACCESS  read-only
   STATUS      current
   DESCRIPTION
       "The number of counter overflow - since last 'clear'.
	   "
   ::= { sm48tat4xarpPerformanceMonitor 63 }

sm48tat4xarpDelayMeasureStateFtoNTx OBJECT-TYPE
   SYNTAX      Integer32
   MAX-ACCESS  read-only
   STATUS      current
   DESCRIPTION
       "The accumulated transmit count - since last 'clear'.
	   "
   ::= { sm48tat4xarpPerformanceMonitor 64 }

sm48tat4xarpDelayMeasureStateFtoNRx OBJECT-TYPE
   SYNTAX      Integer32
   MAX-ACCESS  read-only
   STATUS      current
   DESCRIPTION
       "The accumulated receive count - since last 'clear'.
	   "
   ::= { sm48tat4xarpPerformanceMonitor 65 }

sm48tat4xarpDelayMeasureStateFtoNRxTimeout OBJECT-TYPE
   SYNTAX      Integer32
   MAX-ACCESS  read-only
   STATUS      current
   DESCRIPTION
       "The accumulated receive timeout count for two-way only - since last 'clear'.
	   "
   ::= { sm48tat4xarpPerformanceMonitor 66 }

sm48tat4xarpDelayMeasureStateFtoNRxError OBJECT-TYPE
   SYNTAX      Integer32
   MAX-ACCESS  read-only
   STATUS      current
   DESCRIPTION
       "The accumulated receive error count - since last 'clear'.
	   This is counting if the frame delay is larger than 1 second or if far end residence time is larger than the round trip time.
	   "
   ::= { sm48tat4xarpPerformanceMonitor 67 }

sm48tat4xarpDelayMeasureStateFtoNAvDelayTot OBJECT-TYPE
   SYNTAX      Integer32
   MAX-ACCESS  read-only
   STATUS      current
   DESCRIPTION
       "The average total delay - since last 'clear'.
	   "
   ::= { sm48tat4xarpPerformanceMonitor 68 }

sm48tat4xarpDelayMeasureStateFtoNAvDelaylastN OBJECT-TYPE
   SYNTAX      Integer32
   MAX-ACCESS  read-only
   STATUS      current
   DESCRIPTION
       "The average delay of the last n packets - since last 'clear'.
	   "
   ::= { sm48tat4xarpPerformanceMonitor 69 }

sm48tat4xarpDelayMeasureStateFtoNDelayMin OBJECT-TYPE
   SYNTAX      Integer32
   MAX-ACCESS  read-only
   STATUS      current
   DESCRIPTION
       "The minimum delay - since last 'clear'.
	   "
   ::= { sm48tat4xarpPerformanceMonitor 70 }

sm48tat4xarpDelayMeasureStateFtoNDelayMax OBJECT-TYPE
   SYNTAX      Integer32
   MAX-ACCESS  read-only
   STATUS      current
   DESCRIPTION
       "The maximum delay - since last 'clear'.
	   "
   ::= { sm48tat4xarpPerformanceMonitor 71 }

sm48tat4xarpDelayMeasureStateFtoNAvDelayVarTot OBJECT-TYPE
   SYNTAX      Integer32
   MAX-ACCESS  read-only
   STATUS      current
   DESCRIPTION
       "The average total delay variation - since last 'clear'.
	   "
   ::= { sm48tat4xarpPerformanceMonitor 72 }

sm48tat4xarpDelayMeasureStateFtoNAvDelayVarlastN OBJECT-TYPE
   SYNTAX      Integer32
   MAX-ACCESS  read-only
   STATUS      current
   DESCRIPTION
       "The average delay variation of the last n packets - since last 'clear'.
	   "
   ::= { sm48tat4xarpPerformanceMonitor 73 }

sm48tat4xarpDelayMeasureStateFtoNDelayVarMin OBJECT-TYPE
   SYNTAX      Integer32
   MAX-ACCESS  read-only
   STATUS      current
   DESCRIPTION
       "The minimum delay variation - since last 'clear'.
	   "
   ::= { sm48tat4xarpPerformanceMonitor 74 }

sm48tat4xarpDelayMeasureStateFtoNDelayVarMax OBJECT-TYPE
   SYNTAX      Integer32
   MAX-ACCESS  read-only
   STATUS      current
   DESCRIPTION
       "The maximum delay variation - since last 'clear'.
	   "
   ::= { sm48tat4xarpPerformanceMonitor 75 }

sm48tat4xarpDelayMeasureStateFtoNOverflow OBJECT-TYPE
   SYNTAX      Integer32
   MAX-ACCESS  read-only
   STATUS      current
   DESCRIPTION
       "The number of counter overflow - since last 'clear'.
	   "
   ::= { sm48tat4xarpPerformanceMonitor 76 }

sm48tat4xarpDelayMeasureStateNtoFTx OBJECT-TYPE
   SYNTAX      Integer32
   MAX-ACCESS  read-only
   STATUS      current
   DESCRIPTION
       "The accumulated transmit count - since last 'clear'.
	   "
   ::= { sm48tat4xarpPerformanceMonitor 77 }

sm48tat4xarpDelayMeasureStateNtoFRx OBJECT-TYPE
   SYNTAX      Integer32
   MAX-ACCESS  read-only
   STATUS      current
   DESCRIPTION
       "The accumulated receive count - since last 'clear'.
	   "
   ::= { sm48tat4xarpPerformanceMonitor 78 }

sm48tat4xarpDelayMeasureStateNtoFRxTimeout OBJECT-TYPE
   SYNTAX      Integer32
   MAX-ACCESS  read-only
   STATUS      current
   DESCRIPTION
       "The accumulated receive timeout count for two-way only - since last 'clear'.
	   "
   ::= { sm48tat4xarpPerformanceMonitor 79 }

sm48tat4xarpDelayMeasureStateNtoFRxError OBJECT-TYPE
   SYNTAX      Integer32
   MAX-ACCESS  read-only
   STATUS      current
   DESCRIPTION
       "The accumulated receive error count - since last 'clear'.
	   This is counting if the frame delay is larger than 1 second or if far end residence time is larger than the round trip time.
	   "
   ::= { sm48tat4xarpPerformanceMonitor 80 }

sm48tat4xarpDelayMeasureStateNtoFAvDelayTot OBJECT-TYPE
   SYNTAX      Integer32
   MAX-ACCESS  read-only
   STATUS      current
   DESCRIPTION
       "The average total delay - since last 'clear'.
	   "
   ::= { sm48tat4xarpPerformanceMonitor 81 }

sm48tat4xarpDelayMeasureStateNtoFAvDelaylastN OBJECT-TYPE
   SYNTAX      Integer32
   MAX-ACCESS  read-only
   STATUS      current
   DESCRIPTION
       "The average delay of the last n packets - since last 'clear'.
	   "
   ::= { sm48tat4xarpPerformanceMonitor 82 }

sm48tat4xarpDelayMeasureStateNtoFDelayMin OBJECT-TYPE
   SYNTAX      Integer32
   MAX-ACCESS  read-only
   STATUS      current
   DESCRIPTION
       "The minimum delay - since last 'clear'.
	   "
   ::= { sm48tat4xarpPerformanceMonitor 83 }

sm48tat4xarpDelayMeasureStateNtoFDelayMax OBJECT-TYPE
   SYNTAX      Integer32
   MAX-ACCESS  read-only
   STATUS      current
   DESCRIPTION
       "The maximum delay - since last 'clear'.
	   "
   ::= { sm48tat4xarpPerformanceMonitor 84 }

sm48tat4xarpDelayMeasureStateNtoFAvDelayVarTot OBJECT-TYPE
   SYNTAX      Integer32
   MAX-ACCESS  read-only
   STATUS      current
   DESCRIPTION
       "The average total delay variation - since last 'clear'.
	   "
   ::= { sm48tat4xarpPerformanceMonitor 85 }

sm48tat4xarpDelayMeasureStateNtoFAvDelayVarlastN OBJECT-TYPE
   SYNTAX      Integer32
   MAX-ACCESS  read-only
   STATUS      current
   DESCRIPTION
       "The average delay variation of the last n packets - since last 'clear'.
	   "
   ::= { sm48tat4xarpPerformanceMonitor 86 }

sm48tat4xarpDelayMeasureStateNtoFDelayVarMin OBJECT-TYPE
   SYNTAX      Integer32
   MAX-ACCESS  read-only
   STATUS      current
   DESCRIPTION
       "The minimum delay variation - since last 'clear'.
	   "
   ::= { sm48tat4xarpPerformanceMonitor 87 }

sm48tat4xarpDelayMeasureStateNtoFDelayVarMax OBJECT-TYPE
   SYNTAX      Integer32
   MAX-ACCESS  read-only
   STATUS      current
   DESCRIPTION
       "The maximum delay variation - since last 'clear'.
	   "
   ::= { sm48tat4xarpPerformanceMonitor 88 }

sm48tat4xarpDelayMeasureStateNtoFOverflow OBJECT-TYPE
   SYNTAX      Integer32
   MAX-ACCESS  read-only
   STATUS      current
   DESCRIPTION
       "The number of counter overflow - since last 'clear'.
	   "
   ::= { sm48tat4xarpPerformanceMonitor 89 }

sm48tat4xarpDelayMeasureStateTwowayTx OBJECT-TYPE
   SYNTAX      Integer32
   MAX-ACCESS  read-only
   STATUS      current
   DESCRIPTION
       "The accumulated transmit count - since last 'clear'.
	   "
   ::= { sm48tat4xarpPerformanceMonitor 90 }

sm48tat4xarpDelayMeasureStateTwowayRx OBJECT-TYPE
   SYNTAX      Integer32
   MAX-ACCESS  read-only
   STATUS      current
   DESCRIPTION
       "The accumulated receive count - since last 'clear'.
	   "
   ::= { sm48tat4xarpPerformanceMonitor 91 }

sm48tat4xarpDelayMeasureStateTwowayRxTimeout OBJECT-TYPE
   SYNTAX      Integer32
   MAX-ACCESS  read-only
   STATUS      current
   DESCRIPTION
       "The accumulated receive timeout count for two-way only - since last 'clear'.
	   "
   ::= { sm48tat4xarpPerformanceMonitor 92 }

sm48tat4xarpDelayMeasureStateTwowayRxError OBJECT-TYPE
   SYNTAX      Integer32
   MAX-ACCESS  read-only
   STATUS      current
   DESCRIPTION
       "The accumulated receive error count - since last 'clear'.
	   This is counting if the frame delay is larger than 1 second or if far end residence time is larger than the round trip time.
	   "
   ::= { sm48tat4xarpPerformanceMonitor 93 }

sm48tat4xarpDelayMeasureStateTwowayAvDelayTot OBJECT-TYPE
   SYNTAX      Integer32
   MAX-ACCESS  read-only
   STATUS      current
   DESCRIPTION
       "The average total delay - since last 'clear'.
	   "
   ::= { sm48tat4xarpPerformanceMonitor 94 }

sm48tat4xarpDelayMeasureStateTwowayAvDelaylastN OBJECT-TYPE
   SYNTAX      Integer32
   MAX-ACCESS  read-only
   STATUS      current
   DESCRIPTION
       "The average delay of the last n packets - since last 'clear'.
	   "
   ::= { sm48tat4xarpPerformanceMonitor 95 }

sm48tat4xarpDelayMeasureStateTwowayDelayMin OBJECT-TYPE
   SYNTAX      Integer32
   MAX-ACCESS  read-only
   STATUS      current
   DESCRIPTION
       "The minimum delay - since last 'clear'.
	   "
   ::= { sm48tat4xarpPerformanceMonitor 96 }

sm48tat4xarpDelayMeasureStateTwowayDelayMax OBJECT-TYPE
   SYNTAX      Integer32
   MAX-ACCESS  read-only
   STATUS      current
   DESCRIPTION
       "The maximum delay - since last 'clear'.
	   "
   ::= { sm48tat4xarpPerformanceMonitor 97 }

sm48tat4xarpDelayMeasureStateTwowayAvDelayVarTot OBJECT-TYPE
   SYNTAX      Integer32
   MAX-ACCESS  read-only
   STATUS      current
   DESCRIPTION
       "The average total delay variation - since last 'clear'.
	   "
   ::= { sm48tat4xarpPerformanceMonitor 98 }

sm48tat4xarpDelayMeasureStateTwowayAvDelayVarlastN OBJECT-TYPE
   SYNTAX      Integer32
   MAX-ACCESS  read-only
   STATUS      current
   DESCRIPTION
       "The average delay variation of the last n packets - since last 'clear'.
	   "
   ::= { sm48tat4xarpPerformanceMonitor 99 }

sm48tat4xarpDelayMeasureStateTwowayDelayVarMin OBJECT-TYPE
   SYNTAX      Integer32
   MAX-ACCESS  read-only
   STATUS      current
   DESCRIPTION
       "The minimum delay variation - since last 'clear'.
	   "
   ::= { sm48tat4xarpPerformanceMonitor 100 }

sm48tat4xarpDelayMeasureStateTwowayDelayVarMax OBJECT-TYPE
   SYNTAX      Integer32
   MAX-ACCESS  read-only
   STATUS      current
   DESCRIPTION
       "The maximum delay variation - since last 'clear'.
	   "
   ::= { sm48tat4xarpPerformanceMonitor 101 }

sm48tat4xarpDelayMeasureStateTwowayOverflow OBJECT-TYPE
   SYNTAX      Integer32
   MAX-ACCESS  read-only
   STATUS      current
   DESCRIPTION
       "The number of counter overflow - since last 'clear'.
	   "
   ::= { sm48tat4xarpPerformanceMonitor 102 }

sm48tat4xarpDelayMeasureStateClear OBJECT-TYPE
   SYNTAX      Integer32
   MAX-ACCESS  read-write
   STATUS      current
   DESCRIPTION
       "Set of this check and save will clear the accumulated counters.
	   1:clear
	   "
   ::= { sm48tat4xarpPerformanceMonitor 103 }

sm48tat4xarpDelayMeasureBinsMeasurementBinsforFD OBJECT-TYPE
   SYNTAX      Integer32
   MAX-ACCESS  read-write
   STATUS      current
   DESCRIPTION
       "Configurable number of Frame Delay Measurement Bins per Measurement Interval.
	   range: 2-10
	   "
   ::= { sm48tat4xarpPerformanceMonitor 104 }

sm48tat4xarpDelayMeasureBinsMeasurementBinsforIFDV OBJECT-TYPE
   SYNTAX      Integer32
   MAX-ACCESS  read-write
   STATUS      current
   DESCRIPTION
       "Configurable number of Inter-Frame Delay Variation Measurement Bins per Measurement Interval.
	   range: 2-10
	   "
   ::= { sm48tat4xarpPerformanceMonitor 105 }

sm48tat4xarpDelayMeasureBinsMeasurementThreshold OBJECT-TYPE
   SYNTAX      Integer32
   MAX-ACCESS  read-write
   STATUS      current
   DESCRIPTION
       "Configurable the Measurement Threshold for each Measurement Bin.
	   "
   ::= { sm48tat4xarpPerformanceMonitor 106 }




sm48tat4xarpPerformanceMonitorDelayMeasurementBinsforFDTable OBJECT-TYPE
   SYNTAX      SEQUENCE OF SM48TAT4XARPPerformanceMonitorDelayMeasurementBinsforFDEntry
   MAX-ACCESS  not-accessible
   STATUS      current
   DESCRIPTION
       " "
   ::= { sm48tat4xarpMEP 16 }

sm48tat4xarpPerformanceMonitorDelayMeasurementBinsforFDEntry OBJECT-TYPE
   SYNTAX      SM48TAT4XARPPerformanceMonitorDelayMeasurementBinsforFDEntry
   MAX-ACCESS  not-accessible
   STATUS      current
   DESCRIPTION
       " "
   INDEX    { sm48tat4xarpPerformanceMonitorDelayMeasurementBinsforFDIndex  }
   ::= { sm48tat4xarpPerformanceMonitorDelayMeasurementBinsforFDTable 1 }

SM48TAT4XARPPerformanceMonitorDelayMeasurementBinsforFDEntry ::= SEQUENCE {
   sm48tat4xarpPerformanceMonitorDelayMeasurementBinsforFDIndex    Integer32,
   sm48tat4xarpPerformanceMonitorDelayMeasurementBinsforFDOneway   Integer32,
   sm48tat4xarpPerformanceMonitorDelayMeasurementBinsforFDFtoN     Integer32,
   sm48tat4xarpPerformanceMonitorDelayMeasurementBinsforFDNtoF     Integer32,
   sm48tat4xarpPerformanceMonitorDelayMeasurementBinsforFDTwoway   Integer32

}

sm48tat4xarpPerformanceMonitorDelayMeasurementBinsforFDIndex OBJECT-TYPE
   SYNTAX      Integer32(1..65535)
   MAX-ACCESS  not-accessible
   STATUS      current
   DESCRIPTION
       "Index"
   ::= { sm48tat4xarpPerformanceMonitorDelayMeasurementBinsforFDEntry 1 }

sm48tat4xarpPerformanceMonitorDelayMeasurementBinsforFDOneway OBJECT-TYPE
   SYNTAX      Integer32
   MAX-ACCESS  read-only
   STATUS      current
   DESCRIPTION
       " "
   ::= { sm48tat4xarpPerformanceMonitorDelayMeasurementBinsforFDEntry 2 }

sm48tat4xarpPerformanceMonitorDelayMeasurementBinsforFDFtoN OBJECT-TYPE
   SYNTAX      Integer32
   MAX-ACCESS  read-only
   STATUS      current
   DESCRIPTION
       " "
   ::= { sm48tat4xarpPerformanceMonitorDelayMeasurementBinsforFDEntry 3 }

sm48tat4xarpPerformanceMonitorDelayMeasurementBinsforFDNtoF OBJECT-TYPE
   SYNTAX      Integer32
   MAX-ACCESS  read-only
   STATUS      current
   DESCRIPTION
       " "
   ::= { sm48tat4xarpPerformanceMonitorDelayMeasurementBinsforFDEntry 4 }

sm48tat4xarpPerformanceMonitorDelayMeasurementBinsforFDTwoway OBJECT-TYPE
   SYNTAX      Integer32
   MAX-ACCESS  read-only
   STATUS      current
   DESCRIPTION
       " "
   ::= { sm48tat4xarpPerformanceMonitorDelayMeasurementBinsforFDEntry 5 }




sm48tat4xarpPerformanceMonitorDelayMeasurementBinsforIFDVTable OBJECT-TYPE
   SYNTAX      SEQUENCE OF SM48TAT4XARPPerformanceMonitorDelayMeasurementBinsforIFDVEntry
   MAX-ACCESS  not-accessible
   STATUS      current
   DESCRIPTION
       " "
   ::= { sm48tat4xarpMEP 17 }

sm48tat4xarpPerformanceMonitorDelayMeasurementBinsforIFDVEntry OBJECT-TYPE
   SYNTAX      SM48TAT4XARPPerformanceMonitorDelayMeasurementBinsforIFDVEntry
   MAX-ACCESS  not-accessible
   STATUS      current
   DESCRIPTION
       " "
   INDEX    { sm48tat4xarpPerformanceMonitorDelayMeasureBinsforIFDVIndex  }
   ::= { sm48tat4xarpPerformanceMonitorDelayMeasurementBinsforIFDVTable 1 }

SM48TAT4XARPPerformanceMonitorDelayMeasurementBinsforIFDVEntry ::= SEQUENCE {
   sm48tat4xarpPerformanceMonitorDelayMeasureBinsforIFDVIndex    Integer32,
   sm48tat4xarpPerformanceMonitorDelayMeasureBinsforIFDVOneway   Integer32,
   sm48tat4xarpPerformanceMonitorDelayMeasureBinsforIFDVFtoN     Integer32,
   sm48tat4xarpPerformanceMonitorDelayMeasureBinsforIFDVNtoF     Integer32,
   sm48tat4xarpPerformanceMonitorDelayMeasureBinsforIFDVTwoway   Integer32

}

sm48tat4xarpPerformanceMonitorDelayMeasureBinsforIFDVIndex OBJECT-TYPE
   SYNTAX      Integer32(1..65535)
   MAX-ACCESS  not-accessible
   STATUS      current
   DESCRIPTION
       "Index"
   ::= { sm48tat4xarpPerformanceMonitorDelayMeasurementBinsforIFDVEntry 1 }

sm48tat4xarpPerformanceMonitorDelayMeasureBinsforIFDVOneway OBJECT-TYPE
   SYNTAX      Integer32
   MAX-ACCESS  read-only
   STATUS      current
   DESCRIPTION
       " "
   ::= { sm48tat4xarpPerformanceMonitorDelayMeasurementBinsforIFDVEntry 2 }

sm48tat4xarpPerformanceMonitorDelayMeasureBinsforIFDVFtoN OBJECT-TYPE
   SYNTAX      Integer32
   MAX-ACCESS  read-only
   STATUS      current
   DESCRIPTION
       " "
   ::= { sm48tat4xarpPerformanceMonitorDelayMeasurementBinsforIFDVEntry 3 }

sm48tat4xarpPerformanceMonitorDelayMeasureBinsforIFDVNtoF OBJECT-TYPE
   SYNTAX      Integer32
   MAX-ACCESS  read-only
   STATUS      current
   DESCRIPTION
       " "
   ::= { sm48tat4xarpPerformanceMonitorDelayMeasurementBinsforIFDVEntry 4 }

sm48tat4xarpPerformanceMonitorDelayMeasureBinsforIFDVTwoway OBJECT-TYPE
   SYNTAX      Integer32
   MAX-ACCESS  read-only
   STATUS      current
   DESCRIPTION
       " "
   ::= { sm48tat4xarpPerformanceMonitorDelayMeasurementBinsforIFDVEntry 5 }
-- =============================================================================================================
sm48tat4xarpPTP    OBJECT IDENTIFIER ::= { sm48tat4xarpConfiguration 28 }

sm48tat4xarpPTPExternalEnable OBJECT-TYPE
   SYNTAX      Integer32
   MAX-ACCESS  read-write
   STATUS      current
   DESCRIPTION
       "This Selection box will allow you to configure the External Clock output.
		The following values are possible:
		1. True : Enable the external clock output
		0. False : Disable the external clock output
		"
   ::= { sm48tat4xarpPTP 1 }

sm48tat4xarpPTPAdjustMethod OBJECT-TYPE
   SYNTAX      Integer32
   MAX-ACCESS  read-write
   STATUS      current
   DESCRIPTION
       "This Selection box will allow you to configure the Frequency adjustment configuration.
		0: LTC frequency : Select Local Time Counter (LTC) frequency control
		1: SyncE-DPLL : Select SyncE DPLL frequency control, if allowed by SyncE
		2: Oscillator : Select an oscillator independent of SyncE for frequency control, if supported by the HW
		3: LTC phase : Select Local Time Counter (LTC) phase control (assumes that the frequency is locked by means of SyncE)
		"
   ::= { sm48tat4xarpPTP 2 }

sm48tat4xarpPTPClockFrequency OBJECT-TYPE
   SYNTAX      Integer32
   MAX-ACCESS  read-write
   STATUS      current
   DESCRIPTION
       "This will allow to set the Clock Frequency.
        The possible range of values are 1 - 25000000 (1 - 25MHz)
	   "
   ::= { sm48tat4xarpPTP 3 }



sm48tat4xarpPTPClockConfTable  OBJECT-TYPE
   SYNTAX      SEQUENCE OF SM48TAT4XARPPTPClockConfEntry
   MAX-ACCESS  not-accessible
   STATUS      current
   DESCRIPTION
       "A table of PTP Clock Conf."
 ::= { sm48tat4xarpPTP 5 }

sm48tat4xarpPTPClockConfEntry OBJECT-TYPE
    SYNTAX        SM48TAT4XARPPTPClockConfEntry
    MAX-ACCESS    not-accessible
    STATUS        current
    DESCRIPTION
        "An entry in the PTP Clock Conf table."
    INDEX        { sm48tat4xarpPTPClockConfIndex }
    ::= { sm48tat4xarpPTPClockConfTable 1 }

SM48TAT4XARPPTPClockConfEntry ::=
    SEQUENCE {
        sm48tat4xarpPTPClockConfIndex                    Integer32,
        sm48tat4xarpPTPClockConfClockInstance            Integer32,
        sm48tat4xarpPTPClockConfDeviceType               Integer32,
		sm48tat4xarpPTPClockConfProfile                  Integer32,
        sm48tat4xarpPTPClockConfRowStatus                RowStatus
    }

sm48tat4xarpPTPClockConfIndex OBJECT-TYPE
   SYNTAX      Integer32(1..65535)
   MAX-ACCESS  not-accessible
   STATUS      current
   DESCRIPTION
       "PTP Clock Conf index."
   ::= {sm48tat4xarpPTPClockConfEntry 1 }

sm48tat4xarpPTPClockConfClockInstance OBJECT-TYPE
   SYNTAX      Integer32
   MAX-ACCESS  read-create
   STATUS      current
   DESCRIPTION
       "Indicates the Instance of a particular Clock Instance [0..3]."
   ::= {sm48tat4xarpPTPClockConfEntry 2 }

sm48tat4xarpPTPClockConfDeviceType OBJECT-TYPE
   SYNTAX      Integer32
   MAX-ACCESS  read-create
   STATUS      current
   DESCRIPTION
       "Indicates the Type of the Clock Instance. There are five Device Types.
	    0: Inactive - passive clock instance
		1: Ord-Bound - clock's Device Type is Ordinary-Boundary Clock.
		2: P2p Transp - clock's Device Type is Peer to Peer Transparent Clock.
		3: E2e Transp - clock's Device Type is End to End Transparent Clock.
		4: Master Only - clock's Device Type is Master Only.
		5: Slave Only - clock's Device Type is Slave Only.
		6: Boundary Clock frontend clock instance, only 1-step, 1-way is supported."
   ::= {sm48tat4xarpPTPClockConfEntry 3 }

sm48tat4xarpPTPClockConfProfile OBJECT-TYPE
   SYNTAX      Integer32
   MAX-ACCESS  read-create
   STATUS      current
   DESCRIPTION
       "0:No profile
	   1:1588
	   2:G8265.1
	   3:G8275.1
	   "
   ::= {sm48tat4xarpPTPClockConfEntry 4 }

sm48tat4xarpPTPClockConfRowStatus OBJECT-TYPE
   SYNTAX      RowStatus
   MAX-ACCESS  read-create
   STATUS      current
   DESCRIPTION
       "PTP Clock Conf Row Status."
   ::= {sm48tat4xarpPTPClockConfEntry 5 }

sm48tat4xarpPTPClockInstance OBJECT-TYPE
   SYNTAX      Integer32
   MAX-ACCESS  read-write
   STATUS      current
   DESCRIPTION
       "Specify the PTP clock instance for the following item used [0..3]."
   ::= {sm48tat4xarpPTP 6 }


sm48tat4xarpPTPClockConfAndStatus    OBJECT IDENTIFIER ::= { sm48tat4xarpPTP 7 }

sm48tat4xarpEntryClockInstance OBJECT-TYPE
   SYNTAX      Integer32
   MAX-ACCESS  read-only
   STATUS      current
   DESCRIPTION
       ""
   ::= {sm48tat4xarpPTPClockConfAndStatus 2 }

sm48tat4xarpEntryDeviceType OBJECT-TYPE
   SYNTAX      DisplayString
   MAX-ACCESS  read-only
   STATUS      current
   DESCRIPTION
       ""
   ::= {sm48tat4xarpPTPClockConfAndStatus 3 }

sm48tat4xarpEntryProfile OBJECT-TYPE
   SYNTAX      DisplayString
   MAX-ACCESS  read-only
   STATUS      current
   DESCRIPTION
       ""
   ::= {sm48tat4xarpPTPClockConfAndStatus 4 }

sm48tat4xarpEntryApplyProfileDefaults OBJECT-TYPE
   SYNTAX      Integer32
   MAX-ACCESS  read-write
   STATUS      current
   DESCRIPTION
       "-1:n/a
	   0:normal state
	   1:apply profile default"
   ::= {sm48tat4xarpPTPClockConfAndStatus 5 }

sm48tat4xarpEntryPTPTime OBJECT-TYPE
   SYNTAX      DisplayString
   MAX-ACCESS  read-only
   STATUS      current
   DESCRIPTION
       "Shows the actual PTP time with nanosecond resolution."
   ::= {sm48tat4xarpPTPClockConfAndStatus 6 }

sm48tat4xarpEntryClockAdjustmentMethod OBJECT-TYPE
   SYNTAX      DisplayString
   MAX-ACCESS  read-only
   STATUS      current
   DESCRIPTION
       "Shows the actual clock adjustment method. The method depends on the available hardware."
   ::= {sm48tat4xarpPTPClockConfAndStatus 7 }

sm48tat4xarpEntrySynchronizeToSystemClock OBJECT-TYPE
   SYNTAX      Integer32
   MAX-ACCESS  read-write
   STATUS      current
   DESCRIPTION
       "Activate this button to synchronize the System Clock to PTP Time.
	   1:Synchronize to system clock."
   ::= {sm48tat4xarpPTPClockConfAndStatus 8 }

sm48tat4xarpEntryClockCurrentDataSetstpRm OBJECT-TYPE
   SYNTAX      Integer32
   MAX-ACCESS  read-only
   STATUS      current
   DESCRIPTION
       "Steps Removed : It is the number of PTP clocks traversed from the grandmaster to the local slave clock."
   ::= {sm48tat4xarpPTPClockConfAndStatus 9 }

sm48tat4xarpEntryClockCurrentDataSetOffsetFromMaster OBJECT-TYPE
   SYNTAX      DisplayString
   MAX-ACCESS  read-only
   STATUS      current
   DESCRIPTION
       "Time difference between the master clock and the local slave clock, measured in ns."
   ::= {sm48tat4xarpPTPClockConfAndStatus 10 }

sm48tat4xarpEntryClockCurrentDataSetMeanPathDelay OBJECT-TYPE
   SYNTAX      DisplayString
   MAX-ACCESS  read-only
   STATUS      current
   DESCRIPTION
       "The mean propagation time for the link between the master and the local slave."
   ::= {sm48tat4xarpPTPClockConfAndStatus 11 }

sm48tat4xarpEntryClockCurrentDataSetSlavePort OBJECT-TYPE
   SYNTAX      Integer32
   MAX-ACCESS  read-only
   STATUS      current
   DESCRIPTION
       "Shows which port is in slave mode. The value is 0 if no ports are in slave mode."
   ::= {sm48tat4xarpPTPClockConfAndStatus 12 }

sm48tat4xarpEntryClockCurrentDataSetSlaveState OBJECT-TYPE
   SYNTAX      DisplayString
   MAX-ACCESS  read-only
   STATUS      current
   DESCRIPTION
       "Shows synchronization state of the slave."
   ::= {sm48tat4xarpPTPClockConfAndStatus 13 }

sm48tat4xarpEntryClockCurrentDataSetHoldover OBJECT-TYPE
   SYNTAX      DisplayString
   MAX-ACCESS  read-only
   STATUS      current
   DESCRIPTION
       "After the slave has been in Locked mode during the stabilization period,
	   this value shows the actual clock offset between the freerun and the actual holdover frequency,
	   the value is shown in parts pr billion (ppb).
	   During the stabilization period, the value is shown as N.A.
	   The stabilization period is 60 sec as default, it can be changed from the CLI interface."
   ::= {sm48tat4xarpPTPClockConfAndStatus 14 }

sm48tat4xarpEntryClockParentDataSetParentPortID OBJECT-TYPE
   SYNTAX      DisplayString
   MAX-ACCESS  read-only
   STATUS      current
   DESCRIPTION
       "Clock identity for the parent clock, if the local clock is not a slave, the value is the clocks own id."
   ::= {sm48tat4xarpPTPClockConfAndStatus 15 }

sm48tat4xarpEntryClockParentDataSetPort OBJECT-TYPE
   SYNTAX      Integer32
   MAX-ACCESS  read-only
   STATUS      current
   DESCRIPTION
       "Port Id for the parent master port"
   ::= {sm48tat4xarpPTPClockConfAndStatus 16 }

sm48tat4xarpEntryClockParentDataSetPStat OBJECT-TYPE
   SYNTAX      DisplayString
   MAX-ACCESS  read-only
   STATUS      current
   DESCRIPTION
       "Parents Stats (always false)."
   ::= {sm48tat4xarpPTPClockConfAndStatus 17 }

sm48tat4xarpEntryClockParentDataSetVar OBJECT-TYPE
   SYNTAX      Integer32
   MAX-ACCESS  read-only
   STATUS      current
   DESCRIPTION
       "It is observed parent offset scaled log variance"
   ::= {sm48tat4xarpPTPClockConfAndStatus 18 }

sm48tat4xarpEntryClockParentDataSetRate OBJECT-TYPE
   SYNTAX      Integer32
   MAX-ACCESS  read-only
   STATUS      current
   DESCRIPTION
       "Observed Parent Clock Phase Change Rate. i.e. the slave clocks rate offset compared to the master.
	   (unit = ns per s)."
   ::= {sm48tat4xarpPTPClockConfAndStatus 19 }

sm48tat4xarpEntryClockParentDataSetGrandMasterID OBJECT-TYPE
   SYNTAX      DisplayString
   MAX-ACCESS  read-only
   STATUS      current
   DESCRIPTION
       "Clock identity for the grand master clock, if the local clock is not a slave, the value is the clocks own id."
   ::= {sm48tat4xarpPTPClockConfAndStatus 20 }

sm48tat4xarpParentDataSetGrandMasterClockQuality OBJECT-TYPE
   SYNTAX      DisplayString
   MAX-ACCESS  read-only
   STATUS      current
   DESCRIPTION
       "The clock quality announced by the grand master (See description of Clock Default DataSet:Clock Quality)"
   ::= {sm48tat4xarpPTPClockConfAndStatus 21 }

sm48tat4xarpEntryClockParentDataSetPri1 OBJECT-TYPE
   SYNTAX      Integer32
   MAX-ACCESS  read-only
   STATUS      current
   DESCRIPTION
       "Clock priority 1 announced by the grand master"
   ::= {sm48tat4xarpPTPClockConfAndStatus 22 }

sm48tat4xarpEntryClockParentDataSetPri2 OBJECT-TYPE
   SYNTAX      Integer32
   MAX-ACCESS  read-only
   STATUS      current
   DESCRIPTION
       "Clock priority 2 announced by the grand master."
   ::= {sm48tat4xarpPTPClockConfAndStatus 23 }

sm48tat4xarpEntryClockDefaultDataSetClockID OBJECT-TYPE
   SYNTAX      Integer32
   MAX-ACCESS  read-only
   STATUS      current
   DESCRIPTION
       "An internal instance id (0..3)"
   ::= {sm48tat4xarpPTPClockConfAndStatus 24 }

sm48tat4xarpEntryClockDefaultDataSetDeviceType OBJECT-TYPE
   SYNTAX      DisplayString
   MAX-ACCESS  read-only
   STATUS      current
   DESCRIPTION
       "Indicates the Type of the Clock Instance. There are five Device Types.
		1. Ord-Bound - Clock's Device Type is Ordinary-Boundary Clock.
		2. P2p Transp - Clock's Device Type is Peer to Peer Transparent Clock.
		3. E2e Transp - Clock's Device Type is End to End Transparent Clock.
		4. Master Only - Clock's Device Type is Master Only.
		5. Slave Only - Clock's Device Type is Slave Only."
   ::= {sm48tat4xarpPTPClockConfAndStatus 25 }

sm48tat4xarpEntryClockDefaultDataSet2StepFlag OBJECT-TYPE
   SYNTAX      Integer32
   MAX-ACCESS  read-write
   STATUS      current
   DESCRIPTION
       "True if two-step Sync events and Pdelay_Resp events are used
	   0:false
	   1:true"
   ::= {sm48tat4xarpPTPClockConfAndStatus 26 }

sm48tat4xarpEntryClockDefaultDataSetPorts OBJECT-TYPE
   SYNTAX      Integer32
   MAX-ACCESS  read-only
   STATUS      current
   DESCRIPTION
       "The total number of physical ports in the node"
   ::= {sm48tat4xarpPTPClockConfAndStatus 27 }

sm48tat4xarpEntryClockDefaultDataSetClockIdentity OBJECT-TYPE
   SYNTAX      DisplayString
   MAX-ACCESS  read-only
   STATUS      current
   DESCRIPTION
       "It shows unique clock identifier"
   ::= {sm48tat4xarpPTPClockConfAndStatus 28 }

sm48tat4xarpEntryClockDefaultDataSetDom OBJECT-TYPE
   SYNTAX      Integer32
   MAX-ACCESS  read-write
   STATUS      current
   DESCRIPTION
       "Clock domain [0..127]."
   ::= {sm48tat4xarpPTPClockConfAndStatus 29 }

sm48tat4xarpEntryClockDefaultDataSetClockQuality OBJECT-TYPE
   SYNTAX      DisplayString
   MAX-ACCESS  read-only
   STATUS      current
   DESCRIPTION
       "The clock quality is determined by the system, and holds 3 parts: Clock Class, Clock Accuracy and OffsetScaledLog Variance as defined in IEEE1588.
The Clock Accuracy values are defined in IEEE1588 table 6 (Currently the clock Accuracy is set to 'Unknown' as default)."
   ::= {sm48tat4xarpPTPClockConfAndStatus 30 }

sm48tat4xarpEntryClockDefaultDataSetPri1 OBJECT-TYPE
   SYNTAX      Integer32
   MAX-ACCESS  read-write
   STATUS      current
   DESCRIPTION
       "Clock priority 1 [0..255] used by the BMC master select algorithm."
   ::= {sm48tat4xarpPTPClockConfAndStatus 31 }

sm48tat4xarpEntryClockDefaultDataSetPri2 OBJECT-TYPE
   SYNTAX      Integer32
   MAX-ACCESS  read-write
   STATUS      current
   DESCRIPTION
       "Clock priority 2 [0..255] used by the BMC master select algorithm."
   ::= {sm48tat4xarpPTPClockConfAndStatus 32 }

sm48tat4xarpEntryClockDefaultDataSetProtocol OBJECT-TYPE
   SYNTAX      Integer32
   MAX-ACCESS  read-write
   STATUS      current
   DESCRIPTION
       "0:Ethernet
	   1:Ethernet Mixed
	   2:IP4Multi
	   3:IP4Mixed
	   4:IP4Uni
	   5:OAM"
   ::= {sm48tat4xarpPTPClockConfAndStatus 33 }

sm48tat4xarpEntryClockDefaultDataSetOneWay OBJECT-TYPE
   SYNTAX      Integer32
   MAX-ACCESS  read-write
   STATUS      current
   DESCRIPTION
       "If true, one way measurements are used.
	   This parameter applies only to a slave.
	   In one-way mode no delay measurements are performed, i.e. this is applicable only if frequency synchronization is needed.
	   The master always responds to delay requests.
	   0:false
	   1:true"
   ::= {sm48tat4xarpPTPClockConfAndStatus 34 }

sm48tat4xarpEntryClockDefaultDataSetVLANTagEnable OBJECT-TYPE
   SYNTAX      Integer32
   MAX-ACCESS  read-write
   STATUS      current
   DESCRIPTION
       "The VLAN Tag Enable parameter is ignored, because the tagging is controlled by the VLAN configuration.
	   0:false
	   1:true"
   ::= {sm48tat4xarpPTPClockConfAndStatus 35 }

sm48tat4xarpEntryClockDefaultDataSetVID OBJECT-TYPE
   SYNTAX      Integer32
   MAX-ACCESS  read-write
   STATUS      current
   DESCRIPTION
       "TVLAN Identifier used for tagging the VLAN packets.
	   range:1-4095"
   ::= {sm48tat4xarpPTPClockConfAndStatus 36 }

sm48tat4xarpEntryClockDefaultDataSetPCP OBJECT-TYPE
   SYNTAX      Integer32
   MAX-ACCESS  read-write
   STATUS      current
   DESCRIPTION
       "Priority Code Point value used for PTP frames. range:0-7"
   ::= {sm48tat4xarpPTPClockConfAndStatus 37 }

sm48tat4xarpEntryClockDefaultDataSetDSCP OBJECT-TYPE
   SYNTAX      Integer32
   MAX-ACCESS  read-write
   STATUS      current
   DESCRIPTION
       ""
   ::= {sm48tat4xarpPTPClockConfAndStatus 38 }

sm48tat4xarpEntryClockTimePropertiesDataSetUtcOffset OBJECT-TYPE
   SYNTAX      Integer32
   MAX-ACCESS  read-write
   STATUS      current
   DESCRIPTION
       "range: 0-10000"
   ::= {sm48tat4xarpPTPClockConfAndStatus 39 }

sm48tat4xarpEntryClockTimePropertiesDataSetValid OBJECT-TYPE
   SYNTAX      Integer32
   MAX-ACCESS  read-write
   STATUS      current
   DESCRIPTION
       "0:false
	   1:true"
   ::= {sm48tat4xarpPTPClockConfAndStatus 40 }

sm48tat4xarpEntryClockTimePropertiesDataSetLeap59 OBJECT-TYPE
   SYNTAX      Integer32
   MAX-ACCESS  read-write
   STATUS      current
   DESCRIPTION
       "0:false
	   1:true"
   ::= {sm48tat4xarpPTPClockConfAndStatus 41 }

sm48tat4xarpEntryClockTimePropertiesDataSetLeap61 OBJECT-TYPE
   SYNTAX      Integer32
   MAX-ACCESS  read-write
   STATUS      current
   DESCRIPTION
       "0:false
	   1:true"
   ::= {sm48tat4xarpPTPClockConfAndStatus 42 }

sm48tat4xarpEntryClockTimePropertiesDataSetTimeTrac OBJECT-TYPE
   SYNTAX      Integer32
   MAX-ACCESS  read-write
   STATUS      current
   DESCRIPTION
       "0:false
	   1:true"
   ::= {sm48tat4xarpPTPClockConfAndStatus 43 }

sm48tat4xarpEntryClockTimePropertiesDataSetFreqTrac OBJECT-TYPE
   SYNTAX      Integer32
   MAX-ACCESS  read-write
   STATUS      current
   DESCRIPTION
       "0:false
	   1:true"
   ::= {sm48tat4xarpPTPClockConfAndStatus 44 }

sm48tat4xarpTimePropertiesDataSetPTPTimeScale OBJECT-TYPE
   SYNTAX      Integer32
   MAX-ACCESS  read-write
   STATUS      current
   DESCRIPTION
       "0:false
	   1:true"
   ::= {sm48tat4xarpPTPClockConfAndStatus 45 }

sm48tat4xarpEntryClockTimePropertiesDataSetTimeSource OBJECT-TYPE
   SYNTAX      Integer32
   MAX-ACCESS  read-write
   STATUS      current
   DESCRIPTION
       "range: 0-255"
   ::= {sm48tat4xarpPTPClockConfAndStatus 46 }

sm48tat4xarpEntryFilterParametersFilterType OBJECT-TYPE
   SYNTAX      Integer32
   MAX-ACCESS  read-write
   STATUS      current
   DESCRIPTION
       "Shows the filter type used which can be either the basic filter or an advanced filter that can be configured to use only a fraction of the packets received
	   (i.e. the packets that have experienced the least latency).
	   0:BASIC"
   ::= {sm48tat4xarpPTPClockConfAndStatus 47 }

sm48tat4xarpEntryFilterParametersDelayFilter OBJECT-TYPE
   SYNTAX      Integer32
   MAX-ACCESS  read-write
   STATUS      current
   DESCRIPTION
       "range:0-6"
   ::= {sm48tat4xarpPTPClockConfAndStatus 48 }

sm48tat4xarpEntryFilterParametersPeriod OBJECT-TYPE
   SYNTAX      Integer32
   MAX-ACCESS  read-write
   STATUS      current
   DESCRIPTION
       "range:1-10000"
   ::= {sm48tat4xarpPTPClockConfAndStatus 49 }

sm48tat4xarpEntryFilterParametersDist OBJECT-TYPE
   SYNTAX      Integer32
   MAX-ACCESS  read-write
   STATUS      current
   DESCRIPTION
       "range:1-10"
   ::= {sm48tat4xarpPTPClockConfAndStatus 50 }

sm48tat4xarpEntryServoParametersDisplay OBJECT-TYPE
   SYNTAX      Integer32
   MAX-ACCESS  read-write
   STATUS      current
   DESCRIPTION
       "If true then Offset From Master, MeanPathDelay and clockAdjustment are logged on the debug terminal
	   0:false
	   1:true"
   ::= {sm48tat4xarpPTPClockConfAndStatus 51 }

sm48tat4xarpEntryServoParametersPEnable OBJECT-TYPE
   SYNTAX      Integer32
   MAX-ACCESS  read-write
   STATUS      current
   DESCRIPTION
       "If true the P part of the algorithm is included
	   0:false
	   1:true"
   ::= {sm48tat4xarpPTPClockConfAndStatus 52 }

sm48tat4xarpEntryServoParametersIEnable OBJECT-TYPE
   SYNTAX      Integer32
   MAX-ACCESS  read-write
   STATUS      current
   DESCRIPTION
       "If true the I part of the algorithm is included
	   0:false
	   1:true"
   ::= {sm48tat4xarpPTPClockConfAndStatus 53 }

sm48tat4xarpEntryServoParametersDEnable OBJECT-TYPE
   SYNTAX      Integer32
   MAX-ACCESS  read-write
   STATUS      current
   DESCRIPTION
       "If true the D part of the algorithm is included
	   0:false
	   1:true"
   ::= {sm48tat4xarpPTPClockConfAndStatus 54 }

sm48tat4xarpEntryServoParametersPConstant OBJECT-TYPE
   SYNTAX      Integer32
   MAX-ACCESS  read-write
   STATUS      current
   DESCRIPTION
       "range:0-1000"
   ::= {sm48tat4xarpPTPClockConfAndStatus 55 }

sm48tat4xarpEntryServoParametersIConstant OBJECT-TYPE
   SYNTAX      Integer32
   MAX-ACCESS  read-write
   STATUS      current
   DESCRIPTION
       "range:0-10000"
   ::= {sm48tat4xarpPTPClockConfAndStatus 56 }

sm48tat4xarpEntryServoParametersDConstant OBJECT-TYPE
   SYNTAX      Integer32
   MAX-ACCESS  read-write
   STATUS      current
   DESCRIPTION
       "range:0-1000"
   ::= {sm48tat4xarpPTPClockConfAndStatus 57 }


sm48tat4xarpPTPClockPortDataSetConfTable OBJECT-TYPE
   SYNTAX      SEQUENCE OF SM48TAT4XARPPTPClockPortDataSetConfEntry
   MAX-ACCESS  not-accessible
   STATUS      current
   DESCRIPTION
       " "
   ::= { sm48tat4xarpPTP 8 }

sm48tat4xarpPTPClockPortDataSetConfEntry OBJECT-TYPE
   SYNTAX      SM48TAT4XARPPTPClockPortDataSetConfEntry
   MAX-ACCESS  not-accessible
   STATUS      current
   DESCRIPTION
       " "
   INDEX    { sm48tat4xarpPTPClockPortDataSetConfPort  }
   ::= { sm48tat4xarpPTPClockPortDataSetConfTable 1 }

SM48TAT4XARPPTPClockPortDataSetConfEntry ::= SEQUENCE {
   sm48tat4xarpPTPClockPortDataSetConfPort               Integer32,
   sm48tat4xarpPTPClockConfEntryPortConfEnable           Integer32,
   sm48tat4xarpPTPClockConfEntryPortConfStat             DisplayString,
   sm48tat4xarpPTPClockConfEntryPortConfMDR              Integer32,
   sm48tat4xarpPTPClockConfEntryPortConfPeerMeanPathDel  DisplayString,
   sm48tat4xarpPTPClockConfEntryPortConfAnv              Integer32,
   sm48tat4xarpPTPClockConfEntryPortConfATo              Integer32,
   sm48tat4xarpPTPClockConfEntryPortConfSyv              Integer32,
   sm48tat4xarpPTPClockConfEntryPortConfDlm              Integer32,
   sm48tat4xarpPTPClockConfEntryPortConfMPR              Integer32,
   sm48tat4xarpPTPClockConfEntryPortConfDelayAsymmetry   Integer32,
   sm48tat4xarpPTPClockConfEntryPortConfIngressLatency   Integer32,
   sm48tat4xarpPTPClockConfEntryPortConfEgressLatency    Integer32,
   sm48tat4xarpPTPClockConfEntryPortConfVersion          Integer32
}

sm48tat4xarpPTPClockPortDataSetConfPort OBJECT-TYPE
   SYNTAX      Integer32(1..65535)
   MAX-ACCESS  not-accessible
   STATUS      current
   DESCRIPTION
       "Index"
   ::= { sm48tat4xarpPTPClockPortDataSetConfEntry 1 }

sm48tat4xarpPTPClockConfEntryPortConfEnable OBJECT-TYPE
   SYNTAX      Integer32
   MAX-ACCESS  read-write
   STATUS      current
   DESCRIPTION
       "0:false
	   1:true"
   ::= { sm48tat4xarpPTPClockPortDataSetConfEntry 2 }

sm48tat4xarpPTPClockConfEntryPortConfStat OBJECT-TYPE
   SYNTAX      DisplayString
   MAX-ACCESS  read-only
   STATUS      current
   DESCRIPTION
       "Dynamic member portState: Current state of the port."
   ::= { sm48tat4xarpPTPClockPortDataSetConfEntry 3 }

sm48tat4xarpPTPClockConfEntryPortConfMDR OBJECT-TYPE
   SYNTAX      Integer32
   MAX-ACCESS  read-only
   STATUS      current
   DESCRIPTION
       "Dynamic member log Min Delay Req Interval: The delay request interval announced by the master."
   ::= { sm48tat4xarpPTPClockPortDataSetConfEntry 4 }

sm48tat4xarpPTPClockConfEntryPortConfPeerMeanPathDel OBJECT-TYPE
   SYNTAX      DisplayString
   MAX-ACCESS  read-only
   STATUS      current
   DESCRIPTION
       "The path delay measured by the port in P2P mode. In E2E mode this value is 0"
   ::= { sm48tat4xarpPTPClockPortDataSetConfEntry 5 }



sm48tat4xarpPTPClockConfEntryPortConfAnv OBJECT-TYPE
   SYNTAX      Integer32
   MAX-ACCESS  read-write
   STATUS      current
   DESCRIPTION
       "The interval for issuing announce messages in master state. Range is -3 to 4."
   ::= { sm48tat4xarpPTPClockPortDataSetConfEntry 6 }

sm48tat4xarpPTPClockConfEntryPortConfATo OBJECT-TYPE
   SYNTAX      Integer32
   MAX-ACCESS  read-write
   STATUS      current
   DESCRIPTION
       "The timeout for receiving announce messages on the port. Range is 1 to 10."
   ::= { sm48tat4xarpPTPClockPortDataSetConfEntry 7 }

sm48tat4xarpPTPClockConfEntryPortConfSyv OBJECT-TYPE
   SYNTAX      Integer32
   MAX-ACCESS  read-write
   STATUS      current
   DESCRIPTION
       "The interval for issuing sync messages in master. Range is -7 to 4."
   ::= { sm48tat4xarpPTPClockPortDataSetConfEntry 8 }

sm48tat4xarpPTPClockConfEntryPortConfDlm OBJECT-TYPE
   SYNTAX      Integer32
   MAX-ACCESS  read-write
   STATUS      current
   DESCRIPTION
       "Configurable member delayMechanism: The delay mechanism used for the port:
		e2e	End to end delay measurement
		p2p	Peer to peer delay measurement.
		Can be defined per port in an Ordinary/Boundary clock.
		In a transparent clock all ports use the same delay mechanism, determined by the clock type.
		1:e2e
		2:p2p"
   ::= { sm48tat4xarpPTPClockPortDataSetConfEntry 9 }

sm48tat4xarpPTPClockConfEntryPortConfMPR OBJECT-TYPE
   SYNTAX      Integer32
   MAX-ACCESS  read-write
   STATUS      current
   DESCRIPTION
       "The interval for issuing Delay_Req messages for the port in E2e mode. This value is announced from the master to the slave in an announce message. The value is reflected in the MDR field in the Slave
The interval for issuing Pdelay_Req messages for the port in P2P mode
Note: The interpretation of this parameter has changed from release 2.40. In earlier versions the value was interpreted relative to the Sync interval, this was a violation of the standard, so now the value is interpreted as an interval. I.e. MPR = 0 => 1 Delay_Req pr sec, independent of the Sync rate.
Range is -7 to 5."
   ::= { sm48tat4xarpPTPClockPortDataSetConfEntry 10 }

sm48tat4xarpPTPClockConfEntryPortConfDelayAsymmetry OBJECT-TYPE
   SYNTAX      Integer32
   MAX-ACCESS  read-write
   STATUS      current
   DESCRIPTION
       "If the transmission delay for a link in not symmetric, the asymmetry can be configured here, see IEEE 1588 Section 7.4.2 Communication path asymmetry
Range is -100000 to 100000."
   ::= { sm48tat4xarpPTPClockPortDataSetConfEntry 11 }

sm48tat4xarpPTPClockConfEntryPortConfIngressLatency OBJECT-TYPE
   SYNTAX      Integer32
   MAX-ACCESS  read-write
   STATUS      current
   DESCRIPTION
       "Ingress latency measured in ns, as defined in IEEE 1588 Section 7.3.4.2.
Range is -100000 to 100000."
   ::= { sm48tat4xarpPTPClockPortDataSetConfEntry 12 }

sm48tat4xarpPTPClockConfEntryPortConfEgressLatency OBJECT-TYPE
   SYNTAX      Integer32
   MAX-ACCESS  read-write
   STATUS      current
   DESCRIPTION
       "Egress latency measured in ns, as defined in IEEE 1588 Section 7.3.4.2.
Range is -100000 to 100000."
   ::= { sm48tat4xarpPTPClockPortDataSetConfEntry 13 }

sm48tat4xarpPTPClockConfEntryPortConfVersion OBJECT-TYPE
   SYNTAX      Integer32
   MAX-ACCESS  read-only
   STATUS      current
   DESCRIPTION
       "The current implementation only supports PTP version 2"
   ::= { sm48tat4xarpPTPClockPortDataSetConfEntry 14 }


sm48tat4xarpPTPClockUnicastSlaveConfTable OBJECT-TYPE
   SYNTAX      SEQUENCE OF SM48TAT4XARPPTPClockUnicastSlaveConfEntry
   MAX-ACCESS  not-accessible
   STATUS      current
   DESCRIPTION
       " "
   ::= { sm48tat4xarpPTP 9 }

sm48tat4xarpPTPClockUnicastSlaveConfEntry OBJECT-TYPE
   SYNTAX      SM48TAT4XARPPTPClockUnicastSlaveConfEntry
   MAX-ACCESS  not-accessible
   STATUS      current
   DESCRIPTION
       " "
   INDEX    { sm48tat4xarpPTPClockConfEntryUnicastSlaveConfIndex  }
   ::= { sm48tat4xarpPTPClockUnicastSlaveConfTable 1 }

SM48TAT4XARPPTPClockUnicastSlaveConfEntry ::= SEQUENCE {
   sm48tat4xarpPTPClockConfEntryUnicastSlaveConfIndex              Integer32,
   sm48tat4xarpPTPClockConfEntryUnicastSlaveConfDuration           Integer32,
   sm48tat4xarpPTPClockConfEntryUnicastSlaveConfIPAddress          IpAddress,
   sm48tat4xarpPTPClockConfEntryUnicastSlaveConfGrant              Integer32,
   sm48tat4xarpPTPClockConfEntryUnicastSlaveConfCommState          DisplayString
}

sm48tat4xarpPTPClockConfEntryUnicastSlaveConfIndex OBJECT-TYPE
   SYNTAX      Integer32(1..65535)
   MAX-ACCESS  not-accessible
   STATUS      current
   DESCRIPTION
       "Index"
   ::= { sm48tat4xarpPTPClockUnicastSlaveConfEntry 1 }

sm48tat4xarpPTPClockConfEntryUnicastSlaveConfDuration OBJECT-TYPE
   SYNTAX      Integer32
   MAX-ACCESS  read-write
   STATUS      current
   DESCRIPTION
       "The number of seconds a master is requested to send Announce/Sync messages.
	   The request is repeated from the slave each Duration/4 seconds.
	   range:10-1000"
   ::= { sm48tat4xarpPTPClockUnicastSlaveConfEntry 2 }

sm48tat4xarpPTPClockConfEntryUnicastSlaveConfIPAddress OBJECT-TYPE
   SYNTAX      IpAddress
   MAX-ACCESS  read-write
   STATUS      current
   DESCRIPTION
       "IPv4 Address of the Master clock"
   ::= { sm48tat4xarpPTPClockUnicastSlaveConfEntry 3 }

sm48tat4xarpPTPClockConfEntryUnicastSlaveConfGrant OBJECT-TYPE
   SYNTAX      Integer32
   MAX-ACCESS  read-only
   STATUS      current
   DESCRIPTION
       "The granted repetition period for the sync message"
   ::= { sm48tat4xarpPTPClockUnicastSlaveConfEntry 4 }

sm48tat4xarpPTPClockConfEntryUnicastSlaveConfCommState OBJECT-TYPE
   SYNTAX      DisplayString
   MAX-ACCESS  read-only
   STATUS      current
   DESCRIPTION
       "The state of the communication with the master, possible values are:
		IDLE : The entry is not in use.
		INIT : Announce is sent to the master (Waiting for a response).
		CONN : The master has responded.
		SELL : The assigned master is selected as current master.
		SYNC : The master is sending Sync messages."
   ::= { sm48tat4xarpPTPClockUnicastSlaveConfEntry 5 }
-- =======================================================================================================================
sm48tat4xarpETHLINKOAM    OBJECT IDENTIFIER ::= { sm48tat4xarpConfiguration 29 }

sm48tat4xarpEthLinkOAMPortConfTable OBJECT-TYPE
   SYNTAX      SEQUENCE OF SM48TAT4XARPEthLinkOAMPortConfEntry
   MAX-ACCESS  not-accessible
   STATUS      current
   DESCRIPTION
       " "
   ::= { sm48tat4xarpETHLINKOAM 1 }

sm48tat4xarpEthLinkOAMPortConfEntry OBJECT-TYPE
   SYNTAX      SM48TAT4XARPEthLinkOAMPortConfEntry
   MAX-ACCESS  not-accessible
   STATUS      current
   DESCRIPTION
       " "
   INDEX    { sm48tat4xarpEthLinkOAMPortConfIndex  }
   ::= { sm48tat4xarpEthLinkOAMPortConfTable 1 }

SM48TAT4XARPEthLinkOAMPortConfEntry ::= SEQUENCE {
   sm48tat4xarpEthLinkOAMPortConfIndex               Integer32,
   sm48tat4xarpEthLinkOAMPortConfOAMEnable           Integer32,
   sm48tat4xarpEthLinkOAMPortConfOAMMode             Integer32,
   sm48tat4xarpEthLinkOAMPortConfLoopbackSupport     Integer32,
   sm48tat4xarpEthLinkOAMPortConfLinkMonitorSupport  Integer32,
   sm48tat4xarpEthLinkOAMPortConfMIBRetrievalSupport Integer32,
   sm48tat4xarpEthLinkOAMPortConfLoopbackOperation   Integer32
}

sm48tat4xarpEthLinkOAMPortConfIndex OBJECT-TYPE
   SYNTAX      Integer32(1..65535)
   MAX-ACCESS  not-accessible
   STATUS      current
   DESCRIPTION
       "Index"
   ::= { sm48tat4xarpEthLinkOAMPortConfEntry 1 }

sm48tat4xarpEthLinkOAMPortConfOAMEnable OBJECT-TYPE
   SYNTAX      Integer32
   MAX-ACCESS  read-write
   STATUS      current
   DESCRIPTION
       "Controls whether Link OAM is enabled on this switch port.
	   Enabling Link OAM provides the network operators the ability to monitor the health of the network and
	   quickly determine the location of failing links or fault conditions.
	   0:disable
	   1:enable"
   ::= { sm48tat4xarpEthLinkOAMPortConfEntry 2 }

sm48tat4xarpEthLinkOAMPortConfOAMMode OBJECT-TYPE
   SYNTAX      Integer32
   MAX-ACCESS  read-write
   STATUS      current
   DESCRIPTION
       "Configures the OAM Mode as Active or Passive. The default mode is Passive.
	   0:Passive mode
	   1:Active mode"
   ::= { sm48tat4xarpEthLinkOAMPortConfEntry 3 }

sm48tat4xarpEthLinkOAMPortConfLoopbackSupport OBJECT-TYPE
   SYNTAX      Integer32
   MAX-ACCESS  read-write
   STATUS      current
   DESCRIPTION
       "Controls whether the loopback support is enabled for the switch port.
	   0:disable
	   1:enable"
   ::= { sm48tat4xarpEthLinkOAMPortConfEntry 4 }

sm48tat4xarpEthLinkOAMPortConfLinkMonitorSupport OBJECT-TYPE
   SYNTAX      Integer32
   MAX-ACCESS  read-write
   STATUS      current
   DESCRIPTION
       "Controls whether the Link Monitor support is enabled for the switch port.
	   0:disable
	   1:enable"
   ::= { sm48tat4xarpEthLinkOAMPortConfEntry 5 }

sm48tat4xarpEthLinkOAMPortConfMIBRetrievalSupport OBJECT-TYPE
   SYNTAX      Integer32
   MAX-ACCESS  read-write
   STATUS      current
   DESCRIPTION
       "Controls whether the MIB Retrieval Support is enabled for the switch port.
	   0:disable
	   1:enable"
   ::= { sm48tat4xarpEthLinkOAMPortConfEntry 6 }

sm48tat4xarpEthLinkOAMPortConfLoopbackOperation OBJECT-TYPE
   SYNTAX      Integer32
   MAX-ACCESS  read-write
   STATUS      current
   DESCRIPTION
       "If the Loopback support is enabled, enabling this field will start a loopback operation for the port.
	   0:disable
	   1:enable"
   ::= { sm48tat4xarpEthLinkOAMPortConfEntry 7 }



sm48tat4xarpEthLinkOAMPortDetailStatusTable OBJECT-TYPE
   SYNTAX      SEQUENCE OF SM48TAT4XARPEthLinkOAMPortDetailStatusEntry
   MAX-ACCESS  not-accessible
   STATUS      current
   DESCRIPTION
       "Eth Link OAM Port Detail Status table"
   ::= { sm48tat4xarpETHLINKOAM 2 }

sm48tat4xarpEthLinkOAMPortDetailStatusEntry OBJECT-TYPE
   SYNTAX      SM48TAT4XARPEthLinkOAMPortDetailStatusEntry
   MAX-ACCESS  not-accessible
   STATUS      current
   DESCRIPTION
       "Eth Link OAM Port Detail Status entry"
   INDEX    { sm48tat4xarpEthLinkOAMPortDetailStatusIndex  }
   ::= { sm48tat4xarpEthLinkOAMPortDetailStatusTable 1 }

SM48TAT4XARPEthLinkOAMPortDetailStatusEntry ::= SEQUENCE {
   sm48tat4xarpEthLinkOAMPortDetailStatusIndex                       Integer32,
   sm48tat4xarpEthLinkOAMPortPDUPermission                           DisplayString,
   sm48tat4xarpEthLinkOAMPortDiscoveryState                          DisplayString,
   sm48tat4xarpEthLinkOAMPortPeerMACAddress                          DisplayString,
   sm48tat4xarpEthLinkOAMPortLocalMode                               DisplayString,
   sm48tat4xarpEthLinkOAMPortLocalUnidirectionalOperationSupport     DisplayString,
   sm48tat4xarpEthLinkOAMPortLocalRemoteLoopbackSupport              DisplayString,
   sm48tat4xarpEthLinkOAMPortLocalLinkMonitoringSupport              DisplayString,
   sm48tat4xarpEthLinkOAMPortLocalMIBRetrievalSupport                DisplayString,
   sm48tat4xarpEthLinkOAMPortLocalMTUSize                            Integer32,
   sm48tat4xarpEthLinkOAMPortLocalMultiplexerState                   DisplayString,
   sm48tat4xarpEthLinkOAMPortLocalParserState                        DisplayString,
   sm48tat4xarpEthLinkOAMPortLocalOrganizationalUniqueIdent          DisplayString,
   sm48tat4xarpEthLinkOAMPortLocalPDURevision                        Integer32,
   sm48tat4xarpEthLinkOAMPortPeerMode                                DisplayString,
   sm48tat4xarpEthLinkOAMPortPeerUnidirectionalOperationSupport      DisplayString,
   sm48tat4xarpEthLinkOAMPortPeerRemoteLoopbackSupport               DisplayString,
   sm48tat4xarpEthLinkOAMPortPeerLinkMonitoringSupport               DisplayString,
   sm48tat4xarpEthLinkOAMPortPeerMIBRetrievalSupport                 DisplayString,
   sm48tat4xarpEthLinkOAMPortPeerMTUSize                             DisplayString,
   sm48tat4xarpEthLinkOAMPortPeerMultiplexerState                    DisplayString,
   sm48tat4xarpEthLinkOAMPortPeerParserState                         DisplayString,
   sm48tat4xarpEthLinkOAMPortPeerOrganizationalUniqueIdent           DisplayString,
   sm48tat4xarpEthLinkOAMPortPDURevision                             DisplayString
}

sm48tat4xarpEthLinkOAMPortDetailStatusIndex OBJECT-TYPE
   SYNTAX      Integer32(1..65535)
   MAX-ACCESS  not-accessible
   STATUS      current
   DESCRIPTION
       "Index"
   ::= { sm48tat4xarpEthLinkOAMPortDetailStatusEntry 1 }

sm48tat4xarpEthLinkOAMPortPDUPermission OBJECT-TYPE
   SYNTAX      DisplayString
   MAX-ACCESS  read-only
   STATUS      current
   DESCRIPTION
       "This field is available only for the Local DTE.
	   It displays the current permission rules set for the local DTE.
	   Possible values are Link fault, Receive only, Information exchange only, ANY."
   ::= { sm48tat4xarpEthLinkOAMPortDetailStatusEntry 2 }

sm48tat4xarpEthLinkOAMPortDiscoveryState OBJECT-TYPE
   SYNTAX      DisplayString
   MAX-ACCESS  read-only
   STATUS      current
   DESCRIPTION
       "Displays the current state of the discovery process.
	   Possible states are Fault state, Active state, Passive state,
	   SEND_LOCAL_REMOTE_STATE, SEND_LOCAL_REMOTE_OK_STATE, SEND_ANY_STATE."
   ::= { sm48tat4xarpEthLinkOAMPortDetailStatusEntry 3 }

sm48tat4xarpEthLinkOAMPortPeerMACAddress OBJECT-TYPE
   SYNTAX      DisplayString
   MAX-ACCESS  read-only
   STATUS      current
   DESCRIPTION
       " "
   ::= { sm48tat4xarpEthLinkOAMPortDetailStatusEntry 4 }

sm48tat4xarpEthLinkOAMPortLocalMode OBJECT-TYPE
   SYNTAX      DisplayString
   MAX-ACCESS  read-only
   STATUS      current
   DESCRIPTION
       "The Mode in which the Link OAM is operating, Active or Passive."
   ::= { sm48tat4xarpEthLinkOAMPortDetailStatusEntry 5 }

sm48tat4xarpEthLinkOAMPortLocalUnidirectionalOperationSupport OBJECT-TYPE
   SYNTAX      DisplayString
   MAX-ACCESS  read-only
   STATUS      current
   DESCRIPTION
       "This feature is not available to be configured by the user. The status of this configuration is retrieved from the PHY."
   ::= { sm48tat4xarpEthLinkOAMPortDetailStatusEntry 6 }

sm48tat4xarpEthLinkOAMPortLocalRemoteLoopbackSupport OBJECT-TYPE
   SYNTAX      DisplayString
   MAX-ACCESS  read-only
   STATUS      current
   DESCRIPTION
       "If status is enabled, DTE is capable of OAM remote loopback mode."
   ::= { sm48tat4xarpEthLinkOAMPortDetailStatusEntry 7 }

sm48tat4xarpEthLinkOAMPortLocalLinkMonitoringSupport OBJECT-TYPE
   SYNTAX      DisplayString
   MAX-ACCESS  read-only
   STATUS      current
   DESCRIPTION
       "If status is enabled, DTE supports interpreting Link Events."
   ::= { sm48tat4xarpEthLinkOAMPortDetailStatusEntry 8 }

sm48tat4xarpEthLinkOAMPortLocalMIBRetrievalSupport OBJECT-TYPE
   SYNTAX      DisplayString
   MAX-ACCESS  read-only
   STATUS      current
   DESCRIPTION
       "If status ie enabled DTE supports sending Variable Response OAMPDUs."
   ::= { sm48tat4xarpEthLinkOAMPortDetailStatusEntry 9 }

sm48tat4xarpEthLinkOAMPortLocalMTUSize OBJECT-TYPE
   SYNTAX      Integer32
   MAX-ACCESS  read-only
   STATUS      current
   DESCRIPTION
       "It represents the largest OAMPDU, in octets, supported by the DTE.
	   This value is compared to the remotes Maximum PDU Size and the smaller of the two is used."
   ::= { sm48tat4xarpEthLinkOAMPortDetailStatusEntry 10 }

sm48tat4xarpEthLinkOAMPortLocalMultiplexerState OBJECT-TYPE
   SYNTAX      DisplayString
   MAX-ACCESS  read-only
   STATUS      current
   DESCRIPTION
       "When in forwarding state, the Device is forwarding non-OAMPDUs to the lower sublayer.
	   Incase of discarding, the device discards all the non-OAMPDU's."
   ::= { sm48tat4xarpEthLinkOAMPortDetailStatusEntry 11 }

sm48tat4xarpEthLinkOAMPortLocalParserState OBJECT-TYPE
   SYNTAX      DisplayString
   MAX-ACCESS  read-only
   STATUS      current
   DESCRIPTION
       "When in forwarding state, Device is forwarding non-OAMPDUs to higher sublayer.
	   When in loopback, Device is looping back non-OAMPDUs to the lower sublayer.
	   When in discarding state, Device is discarding non-OAMPDUs."
   ::= { sm48tat4xarpEthLinkOAMPortDetailStatusEntry 12 }

sm48tat4xarpEthLinkOAMPortLocalOrganizationalUniqueIdent OBJECT-TYPE
   SYNTAX      DisplayString
   MAX-ACCESS  read-only
   STATUS      current
   DESCRIPTION
       "24-bit Organizationally Unique Identifier of the vendor."
   ::= { sm48tat4xarpEthLinkOAMPortDetailStatusEntry 13 }

sm48tat4xarpEthLinkOAMPortLocalPDURevision OBJECT-TYPE
   SYNTAX      Integer32
   MAX-ACCESS  read-only
   STATUS      current
   DESCRIPTION
       "It indicates the current revision of the Information TLV.
	   The value of this field shall start at zero and be incremented each time something in the Information TLV changes.
	   Upon reception of an Information TLV from a peer, an OAM client may use this field to decide if it needs to be processed
	   (an Information TLV that is identical to the previous Information TLV doesn't need to be parsed as nothing in it has changed)."
   ::= { sm48tat4xarpEthLinkOAMPortDetailStatusEntry 14 }

sm48tat4xarpEthLinkOAMPortPeerMode OBJECT-TYPE
   SYNTAX      DisplayString
   MAX-ACCESS  read-only
   STATUS      current
   DESCRIPTION
       "The Mode in which the Link OAM is operating, Active or Passive."
   ::= { sm48tat4xarpEthLinkOAMPortDetailStatusEntry 15 }

sm48tat4xarpEthLinkOAMPortPeerUnidirectionalOperationSupport OBJECT-TYPE
   SYNTAX      DisplayString
   MAX-ACCESS  read-only
   STATUS      current
   DESCRIPTION
       "This feature is not available to be configured by the user.
	   The status of this configuration is retrieved from the PHY."
   ::= { sm48tat4xarpEthLinkOAMPortDetailStatusEntry 16 }

sm48tat4xarpEthLinkOAMPortPeerRemoteLoopbackSupport OBJECT-TYPE
   SYNTAX      DisplayString
   MAX-ACCESS  read-only
   STATUS      current
   DESCRIPTION
       "If status is enabled, DTE is capable of OAM remote loopback mode."
   ::= { sm48tat4xarpEthLinkOAMPortDetailStatusEntry 17 }

sm48tat4xarpEthLinkOAMPortPeerLinkMonitoringSupport OBJECT-TYPE
   SYNTAX      DisplayString
   MAX-ACCESS  read-only
   STATUS      current
   DESCRIPTION
       "If status is enabled, DTE supports interpreting Link Events."
   ::= { sm48tat4xarpEthLinkOAMPortDetailStatusEntry 18 }

sm48tat4xarpEthLinkOAMPortPeerMIBRetrievalSupport OBJECT-TYPE
   SYNTAX      DisplayString
   MAX-ACCESS  read-only
   STATUS      current
   DESCRIPTION
       "If status ie enabled DTE supports sending Variable Response OAMPDUs."
   ::= { sm48tat4xarpEthLinkOAMPortDetailStatusEntry 19 }

sm48tat4xarpEthLinkOAMPortPeerMTUSize OBJECT-TYPE
   SYNTAX      DisplayString
   MAX-ACCESS  read-only
   STATUS      current
   DESCRIPTION
       "It represents the largest OAMPDU, in octets, supported by the DTE.
	   This value is compared to the remotes Maximum PDU Size and the smaller of the two is used."
   ::= { sm48tat4xarpEthLinkOAMPortDetailStatusEntry 20 }

sm48tat4xarpEthLinkOAMPortPeerMultiplexerState OBJECT-TYPE
   SYNTAX      DisplayString
   MAX-ACCESS  read-only
   STATUS      current
   DESCRIPTION
       "When in forwarding state, the Device is forwarding non-OAMPDUs to the lower sublayer.
	   Incase of discarding, the device discards all the non-OAMPDU's."
   ::= { sm48tat4xarpEthLinkOAMPortDetailStatusEntry 21 }

sm48tat4xarpEthLinkOAMPortPeerParserState OBJECT-TYPE
   SYNTAX      DisplayString
   MAX-ACCESS  read-only
   STATUS      current
   DESCRIPTION
       "When in forwarding state, Device is forwarding non-OAMPDUs to higher sublayer.
	   When in loopback, Device is looping back non-OAMPDUs to the lower sublayer.
	   When in discarding state, Device is discarding non-OAMPDUs."
   ::= { sm48tat4xarpEthLinkOAMPortDetailStatusEntry 22 }

sm48tat4xarpEthLinkOAMPortPeerOrganizationalUniqueIdent OBJECT-TYPE
   SYNTAX      DisplayString
   MAX-ACCESS  read-only
   STATUS      current
   DESCRIPTION
       "24-bit Organizationally Unique Identifier of the vendor."
   ::= { sm48tat4xarpEthLinkOAMPortDetailStatusEntry 23 }

sm48tat4xarpEthLinkOAMPortPDURevision                              OBJECT-TYPE
   SYNTAX      DisplayString
   MAX-ACCESS  read-only
   STATUS      current
   DESCRIPTION
       "It indicates the current revision of the Information TLV.
	   The value of this field shall start at zero and be incremented each time something in the Information TLV changes.
	   Upon reception of an Information TLV from a peer, an OAM client may use this field to decide if it needs to be processed
	   (an Information TLV that is identical to the previous Information TLV doesn't need to be parsed as nothing in it has changed)."
   ::= { sm48tat4xarpEthLinkOAMPortDetailStatusEntry 24 }


sm48tat4xarpEthLinkOAMPortLinkEventConfTable OBJECT-TYPE
   SYNTAX      SEQUENCE OF SM48TAT4XARPEthLinkOAMPortLinkEventConfEntry
   MAX-ACCESS  not-accessible
   STATUS      current
   DESCRIPTION
       "Eth Link OAM Port Link Event Conf Table"
   ::= { sm48tat4xarpETHLINKOAM 3 }

sm48tat4xarpEthLinkOAMPortLinkEventConfEntry OBJECT-TYPE
   SYNTAX      SM48TAT4XARPEthLinkOAMPortLinkEventConfEntry
   MAX-ACCESS  not-accessible
   STATUS      current
   DESCRIPTION
       "Eth Link OAM Port Link Event Conf Entry"
   INDEX    { sm48tat4xarpEventConfIndex  }
   ::= { sm48tat4xarpEthLinkOAMPortLinkEventConfTable 1 }

SM48TAT4XARPEthLinkOAMPortLinkEventConfEntry ::= SEQUENCE {
   sm48tat4xarpEventConfIndex                                 Integer32,
   sm48tat4xarpEventConfErrorFrameEventErrorWindow            Integer32,
   sm48tat4xarpEventConfErrorFrameEventErrorThreshold         Integer32,
   sm48tat4xarpEventConfSymbolPeriodErrorEventErrorWindow     Integer32,
   sm48tat4xarpEventConfSymbolPeriodErrorEventErrorThreshold  Integer32,
   sm48tat4xarpEventConfSecondsSummaryEventErrorWindow        Integer32,
   sm48tat4xarpEventConfSecondsSummaryEventErrorThreshold     Integer32
}

sm48tat4xarpEventConfIndex OBJECT-TYPE
   SYNTAX      Integer32(1..65535)
   MAX-ACCESS  not-accessible
   STATUS      current
   DESCRIPTION
       "Index"
   ::= { sm48tat4xarpEthLinkOAMPortLinkEventConfEntry 1 }

sm48tat4xarpEventConfErrorFrameEventErrorWindow OBJECT-TYPE
   SYNTAX      Integer32
   MAX-ACCESS  read-write
   STATUS      current
   DESCRIPTION
       "The Errored Frame Event counts the number of errored frames detected during the specified period.
	   Represents the window period in the order of 1 sec for the observation of various link events.
	   range: 1-60"
   ::= { sm48tat4xarpEthLinkOAMPortLinkEventConfEntry 2 }

sm48tat4xarpEventConfErrorFrameEventErrorThreshold OBJECT-TYPE
   SYNTAX      Integer32
   MAX-ACCESS  read-write
   STATUS      current
   DESCRIPTION
       "The Errored Frame Event counts the number of errored frames detected during the specified period.
	   Represents the threshold value for the window period for the appropriate Link event so as to notify the peer of this error.
	   range:0-0xffffffff"
   ::= { sm48tat4xarpEthLinkOAMPortLinkEventConfEntry 3 }

sm48tat4xarpEventConfSymbolPeriodErrorEventErrorWindow OBJECT-TYPE
   SYNTAX      Integer32
   MAX-ACCESS  read-write
   STATUS      current
   DESCRIPTION
       "The Errored Symbol Period Event counts the number of symbol errors that occurred during the specified period.
	   Represents the window period in the order of 1 sec for the observation of various link events.
	   range: 1-60"
   ::= { sm48tat4xarpEthLinkOAMPortLinkEventConfEntry 4 }

sm48tat4xarpEventConfSymbolPeriodErrorEventErrorThreshold OBJECT-TYPE
   SYNTAX      Integer32
   MAX-ACCESS  read-write
   STATUS      current
   DESCRIPTION
       "The Errored Symbol Period Event counts the number of symbol errors that occurred during the specified period.
	   Represents the threshold value for the window period for the appropriate Link event so as to notify the peer of this error.
	   range:0-0xffffffff"
   ::= { sm48tat4xarpEthLinkOAMPortLinkEventConfEntry 5 }

sm48tat4xarpEventConfSecondsSummaryEventErrorWindow OBJECT-TYPE
   SYNTAX      Integer32
   MAX-ACCESS  read-write
   STATUS      current
   DESCRIPTION
       "The Errored Frame Seconds Summary Event TLV counts the number of errored frame seconds that occurred during the specified period.
	   Represents the window period in the order of 1 sec for the observation of various link events.
	   range: 10-900"
   ::= { sm48tat4xarpEthLinkOAMPortLinkEventConfEntry 6 }

sm48tat4xarpEventConfSecondsSummaryEventErrorThreshold OBJECT-TYPE
   SYNTAX      Integer32
   MAX-ACCESS  read-write
   STATUS      current
   DESCRIPTION
       "The Errored Frame Seconds Summary Event TLV counts the number of errored frame seconds that occurred during the specified period.
	   Represents the threshold value for the window period for the appropriate Link event so as to notify the peer of this error.
	   range:0-0xffff"
   ::= { sm48tat4xarpEthLinkOAMPortLinkEventConfEntry 7 }




sm48tat4xarpEthLinkOAMPortDetailedStatisticsTable OBJECT-TYPE
   SYNTAX      SEQUENCE OF SM48TAT4XARPEthLinkOAMPortDetailedStatisticsEntry
   MAX-ACCESS  not-accessible
   STATUS      current
   DESCRIPTION
       "Eth Link OAM Port Detailed Statistics Table"
   ::= { sm48tat4xarpETHLINKOAM 4 }

sm48tat4xarpEthLinkOAMPortDetailedStatisticsEntry OBJECT-TYPE
   SYNTAX      SM48TAT4XARPEthLinkOAMPortDetailedStatisticsEntry
   MAX-ACCESS  not-accessible
   STATUS      current
   DESCRIPTION
       "Eth Link OAM Port Detailed Statistics Entry"
   INDEX    { sm48tat4xarpStatisticsIndex  }
   ::= { sm48tat4xarpEthLinkOAMPortDetailedStatisticsTable 1 }

SM48TAT4XARPEthLinkOAMPortDetailedStatisticsEntry ::= SEQUENCE {
   sm48tat4xarpStatisticsIndex                             Integer32,
   sm48tat4xarpStatisticsRxOAMInformationPDUs              Integer32,
   sm48tat4xarpStatisticsRxUniqueErrorEventNotification    Integer32,
   sm48tat4xarpStatisticsRxDuplicateErrorEventNotification Integer32,
   sm48tat4xarpStatisticsRxLoopbackControl                 Integer32,
   sm48tat4xarpStatisticsRxVariableRequest                 Integer32,
   sm48tat4xarpStatisticsRxVariableResponse                Integer32,
   sm48tat4xarpStatisticsRxOrgSpecificPDUs                 Integer32,
   sm48tat4xarpStatisticsRxUnsupportedCodes                Integer32,
   sm48tat4xarpStatisticsRxLinkFaultPDUs                   Integer32,
   sm48tat4xarpStatisticsRxDyingGasp                       Integer32,
   sm48tat4xarpStatisticsRxCriticalEventPDUs               Integer32,
   sm48tat4xarpStatisticsTxOAMInformationPDUs              Integer32,
   sm48tat4xarpStatisticsTxUniqueErrorEventNotification    Integer32,
   sm48tat4xarpStatisticsTxDuplicateErrorEventNotification Integer32,
   sm48tat4xarpStatisticsTxLoopbackControl                 Integer32,
   sm48tat4xarpStatisticsTxVariableRequest                 Integer32,
   sm48tat4xarpStatisticsTxVariableResponse                Integer32,
   sm48tat4xarpStatisticsTxOrgSpecificPDUs                 Integer32,
   sm48tat4xarpStatisticsTxUnsupportedCodes                Integer32,
   sm48tat4xarpStatisticsTxLinkFaultPDUs                   Integer32,
   sm48tat4xarpStatisticsTxDyingGasp                       Integer32,
   sm48tat4xarpStatisticsTxCriticalEventPDUs               Integer32,
   sm48tat4xarpStatisticsClear                             Integer32
}

sm48tat4xarpStatisticsIndex OBJECT-TYPE
   SYNTAX      Integer32(1..65535)
   MAX-ACCESS  not-accessible
   STATUS      current
   DESCRIPTION
       "Index"
   ::= { sm48tat4xarpEthLinkOAMPortDetailedStatisticsEntry 1 }

sm48tat4xarpStatisticsRxOAMInformationPDUs OBJECT-TYPE
   SYNTAX      Integer32
   MAX-ACCESS  read-only
   STATUS      current
   DESCRIPTION
       "The number of received and transmitted OAM Information PDU's.
	   Discontinuities of this counter can occur at re-initialization of the management system."
   ::= { sm48tat4xarpEthLinkOAMPortDetailedStatisticsEntry 2 }

sm48tat4xarpStatisticsRxUniqueErrorEventNotification OBJECT-TYPE
   SYNTAX      Integer32
   MAX-ACCESS  read-only
   STATUS      current
   DESCRIPTION
       "A count of the number of unique Event OAMPDUs received and transmitted on this interface.
	   Event Notifications may be sent in duplicate to increase the probability of successfully being received,
	   given the possibility that a frame may be lost in transit.
	   Duplicate Event Notification transmissions are counted by
	   Duplicate Event Notification counters for Tx and Rx respectively.
	   A unique Event Notification OAMPDU is indicated as an Event Notification OAMPDU with
	   a Sequence Number field that is distinct from the previously transmitted Event Notification OAMPDU Sequence Number."
   ::= { sm48tat4xarpEthLinkOAMPortDetailedStatisticsEntry 3 }

sm48tat4xarpStatisticsRxDuplicateErrorEventNotification OBJECT-TYPE
   SYNTAX      Integer32
   MAX-ACCESS  read-only
   STATUS      current
   DESCRIPTION
       "A count of the number of duplicate Event OAMPDUs received and transmitted on this interface.
	   Event Notification OAMPDUs may be sent in duplicate to increase the probability of successfully being received,
	   given the possibility that a frame may be lost in transit.
	   A duplicate Event Notification OAMPDU is indicated as an Event Notification OAMPDU with
	   a Sequence Number field that is identical to the previously transmitted Event Notification OAMPDU Sequence Number."
   ::= { sm48tat4xarpEthLinkOAMPortDetailedStatisticsEntry 4 }

sm48tat4xarpStatisticsRxLoopbackControl OBJECT-TYPE
   SYNTAX      Integer32
   MAX-ACCESS  read-only
   STATUS      current
   DESCRIPTION
       "A count of the number of Loopback Control OAMPDUs received and transmitted on this interface."
   ::= { sm48tat4xarpEthLinkOAMPortDetailedStatisticsEntry 5 }

sm48tat4xarpStatisticsRxVariableRequest OBJECT-TYPE
   SYNTAX      Integer32
   MAX-ACCESS  read-only
   STATUS      current
   DESCRIPTION
       "A count of the number of Variable Request OAMPDUs received and transmitted on this interface."
   ::= { sm48tat4xarpEthLinkOAMPortDetailedStatisticsEntry 6 }

sm48tat4xarpStatisticsRxVariableResponse OBJECT-TYPE
   SYNTAX      Integer32
   MAX-ACCESS  read-only
   STATUS      current
   DESCRIPTION
       "A count of the number of Variable Response OAMPDUs received and transmitted on this interface."
   ::= { sm48tat4xarpEthLinkOAMPortDetailedStatisticsEntry 7 }

sm48tat4xarpStatisticsRxOrgSpecificPDUs OBJECT-TYPE
   SYNTAX      Integer32
   MAX-ACCESS  read-only
   STATUS      current
   DESCRIPTION
       "A count of the number of Organization Specific OAMPDUs transmitted on this interface."
   ::= { sm48tat4xarpEthLinkOAMPortDetailedStatisticsEntry 8 }

sm48tat4xarpStatisticsRxUnsupportedCodes OBJECT-TYPE
   SYNTAX      Integer32
   MAX-ACCESS  read-only
   STATUS      current
   DESCRIPTION
       "A count of the number of OAMPDUs transmitted on this interface with an unsupported op-code."
   ::= { sm48tat4xarpEthLinkOAMPortDetailedStatisticsEntry 9 }

sm48tat4xarpStatisticsRxLinkFaultPDUs OBJECT-TYPE
   SYNTAX      Integer32
   MAX-ACCESS  read-only
   STATUS      current
   DESCRIPTION
       "A count of the number of Link fault PDU's received and transmitted on this interface."
   ::= { sm48tat4xarpEthLinkOAMPortDetailedStatisticsEntry 10 }

sm48tat4xarpStatisticsRxDyingGasp OBJECT-TYPE
   SYNTAX      Integer32
   MAX-ACCESS  read-only
   STATUS      current
   DESCRIPTION
       "A count of the number of Dying Gasp events received and transmitted on this interface."
   ::= { sm48tat4xarpEthLinkOAMPortDetailedStatisticsEntry 11 }

sm48tat4xarpStatisticsRxCriticalEventPDUs OBJECT-TYPE
   SYNTAX      Integer32
   MAX-ACCESS  read-only
   STATUS      current
   DESCRIPTION
       "A count of the number of Critical event PDU's received and transmitted on this interface."
   ::= { sm48tat4xarpEthLinkOAMPortDetailedStatisticsEntry 12 }

sm48tat4xarpStatisticsTxOAMInformationPDUs OBJECT-TYPE
   SYNTAX      Integer32
   MAX-ACCESS  read-only
   STATUS      current
   DESCRIPTION
       "The number of received and transmitted OAM Information PDU's.
	   Discontinuities of this counter can occur at re-initialization of the management system."
   ::= { sm48tat4xarpEthLinkOAMPortDetailedStatisticsEntry 13 }

sm48tat4xarpStatisticsTxUniqueErrorEventNotification OBJECT-TYPE
   SYNTAX      Integer32
   MAX-ACCESS  read-only
   STATUS      current
   DESCRIPTION
       "A count of the number of unique Event OAMPDUs received and transmitted on this interface.
	   Event Notifications may be sent in duplicate to increase the probability of successfully being received,
	   given the possibility that a frame may be lost in transit.
	   Duplicate Event Notification transmissions are counted by
	   Duplicate Event Notification counters for Tx and Rx respectively.
	   A unique Event Notification OAMPDU is indicated as an Event Notification OAMPDU with
	   a Sequence Number field that is distinct from the previously transmitted Event Notification OAMPDU Sequence Number."
   ::= { sm48tat4xarpEthLinkOAMPortDetailedStatisticsEntry 14 }

sm48tat4xarpStatisticsTxDuplicateErrorEventNotification OBJECT-TYPE
   SYNTAX      Integer32
   MAX-ACCESS  read-only
   STATUS      current
   DESCRIPTION
       "A count of the number of duplicate Event OAMPDUs received and transmitted on this interface.
	   Event Notification OAMPDUs may be sent in duplicate to increase the probability of successfully being received,
	   given the possibility that a frame may be lost in transit.
	   A duplicate Event Notification OAMPDU is indicated as an Event Notification OAMPDU with
	   a Sequence Number field that is identical to the previously transmitted Event Notification OAMPDU Sequence Number."
   ::= { sm48tat4xarpEthLinkOAMPortDetailedStatisticsEntry 15 }

sm48tat4xarpStatisticsTxLoopbackControl OBJECT-TYPE
   SYNTAX      Integer32
   MAX-ACCESS  read-only
   STATUS      current
   DESCRIPTION
       "A count of the number of Loopback Control OAMPDUs received and transmitted on this interface."
   ::= { sm48tat4xarpEthLinkOAMPortDetailedStatisticsEntry 16 }

sm48tat4xarpStatisticsTxVariableRequest OBJECT-TYPE
   SYNTAX      Integer32
   MAX-ACCESS  read-only
   STATUS      current
   DESCRIPTION
       "A count of the number of Variable Request OAMPDUs received and transmitted on this interface."
   ::= { sm48tat4xarpEthLinkOAMPortDetailedStatisticsEntry 17 }

sm48tat4xarpStatisticsTxVariableResponse OBJECT-TYPE
   SYNTAX      Integer32
   MAX-ACCESS  read-only
   STATUS      current
   DESCRIPTION
       "A count of the number of Variable Response OAMPDUs received and transmitted on this interface."
   ::= { sm48tat4xarpEthLinkOAMPortDetailedStatisticsEntry 18 }

sm48tat4xarpStatisticsTxOrgSpecificPDUs OBJECT-TYPE
   SYNTAX      Integer32
   MAX-ACCESS  read-only
   STATUS      current
   DESCRIPTION
       "A count of the number of Organization Specific OAMPDUs transmitted on this interface."
   ::= { sm48tat4xarpEthLinkOAMPortDetailedStatisticsEntry 19 }

sm48tat4xarpStatisticsTxUnsupportedCodes OBJECT-TYPE
   SYNTAX      Integer32
   MAX-ACCESS  read-only
   STATUS      current
   DESCRIPTION
       "A count of the number of OAMPDUs transmitted on this interface with an unsupported op-code."
   ::= { sm48tat4xarpEthLinkOAMPortDetailedStatisticsEntry 20 }

sm48tat4xarpStatisticsTxLinkFaultPDUs OBJECT-TYPE
   SYNTAX      Integer32
   MAX-ACCESS  read-only
   STATUS      current
   DESCRIPTION
       "A count of the number of Link fault PDU's received and transmitted on this interface."
   ::= { sm48tat4xarpEthLinkOAMPortDetailedStatisticsEntry 21 }

sm48tat4xarpStatisticsTxDyingGasp OBJECT-TYPE
   SYNTAX      Integer32
   MAX-ACCESS  read-only
   STATUS      current
   DESCRIPTION
       "A count of the number of Dying Gasp events received and transmitted on this interface."
   ::= { sm48tat4xarpEthLinkOAMPortDetailedStatisticsEntry 22 }

sm48tat4xarpStatisticsTxCriticalEventPDUs OBJECT-TYPE
   SYNTAX      Integer32
   MAX-ACCESS  read-only
   STATUS      current
   DESCRIPTION
       "A count of the number of Critical event PDU's received and transmitted on this interface."
   ::= { sm48tat4xarpEthLinkOAMPortDetailedStatisticsEntry 23 }

sm48tat4xarpStatisticsClear OBJECT-TYPE
   SYNTAX      Integer32
   MAX-ACCESS  read-write
   STATUS      current
   DESCRIPTION
       "Clears the counters for the selected port."
   ::= { sm48tat4xarpEthLinkOAMPortDetailedStatisticsEntry 24 }


sm48tat4xarpEthLinkOAMPortEventDetailedStatisticsTable OBJECT-TYPE
   SYNTAX      SEQUENCE OF SM48TAT4XARPEthLinkOAMPortEventDetailedStatisticsEntry
   MAX-ACCESS  not-accessible
   STATUS      current
   DESCRIPTION
       "Eth Link OAM Port Event Detailed Statistics Table"
   ::= { sm48tat4xarpETHLINKOAM 5 }

sm48tat4xarpEthLinkOAMPortEventDetailedStatisticsEntry OBJECT-TYPE
   SYNTAX      SM48TAT4XARPEthLinkOAMPortEventDetailedStatisticsEntry
   MAX-ACCESS  not-accessible
   STATUS      current
   DESCRIPTION
       "Eth Link OAM Port Event Detailed Statistics Entry"
   INDEX    { sm48tat4xarpDetailedStatisticsIndex  }
   ::= { sm48tat4xarpEthLinkOAMPortEventDetailedStatisticsTable 1 }

SM48TAT4XARPEthLinkOAMPortEventDetailedStatisticsEntry ::= SEQUENCE {
   sm48tat4xarpDetailedStatisticsIndex                          Integer32,
   sm48tat4xarpStatisticsLocalSequenceNumber                    Integer32,
   sm48tat4xarpStatisticsLocalFrameErrorEventTimestamp          Integer32,
   sm48tat4xarpStatisticsLocalFrameErrorEventWindow             Integer32,
   sm48tat4xarpStatisticsLocalFrameErrorEventThreshold          Integer32,
   sm48tat4xarpStatisticsLocalFrameErrors                       Integer32,
   sm48tat4xarpStatisticsLocalTotalFrameErrors                  Counter64,
   sm48tat4xarpStatisticsLocalTotalFrameErrorEvents             Integer32,
   sm48tat4xarpStatisticsLocalFramePeriodErrorEventTimestamp    Integer32,
   sm48tat4xarpStatisticsLocalFramePeriodErrorEventWindow       Integer32,
   sm48tat4xarpStatisticsLocalFramePeriodErrorEventThreshold    Integer32,
   sm48tat4xarpStatisticsLocalFramePeriodErrors                 Integer32,
   sm48tat4xarpStatisticsLocalTotalFramePeriodErrors            Counter64,
   sm48tat4xarpStatisticsLocalTotalFramePeriodErrorEvents       Integer32,
   sm48tat4xarpStatisticsLocalSymbolPeriodErrorEventTimestamp   Integer32,
   sm48tat4xarpStatisticsLocalSymbolPeriodErrorEventWindow      Counter64,
   sm48tat4xarpStatisticsLocalSymbolPeriodErrorEventThreshold   Counter64,
   sm48tat4xarpStatisticsLocalSymbolPeriodErrors                Counter64,
   sm48tat4xarpStatisticsLocalSymbolFramePeriodErrors           Counter64,
   sm48tat4xarpStatisticsLocalSymbolFramePeriodErrorEvents      Integer32,
   sm48tat4xarpStatisticsLocalEventSecondsSummaryTimeStamp      Integer32,
   sm48tat4xarpStatisticsLocalEventSecondsSummaryWindow         Integer32,
   sm48tat4xarpStatisticsLocalEventSecondsSummaryThreshold      Integer32,
   sm48tat4xarpStatisticsLocalEventSecondsSummaryEvents         Integer32,
   sm48tat4xarpStatisticsLocalEventSecondsSummaryErrorTotal     Integer32,
   sm48tat4xarpStatisticsLocalEventSecondsSummaryEventTotal     Integer32,
   sm48tat4xarpStatisticsRemoteFrameErrorEventTimestamp         Integer32,
   sm48tat4xarpStatisticsRemoteFrameErrorEventWindow            Integer32,
   sm48tat4xarpStatisticsRemoteFrameErrorEventThreshold         Integer32,
   sm48tat4xarpStatisticsRemoteFrameErrors                      Integer32,
   sm48tat4xarpStatisticsRemoteTotalFrameErrors                 Counter64,
   sm48tat4xarpStatisticsRemoteTotalFrameErrorEvents            Integer32,
   sm48tat4xarpStatisticsRemoteFramePeriodErrorEventTimestamp   Integer32,
   sm48tat4xarpStatisticsRemoteFramePeriodErrorEventWindow      Integer32,
   sm48tat4xarpStatisticsRemoteFramePeriodErrorEventThreshold   Integer32,
   sm48tat4xarpStatisticsRemoteFramePeriodErrors                Integer32,
   sm48tat4xarpStatisticsRemoteTotalFramePeriodErrors           Counter64,
   sm48tat4xarpStatisticsRemoteTotalFramePeriodErrorEvents      Integer32,
   sm48tat4xarpStatisticsRemoteSymbolPeriodErrorEventTimestamp  Integer32,
   sm48tat4xarpStatisticsRemoteSymbolPeriodErrorEventWindow     Counter64,
   sm48tat4xarpStatisticsRemoteSymbolPeriodErrorEventThreshold  Counter64,
   sm48tat4xarpStatisticsRemoteSymbolPeriodErrors               Counter64,
   sm48tat4xarpStatisticsRemoteSymbolFramePeriodErrors          Counter64,
   sm48tat4xarpStatisticsRemoteSymbolFramePeriodErrorEvents     Integer32,
   sm48tat4xarpStatisticsRemoteEventSecondsSummaryTimeStamp     Integer32,
   sm48tat4xarpStatisticsRemoteEventSecondsSummaryWindow        Integer32,
   sm48tat4xarpStatisticsRemoteEventSecondsSummaryThreshold     Integer32,
   sm48tat4xarpStatisticsRemoteEventSecondsSummaryEvents        Integer32,
   sm48tat4xarpStatisticsRemoteEventSecondsSummaryErrorTotal    Integer32,
   sm48tat4xarpStatisticsRemoteEventSecondsSummaryEventTotal    Integer32
}

sm48tat4xarpDetailedStatisticsIndex OBJECT-TYPE
   SYNTAX      Integer32(1..65535)
   MAX-ACCESS  not-accessible
   STATUS      current
   DESCRIPTION
       "Index"
   ::= { sm48tat4xarpEthLinkOAMPortEventDetailedStatisticsEntry 1 }

sm48tat4xarpStatisticsLocalSequenceNumber OBJECT-TYPE
   SYNTAX      Integer32
   MAX-ACCESS  read-only
   STATUS      current
   DESCRIPTION
       "This two-octet field indicates the total number of events occurred at the remote end."
   ::= { sm48tat4xarpEthLinkOAMPortEventDetailedStatisticsEntry 2 }

sm48tat4xarpStatisticsLocalFrameErrorEventTimestamp OBJECT-TYPE
   SYNTAX      Integer32
   MAX-ACCESS  read-only
   STATUS      current
   DESCRIPTION
       "This two-octet field indicates the time reference when the event was generated, in terms of 100 ms intervals."
   ::= { sm48tat4xarpEthLinkOAMPortEventDetailedStatisticsEntry 3 }

sm48tat4xarpStatisticsLocalFrameErrorEventWindow OBJECT-TYPE
   SYNTAX      Integer32
   MAX-ACCESS  read-only
   STATUS      current
   DESCRIPTION
       "This two-octet field indicates the duration of the period in terms of 100 ms intervals. 1)
	   The default value is one second. 2) The lower bound is one second. 3)
	   The upper bound is one minute."
   ::= { sm48tat4xarpEthLinkOAMPortEventDetailedStatisticsEntry 4 }

sm48tat4xarpStatisticsLocalFrameErrorEventThreshold OBJECT-TYPE
   SYNTAX      Integer32
   MAX-ACCESS  read-only
   STATUS      current
   DESCRIPTION
       "This four-octet field indicates the number of detected errored frames in the period is required
	   to be equal to or greater than in order for the event to be generated. 1)
	   The default value is one frame error. 2)
	   The lower bound is zero frame errors. 3)
	   The upper bound is unspecified."
   ::= { sm48tat4xarpEthLinkOAMPortEventDetailedStatisticsEntry 5 }

sm48tat4xarpStatisticsLocalFrameErrors OBJECT-TYPE
   SYNTAX      Integer32
   MAX-ACCESS  read-only
   STATUS      current
   DESCRIPTION
       "This four-octet field indicates the number of detected errored frames in the period."
   ::= { sm48tat4xarpEthLinkOAMPortEventDetailedStatisticsEntry 6 }

sm48tat4xarpStatisticsLocalTotalFrameErrors OBJECT-TYPE
   SYNTAX      Counter64
   MAX-ACCESS  read-only
   STATUS      current
   DESCRIPTION
       "This eight-octet field indicates the sum of errored frames that have been detected since the OAM sublayer was reset."
   ::= { sm48tat4xarpEthLinkOAMPortEventDetailedStatisticsEntry 7 }

sm48tat4xarpStatisticsLocalTotalFrameErrorEvents OBJECT-TYPE
   SYNTAX      Integer32
   MAX-ACCESS  read-only
   STATUS      current
   DESCRIPTION
       "This four-octet field indicates the number of Errored Frame Event TLVs that
	   have been generated since the OAM sublayer was reset."
   ::= { sm48tat4xarpEthLinkOAMPortEventDetailedStatisticsEntry 8 }

sm48tat4xarpStatisticsLocalFramePeriodErrorEventTimestamp OBJECT-TYPE
   SYNTAX      Integer32
   MAX-ACCESS  read-only
   STATUS      current
   DESCRIPTION
       "This two-octet field indicates the time reference when the event was generated, in terms of 100 ms intervals."
   ::= { sm48tat4xarpEthLinkOAMPortEventDetailedStatisticsEntry 9 }

sm48tat4xarpStatisticsLocalFramePeriodErrorEventWindow OBJECT-TYPE
   SYNTAX      Integer32
   MAX-ACCESS  read-only
   STATUS      current
   DESCRIPTION
       "This four-octet field indicates the duration of period in terms of frames."
   ::= { sm48tat4xarpEthLinkOAMPortEventDetailedStatisticsEntry 10 }

sm48tat4xarpStatisticsLocalFramePeriodErrorEventThreshold OBJECT-TYPE
   SYNTAX      Integer32
   MAX-ACCESS  read-only
   STATUS      current
   DESCRIPTION
       "This four-octet field indicates the number of errored frames in the period is required
	   to be equal to or greater than in order for the event to be generated."
   ::= { sm48tat4xarpEthLinkOAMPortEventDetailedStatisticsEntry 11 }

sm48tat4xarpStatisticsLocalFramePeriodErrors OBJECT-TYPE
   SYNTAX      Integer32
   MAX-ACCESS  read-only
   STATUS      current
   DESCRIPTION
       "This four-octet field indicates the number of frame errors in the period."
   ::= { sm48tat4xarpEthLinkOAMPortEventDetailedStatisticsEntry 12 }

sm48tat4xarpStatisticsLocalTotalFramePeriodErrors OBJECT-TYPE
   SYNTAX      Counter64
   MAX-ACCESS  read-only
   STATUS      current
   DESCRIPTION
       "This eight-octet field indicates the sum of frame errors that have been detected since the OAM sublayer was reset."
   ::= { sm48tat4xarpEthLinkOAMPortEventDetailedStatisticsEntry 13 }

sm48tat4xarpStatisticsLocalTotalFramePeriodErrorEvents OBJECT-TYPE
   SYNTAX      Integer32
   MAX-ACCESS  read-only
   STATUS      current
   DESCRIPTION
       "This four-octet field indicates the number of Errored Frame Period Event TLVs
	   that have been generated since the OAM sublayer was reset."
   ::= { sm48tat4xarpEthLinkOAMPortEventDetailedStatisticsEntry 14 }

sm48tat4xarpStatisticsLocalSymbolPeriodErrorEventTimestamp OBJECT-TYPE
   SYNTAX      Integer32
   MAX-ACCESS  read-only
   STATUS      current
   DESCRIPTION
       "This two-octet field indicates the time reference when the event was generated, in terms of 100 ms intervals."
   ::= { sm48tat4xarpEthLinkOAMPortEventDetailedStatisticsEntry 15 }

sm48tat4xarpStatisticsLocalSymbolPeriodErrorEventWindow OBJECT-TYPE
   SYNTAX      Counter64
   MAX-ACCESS  read-only
   STATUS      current
   DESCRIPTION
       "This eight-octet field indicates the number of symbols in the period."
   ::= { sm48tat4xarpEthLinkOAMPortEventDetailedStatisticsEntry 16 }

sm48tat4xarpStatisticsLocalSymbolPeriodErrorEventThreshold OBJECT-TYPE
   SYNTAX      Counter64
   MAX-ACCESS  read-only
   STATUS      current
   DESCRIPTION
       "This eight-octet field indicates the number of errored symbols in the period is required to
	   be equal to or greater than in order for the event to be generated."
   ::= { sm48tat4xarpEthLinkOAMPortEventDetailedStatisticsEntry 17 }

sm48tat4xarpStatisticsLocalSymbolPeriodErrors OBJECT-TYPE
   SYNTAX      Counter64
   MAX-ACCESS  read-only
   STATUS      current
   DESCRIPTION
       "This eight-octet field indicates the number of symbol errors in the period."
   ::= { sm48tat4xarpEthLinkOAMPortEventDetailedStatisticsEntry 18 }

sm48tat4xarpStatisticsLocalSymbolFramePeriodErrors OBJECT-TYPE
   SYNTAX      Counter64
   MAX-ACCESS  read-only
   STATUS      current
   DESCRIPTION
       "This eight-octet field indicates the sum of symbol errors since the OAM sublayer was reset."
   ::= { sm48tat4xarpEthLinkOAMPortEventDetailedStatisticsEntry 19 }

sm48tat4xarpStatisticsLocalSymbolFramePeriodErrorEvents OBJECT-TYPE
   SYNTAX      Integer32
   MAX-ACCESS  read-only
   STATUS      current
   DESCRIPTION
       "This four-octet field indicates the number of Errored Symbol Period Event TLVs that
	   have been generated since the OAM sublayer was reset."
   ::= { sm48tat4xarpEthLinkOAMPortEventDetailedStatisticsEntry 20 }

sm48tat4xarpStatisticsLocalEventSecondsSummaryTimeStamp OBJECT-TYPE
   SYNTAX      Integer32
   MAX-ACCESS  read-only
   STATUS      current
   DESCRIPTION
       "This two-octet field indicates the time reference when the event was generated,
	   in terms of 100 ms intervals, encoded as a 16-bit unsigned integer."
   ::= { sm48tat4xarpEthLinkOAMPortEventDetailedStatisticsEntry 21 }

sm48tat4xarpStatisticsLocalEventSecondsSummaryWindow OBJECT-TYPE
   SYNTAX      Integer32
   MAX-ACCESS  read-only
   STATUS      current
   DESCRIPTION
       "This two-octet field indicates the duration of the period in terms of 100 ms intervals, encoded as a 16-bit unsigned integer."
   ::= { sm48tat4xarpEthLinkOAMPortEventDetailedStatisticsEntry 22 }

sm48tat4xarpStatisticsLocalEventSecondsSummaryThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."
   ::= { sm48tat4xarpEthLinkOAMPortEventDetailedStatisticsEntry 23 }

sm48tat4xarpStatisticsLocalEventSecondsSummaryEvents OBJECT-TYPE
   SYNTAX      Integer32
   MAX-ACCESS  read-only
   STATUS      current
   DESCRIPTION
       "This two-octet field indicates the number of errored frame seconds in the period, encoded as a 16-bit unsigned integer."
   ::= { sm48tat4xarpEthLinkOAMPortEventDetailedStatisticsEntry 24 }

sm48tat4xarpStatisticsLocalEventSecondsSummaryErrorTotal OBJECT-TYPE
   SYNTAX      Integer32
   MAX-ACCESS  read-only
   STATUS      current
   DESCRIPTION
       "This four-octet field indicates the sum of errored frame seconds that have been detected since the OAM sublayer was reset."
   ::= { sm48tat4xarpEthLinkOAMPortEventDetailedStatisticsEntry 25 }

sm48tat4xarpStatisticsLocalEventSecondsSummaryEventTotal OBJECT-TYPE
   SYNTAX      Integer32
   MAX-ACCESS  read-only
   STATUS      current
   DESCRIPTION
       "This four-octet field indicates the number of Errored Frame Seconds Summary Event TLVs that
	   have been generated since the OAM sublayer was reset, encoded as a 32bit unsigned integer."
   ::= { sm48tat4xarpEthLinkOAMPortEventDetailedStatisticsEntry 26 }

sm48tat4xarpStatisticsRemoteFrameErrorEventTimestamp OBJECT-TYPE
   SYNTAX      Integer32
   MAX-ACCESS  read-only
   STATUS      current
   DESCRIPTION
       "This two-octet field indicates the time reference when the event was generated, in terms of 100 ms intervals."
   ::= { sm48tat4xarpEthLinkOAMPortEventDetailedStatisticsEntry 27 }

sm48tat4xarpStatisticsRemoteFrameErrorEventWindow OBJECT-TYPE
   SYNTAX      Integer32
   MAX-ACCESS  read-only
   STATUS      current
   DESCRIPTION
       "This two-octet field indicates the duration of the period in terms of 100 ms intervals. 1)
	   The default value is one second. 2) The lower bound is one second. 3)
	   The upper bound is one minute."
   ::= { sm48tat4xarpEthLinkOAMPortEventDetailedStatisticsEntry 28 }

sm48tat4xarpStatisticsRemoteFrameErrorEventThreshold OBJECT-TYPE
   SYNTAX      Integer32
   MAX-ACCESS  read-only
   STATUS      current
   DESCRIPTION
       "This four-octet field indicates the number of detected errored frames in the period is required
	   to be equal to or greater than in order for the event to be generated. 1)
	   The default value is one frame error. 2)
	   The lower bound is zero frame errors. 3)
	   The upper bound is unspecified."
   ::= { sm48tat4xarpEthLinkOAMPortEventDetailedStatisticsEntry 29 }

sm48tat4xarpStatisticsRemoteFrameErrors OBJECT-TYPE
   SYNTAX      Integer32
   MAX-ACCESS  read-only
   STATUS      current
   DESCRIPTION
       "This four-octet field indicates the number of detected errored frames in the period."
   ::= { sm48tat4xarpEthLinkOAMPortEventDetailedStatisticsEntry 30 }

sm48tat4xarpStatisticsRemoteTotalFrameErrors OBJECT-TYPE
   SYNTAX      Counter64
   MAX-ACCESS  read-only
   STATUS      current
   DESCRIPTION
       "This eight-octet field indicates the sum of errored frames that have been detected since the OAM sublayer was reset."
   ::= { sm48tat4xarpEthLinkOAMPortEventDetailedStatisticsEntry 31 }

sm48tat4xarpStatisticsRemoteTotalFrameErrorEvents OBJECT-TYPE
   SYNTAX      Integer32
   MAX-ACCESS  read-only
   STATUS      current
   DESCRIPTION
       "This four-octet field indicates the number of Errored Frame Event TLVs that
	   have been generated since the OAM sublayer was reset."
   ::= { sm48tat4xarpEthLinkOAMPortEventDetailedStatisticsEntry 32 }

sm48tat4xarpStatisticsRemoteFramePeriodErrorEventTimestamp OBJECT-TYPE
   SYNTAX      Integer32
   MAX-ACCESS  read-only
   STATUS      current
   DESCRIPTION
       "This two-octet field indicates the time reference when the event was generated, in terms of 100 ms intervals."
   ::= { sm48tat4xarpEthLinkOAMPortEventDetailedStatisticsEntry 33 }

sm48tat4xarpStatisticsRemoteFramePeriodErrorEventWindow OBJECT-TYPE
   SYNTAX      Integer32
   MAX-ACCESS  read-only
   STATUS      current
   DESCRIPTION
       "This four-octet field indicates the duration of period in terms of frames."
   ::= { sm48tat4xarpEthLinkOAMPortEventDetailedStatisticsEntry 34 }

sm48tat4xarpStatisticsRemoteFramePeriodErrorEventThreshold OBJECT-TYPE
   SYNTAX      Integer32
   MAX-ACCESS  read-only
   STATUS      current
   DESCRIPTION
       "This four-octet field indicates the number of errored frames in the period is required
	   to be equal to or greater than in order for the event to be generated."
   ::= { sm48tat4xarpEthLinkOAMPortEventDetailedStatisticsEntry 35 }

sm48tat4xarpStatisticsRemoteFramePeriodErrors OBJECT-TYPE
   SYNTAX      Integer32
   MAX-ACCESS  read-only
   STATUS      current
   DESCRIPTION
       "This four-octet field indicates the number of frame errors in the period."
   ::= { sm48tat4xarpEthLinkOAMPortEventDetailedStatisticsEntry 36 }

sm48tat4xarpStatisticsRemoteTotalFramePeriodErrors OBJECT-TYPE
   SYNTAX      Counter64
   MAX-ACCESS  read-only
   STATUS      current
   DESCRIPTION
       "This eight-octet field indicates the sum of frame errors that have been detected since the OAM sublayer was reset."
   ::= { sm48tat4xarpEthLinkOAMPortEventDetailedStatisticsEntry 37 }

sm48tat4xarpStatisticsRemoteTotalFramePeriodErrorEvents OBJECT-TYPE
   SYNTAX      Integer32
   MAX-ACCESS  read-only
   STATUS      current
   DESCRIPTION
       "This four-octet field indicates the number of Errored Frame Period Event TLVs
	   that have been generated since the OAM sublayer was reset."
   ::= { sm48tat4xarpEthLinkOAMPortEventDetailedStatisticsEntry 38 }

sm48tat4xarpStatisticsRemoteSymbolPeriodErrorEventTimestamp OBJECT-TYPE
   SYNTAX      Integer32
   MAX-ACCESS  read-only
   STATUS      current
   DESCRIPTION
       "This two-octet field indicates the time reference when the event was generated, in terms of 100 ms intervals."
   ::= { sm48tat4xarpEthLinkOAMPortEventDetailedStatisticsEntry 39 }

sm48tat4xarpStatisticsRemoteSymbolPeriodErrorEventWindow OBJECT-TYPE
   SYNTAX      Counter64
   MAX-ACCESS  read-only
   STATUS      current
   DESCRIPTION
       "This eight-octet field indicates the number of symbols in the period."
   ::= { sm48tat4xarpEthLinkOAMPortEventDetailedStatisticsEntry 40 }

sm48tat4xarpStatisticsRemoteSymbolPeriodErrorEventThreshold OBJECT-TYPE
   SYNTAX      Counter64
   MAX-ACCESS  read-only
   STATUS      current
   DESCRIPTION
       "This eight-octet field indicates the number of errored symbols in the period is required to
	   be equal to or greater than in order for the event to be generated."
   ::= { sm48tat4xarpEthLinkOAMPortEventDetailedStatisticsEntry 41 }

sm48tat4xarpStatisticsRemoteSymbolPeriodErrors OBJECT-TYPE
   SYNTAX      Counter64
   MAX-ACCESS  read-only
   STATUS      current
   DESCRIPTION
       "This eight-octet field indicates the number of symbol errors in the period."
   ::= { sm48tat4xarpEthLinkOAMPortEventDetailedStatisticsEntry 42 }

sm48tat4xarpStatisticsRemoteSymbolFramePeriodErrors OBJECT-TYPE
   SYNTAX      Counter64
   MAX-ACCESS  read-only
   STATUS      current
   DESCRIPTION
       "This eight-octet field indicates the sum of symbol errors since the OAM sublayer was reset."
   ::= { sm48tat4xarpEthLinkOAMPortEventDetailedStatisticsEntry 43 }

sm48tat4xarpStatisticsRemoteSymbolFramePeriodErrorEvents OBJECT-TYPE
   SYNTAX      Integer32
   MAX-ACCESS  read-only
   STATUS      current
   DESCRIPTION
       "This four-octet field indicates the number of Errored Symbol Period Event TLVs that
	   have been generated since the OAM sublayer was reset."
   ::= { sm48tat4xarpEthLinkOAMPortEventDetailedStatisticsEntry 44 }

sm48tat4xarpStatisticsRemoteEventSecondsSummaryTimeStamp OBJECT-TYPE
   SYNTAX      Integer32
   MAX-ACCESS  read-only
   STATUS      current
   DESCRIPTION
       "This two-octet field indicates the time reference when the event was generated,
	   in terms of 100 ms intervals, encoded as a 16-bit unsigned integer."
   ::= { sm48tat4xarpEthLinkOAMPortEventDetailedStatisticsEntry 45 }

sm48tat4xarpStatisticsRemoteEventSecondsSummaryWindow OBJECT-TYPE
   SYNTAX      Integer32
   MAX-ACCESS  read-only
   STATUS      current
   DESCRIPTION
       "This two-octet field indicates the duration of the period in terms of 100 ms intervals, encoded as a 16-bit unsigned integer."
   ::= { sm48tat4xarpEthLinkOAMPortEventDetailedStatisticsEntry 46 }

sm48tat4xarpStatisticsRemoteEventSecondsSummaryThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."
   ::= { sm48tat4xarpEthLinkOAMPortEventDetailedStatisticsEntry 47 }

sm48tat4xarpStatisticsRemoteEventSecondsSummaryEvents OBJECT-TYPE
   SYNTAX      Integer32
   MAX-ACCESS  read-only
   STATUS      current
   DESCRIPTION
       "This two-octet field indicates the number of errored frame seconds in the period, encoded as a 16-bit unsigned integer."
   ::= { sm48tat4xarpEthLinkOAMPortEventDetailedStatisticsEntry 48 }

sm48tat4xarpStatisticsRemoteEventSecondsSummaryErrorTotal OBJECT-TYPE
   SYNTAX      Integer32
   MAX-ACCESS  read-only
   STATUS      current
   DESCRIPTION
       "This four-octet field indicates the sum of errored frame seconds that have been detected since the OAM sublayer was reset."
   ::= { sm48tat4xarpEthLinkOAMPortEventDetailedStatisticsEntry 49 }

sm48tat4xarpStatisticsRemoteEventSecondsSummaryEventTotal OBJECT-TYPE
   SYNTAX      Integer32
   MAX-ACCESS  read-only
   STATUS      current
   DESCRIPTION
       "This four-octet field indicates the number of Errored Frame Seconds Summary Event TLVs that
	   have been generated since the OAM sublayer was reset, encoded as a 32bit unsigned integer."
   ::= { sm48tat4xarpEthLinkOAMPortEventDetailedStatisticsEntry 50 }


sm48tat4xarpIPMC    OBJECT IDENTIFIER ::= { sm48tat4xarpConfiguration 32 }

sm48tat4xarpIGMPSnooping    OBJECT IDENTIFIER ::= { sm48tat4xarpIPMC 1 }

sm48tat4xarpIGMPSnoopingBasicConfigSnoopingEnabled OBJECT-TYPE
   SYNTAX      Integer32(0|1)
   MAX-ACCESS  read-write
   STATUS      current
   DESCRIPTION
       "Snooping Enabled
       0:Disable
       1:Enable"
   ::= {     sm48tat4xarpIGMPSnooping 2 }

sm48tat4xarpIGMPSnoopingUnregisteredIPMCv4FloodingEnabled OBJECT-TYPE
   SYNTAX      Integer32(0|1)
   MAX-ACCESS  read-write
   STATUS      current
   DESCRIPTION
       "Unregistered IPMCv4 Flooding Enabled
       0:Disable
       1:Enable"
   ::= {     sm48tat4xarpIGMPSnooping 3 }

sm48tat4xarpIGMPSnoopingBasicConfigIGMPSSMRange OBJECT-TYPE
   SYNTAX      IpAddress
   MAX-ACCESS  read-write
   STATUS      current
   DESCRIPTION
       "IGMP SSM Range
        IPv4 multicast address."
   ::= {     sm48tat4xarpIGMPSnooping 4 }

sm48tat4xarpIGMPSnoopingBasicConfigIGMPSSMRangeLength OBJECT-TYPE
   SYNTAX      Integer32(4..32)
   MAX-ACCESS  read-write
   STATUS      current
   DESCRIPTION
       "IGMP SSM Range prefix. "
   ::= {     sm48tat4xarpIGMPSnooping 5 }

sm48tat4xarpIGMPSnoopingBasicConfigLeaveProxyEnabled OBJECT-TYPE
   SYNTAX      Integer32(0|1)
   MAX-ACCESS  read-write
   STATUS      current
   DESCRIPTION
       "Leave Proxy Enabled
       0:Disable
       1:Enable"
   ::= {     sm48tat4xarpIGMPSnooping 6 }

sm48tat4xarpIGMPSnoopingBasicConfigProxyEnabled OBJECT-TYPE
   SYNTAX      Integer32(0|1)
   MAX-ACCESS  read-write
   STATUS      current
   DESCRIPTION
       "Proxy Enabled
       0:Disable
       1:Enable"
   ::= {     sm48tat4xarpIGMPSnooping 7 }



sm48tat4xarpIGMPSnoopingPortRelatedTable OBJECT-TYPE
   SYNTAX      SEQUENCE OF SM48TAT4XARPIGMPSnoopingPortRelatedEntry
   MAX-ACCESS  not-accessible
   STATUS      current
   DESCRIPTION
       " "
   ::= { sm48tat4xarpIGMPSnooping 8 }

sm48tat4xarpIGMPSnoopingPortRelatedEntry OBJECT-TYPE
   SYNTAX      SM48TAT4XARPIGMPSnoopingPortRelatedEntry
   MAX-ACCESS  not-accessible
   STATUS      current
   DESCRIPTION
       " "
   INDEX    { sm48tat4xarpIGMPSnoopingPortRelatedPort  }
   ::= { sm48tat4xarpIGMPSnoopingPortRelatedTable 1 }

SM48TAT4XARPIGMPSnoopingPortRelatedEntry ::= SEQUENCE {
   sm48tat4xarpIGMPSnoopingPortRelatedPort       Integer32,
   sm48tat4xarpIGMPSnoopingPortRouterPort        Integer32,
   sm48tat4xarpIGMPSnoopingPortFastLeave         Integer32,
   sm48tat4xarpIGMPSnoopingPortThrottling        Integer32,
   sm48tat4xarpIGMPSnoopingPortFilteringProfile  DisplayString
}

sm48tat4xarpIGMPSnoopingPortRelatedPort OBJECT-TYPE
   SYNTAX      Integer32(1..65535)
   MAX-ACCESS  not-accessible
   STATUS      current
   DESCRIPTION
       "Index"
   ::= {     sm48tat4xarpIGMPSnoopingPortRelatedEntry 1 }

sm48tat4xarpIGMPSnoopingPortRouterPort OBJECT-TYPE
   SYNTAX      Integer32(0|1)
   MAX-ACCESS  read-write
   STATUS      current
   DESCRIPTION
       "Router Port
       0:Disable
       1:Enable"
   ::= {     sm48tat4xarpIGMPSnoopingPortRelatedEntry 2 }

sm48tat4xarpIGMPSnoopingPortFastLeave OBJECT-TYPE
   SYNTAX      Integer32(0|1)
   MAX-ACCESS  read-write
   STATUS      current
   DESCRIPTION
       "Fast Leave
       0:Disable
       1:Enable"
   ::= {     sm48tat4xarpIGMPSnoopingPortRelatedEntry 3 }

sm48tat4xarpIGMPSnoopingPortThrottling OBJECT-TYPE
   SYNTAX      Integer32(0..10)
   MAX-ACCESS  read-write
   STATUS      current
   DESCRIPTION
       "Throttling.
       Range: 0:unlimited, 1-10"
   ::= {     sm48tat4xarpIGMPSnoopingPortRelatedEntry 4 }

sm48tat4xarpIGMPSnoopingPortFilteringProfile OBJECT-TYPE
   SYNTAX      DisplayString
   MAX-ACCESS  read-write
   STATUS      current
   DESCRIPTION
       "Filtering Profile"
   ::= {     sm48tat4xarpIGMPSnoopingPortRelatedEntry 5 }

sm48tat4xarpIGMPSnoopingVLANConfigTable OBJECT-TYPE
   SYNTAX      SEQUENCE OF SM48TAT4XARPIGMPSnoopingVLANConfigEntry
   MAX-ACCESS  not-accessible
   STATUS      current
   DESCRIPTION
       " "
   ::= { sm48tat4xarpIGMPSnooping 9 }

sm48tat4xarpIGMPSnoopingVLANConfigEntry OBJECT-TYPE
   SYNTAX      SM48TAT4XARPIGMPSnoopingVLANConfigEntry
   MAX-ACCESS  not-accessible
   STATUS      current
   DESCRIPTION
       " "
   INDEX    { sm48tat4xarpIGMPSnoopingVLANConfigIndex  }
   ::= { sm48tat4xarpIGMPSnoopingVLANConfigTable 1 }

SM48TAT4XARPIGMPSnoopingVLANConfigEntry ::= SEQUENCE {
   sm48tat4xarpIGMPSnoopingVLANConfigIndex            Integer32,
   sm48tat4xarpIGMPSnoopingVLANConfigVLANID           Integer32,
   sm48tat4xarpIGMPSnoopingVLANConfigSnoopingEnabled  Integer32,
   sm48tat4xarpIGMPSnoopingVLANConfigQuerierElection  Integer32,
   sm48tat4xarpIGMPSnoopingVLANConfigQuerierAddress   IpAddress,
   sm48tat4xarpIGMPSnoopingVLANConfigCompatibility    Integer32,
   sm48tat4xarpIGMPSnoopingVLANConfigPRI              Integer32,
   sm48tat4xarpIGMPSnoopingVLANConfigRV               Integer32,
   sm48tat4xarpIGMPSnoopingVLANConfigQI               Integer32,
   sm48tat4xarpIGMPSnoopingVLANConfigQRI              Integer32,
   sm48tat4xarpIGMPSnoopingVLANConfigLLQI             Integer32,
   sm48tat4xarpIGMPSnoopingVLANConfigURI              Integer32
}

sm48tat4xarpIGMPSnoopingVLANConfigIndex OBJECT-TYPE
   SYNTAX      Integer32(1..65535)
   MAX-ACCESS  not-accessible
   STATUS      current
   DESCRIPTION
       "Index"
   ::= {     sm48tat4xarpIGMPSnoopingVLANConfigEntry 1 }

sm48tat4xarpIGMPSnoopingVLANConfigVLANID OBJECT-TYPE
   SYNTAX      Integer32
   MAX-ACCESS  read-only
   STATUS      current
   DESCRIPTION
       "VLAN ID"
   ::= {     sm48tat4xarpIGMPSnoopingVLANConfigEntry 2 }

sm48tat4xarpIGMPSnoopingVLANConfigSnoopingEnabled OBJECT-TYPE
   SYNTAX      Integer32(0|1)
   MAX-ACCESS  read-write
   STATUS      current
   DESCRIPTION
       "IGMP Snooping Enabled
       0:Disable
       1:Enable"
   ::= {     sm48tat4xarpIGMPSnoopingVLANConfigEntry 3 }

sm48tat4xarpIGMPSnoopingVLANConfigQuerierElection OBJECT-TYPE
   SYNTAX      Integer32(0|1)
   MAX-ACCESS  read-write
   STATUS      current
   DESCRIPTION
       "Querier Election
       0:Disable
       1:Enable"
   ::= {     sm48tat4xarpIGMPSnoopingVLANConfigEntry 4 }

sm48tat4xarpIGMPSnoopingVLANConfigQuerierAddress OBJECT-TYPE
   SYNTAX      IpAddress
   MAX-ACCESS  read-write
   STATUS      current
   DESCRIPTION
       "Querier Address"
   ::= {     sm48tat4xarpIGMPSnoopingVLANConfigEntry 5 }

sm48tat4xarpIGMPSnoopingVLANConfigCompatibility OBJECT-TYPE
   SYNTAX      Integer32(0..3)
   MAX-ACCESS  read-write
   STATUS      current
   DESCRIPTION
       "Compatibility
       0:IGMP-Auto
       1:Forced IGMPv1
       2:Forced IGMPv2
       3:Forced IGMPv3"
   ::= {     sm48tat4xarpIGMPSnoopingVLANConfigEntry 6 }

sm48tat4xarpIGMPSnoopingVLANConfigPRI OBJECT-TYPE
   SYNTAX      Integer32(0..7)
   MAX-ACCESS  read-write
   STATUS      current
   DESCRIPTION
       "Priority of Interface.
       "
   ::= {     sm48tat4xarpIGMPSnoopingVLANConfigEntry 7 }

sm48tat4xarpIGMPSnoopingVLANConfigRV OBJECT-TYPE
   SYNTAX      Integer32(1..255)
   MAX-ACCESS  read-write
   STATUS      current
   DESCRIPTION
       "Robustness Variable."
   ::= {     sm48tat4xarpIGMPSnoopingVLANConfigEntry 8 }

sm48tat4xarpIGMPSnoopingVLANConfigQI OBJECT-TYPE
   SYNTAX      Integer32(1..31744)
   MAX-ACCESS  read-write
   STATUS      current
   DESCRIPTION
       "Query Interval."
   ::= {     sm48tat4xarpIGMPSnoopingVLANConfigEntry 9 }

sm48tat4xarpIGMPSnoopingVLANConfigQRI OBJECT-TYPE
   SYNTAX      Integer32(0..31744)
   MAX-ACCESS  read-write
   STATUS      current
   DESCRIPTION
       "Query Response Interval."
   ::= {     sm48tat4xarpIGMPSnoopingVLANConfigEntry 10 }

sm48tat4xarpIGMPSnoopingVLANConfigLLQI OBJECT-TYPE
   SYNTAX      Integer32(0..31744)
   MAX-ACCESS  read-write
   STATUS      current
   DESCRIPTION
       "Last Member Query Interval."
   ::= {     sm48tat4xarpIGMPSnoopingVLANConfigEntry 11 }

sm48tat4xarpIGMPSnoopingVLANConfigURI OBJECT-TYPE
   SYNTAX      Integer32(0..31744)
   MAX-ACCESS  read-write
   STATUS      current
   DESCRIPTION
       "Unsolicited Report Interval."
   ::= {     sm48tat4xarpIGMPSnoopingVLANConfigEntry 12 }


sm48tat4xarpIGMPSnoopingStatusClear OBJECT-TYPE
   SYNTAX      Integer32(0|1)
   MAX-ACCESS  read-write
   STATUS      current
   DESCRIPTION
       "Clears all Statistics counters."
   ::= { sm48tat4xarpIGMPSnooping 10 }


sm48tat4xarpIGMPSnoopingStatusTable OBJECT-TYPE
   SYNTAX      SEQUENCE OF SM48TAT4XARPIGMPSnoopingStatusEntry
   MAX-ACCESS  not-accessible
   STATUS      current
   DESCRIPTION
       " "
   ::= { sm48tat4xarpIGMPSnooping 11 }

sm48tat4xarpIGMPSnoopingStatusEntry OBJECT-TYPE
   SYNTAX      SM48TAT4XARPIGMPSnoopingStatusEntry
   MAX-ACCESS  not-accessible
   STATUS      current
   DESCRIPTION
       " "
   INDEX    { sm48tat4xarpIGMPSnoopingStatusIndex  }
   ::= { sm48tat4xarpIGMPSnoopingStatusTable 1 }

SM48TAT4XARPIGMPSnoopingStatusEntry ::= SEQUENCE {
   sm48tat4xarpIGMPSnoopingStatusIndex               Integer32,
   sm48tat4xarpIGMPSnoopingStatusVLANID              Integer32,
   sm48tat4xarpIGMPSnoopingStatusQuerierVersion      DisplayString,
   sm48tat4xarpIGMPSnoopingStatusHostVersion         DisplayString,
   sm48tat4xarpIGMPSnoopingStatusQuerierStatus       Integer32,
   sm48tat4xarpIGMPSnoopingStatusQueriesTransmitted  Integer32,
   sm48tat4xarpIGMPSnoopingStatusQueriesReceived     Integer32,
   sm48tat4xarpIGMPSnoopingStatusV1ReportsReceived   Integer32,
   sm48tat4xarpIGMPSnoopingStatusV2ReportsReceived   Integer32,
   sm48tat4xarpIGMPSnoopingStatusV3ReportsReceived   Integer32,
   sm48tat4xarpIGMPSnoopingStatusV2LeavesReceived    Integer32
}

sm48tat4xarpIGMPSnoopingStatusIndex OBJECT-TYPE
   SYNTAX      Integer32(1..65535)
   MAX-ACCESS  not-accessible
   STATUS      current
   DESCRIPTION
       "Index"
   ::= {     sm48tat4xarpIGMPSnoopingStatusEntry 1 }

sm48tat4xarpIGMPSnoopingStatusVLANID OBJECT-TYPE
   SYNTAX      Integer32
   MAX-ACCESS  read-only
   STATUS      current
   DESCRIPTION
       "VLAN ID"
   ::= {     sm48tat4xarpIGMPSnoopingStatusEntry 2 }

sm48tat4xarpIGMPSnoopingStatusQuerierVersion OBJECT-TYPE
   SYNTAX      DisplayString
   MAX-ACCESS  read-only
   STATUS      current
   DESCRIPTION
       "Querier Version"
   ::= {     sm48tat4xarpIGMPSnoopingStatusEntry 3 }

sm48tat4xarpIGMPSnoopingStatusHostVersion OBJECT-TYPE
   SYNTAX      DisplayString
   MAX-ACCESS  read-only
   STATUS      current
   DESCRIPTION
       "Host Version"
   ::= {     sm48tat4xarpIGMPSnoopingStatusEntry 4 }

sm48tat4xarpIGMPSnoopingStatusQuerierStatus OBJECT-TYPE
   SYNTAX      Integer32
   MAX-ACCESS  read-only
   STATUS      current
   DESCRIPTION
       "Querier Status.
       0:Init
       1:Idle
       2:Active"
   ::= {     sm48tat4xarpIGMPSnoopingStatusEntry 5 }

sm48tat4xarpIGMPSnoopingStatusQueriesTransmitted OBJECT-TYPE
   SYNTAX      Integer32
   MAX-ACCESS  read-only
   STATUS      current
   DESCRIPTION
       "Queries Transmitted."
   ::= {     sm48tat4xarpIGMPSnoopingStatusEntry 6 }

sm48tat4xarpIGMPSnoopingStatusQueriesReceived OBJECT-TYPE
   SYNTAX      Integer32
   MAX-ACCESS  read-only
   STATUS      current
   DESCRIPTION
       "Queries Received."
   ::= {     sm48tat4xarpIGMPSnoopingStatusEntry 7 }

sm48tat4xarpIGMPSnoopingStatusV1ReportsReceived OBJECT-TYPE
   SYNTAX      Integer32
   MAX-ACCESS  read-only
   STATUS      current
   DESCRIPTION
       "V1 Reports Received"
   ::= {     sm48tat4xarpIGMPSnoopingStatusEntry 8 }

sm48tat4xarpIGMPSnoopingStatusV2ReportsReceived OBJECT-TYPE
   SYNTAX      Integer32
   MAX-ACCESS  read-only
   STATUS      current
   DESCRIPTION
       "V2 Reports Received"
   ::= {     sm48tat4xarpIGMPSnoopingStatusEntry 9 }

sm48tat4xarpIGMPSnoopingStatusV3ReportsReceived OBJECT-TYPE
   SYNTAX      Integer32
   MAX-ACCESS  read-only
   STATUS      current
   DESCRIPTION
       "V3 Reports Received"
   ::= {     sm48tat4xarpIGMPSnoopingStatusEntry 10 }

sm48tat4xarpIGMPSnoopingStatusV2LeavesReceived OBJECT-TYPE
   SYNTAX      Integer32
   MAX-ACCESS  read-only
   STATUS      current
   DESCRIPTION
       "V2 Leaves Received"
   ::= {     sm48tat4xarpIGMPSnoopingStatusEntry 11 }

sm48tat4xarpIGMPSnoopingStatusRouterPortTable OBJECT-TYPE
   SYNTAX      SEQUENCE OF SM48TAT4XARPIGMPSnoopingStatusRouterPortEntry
   MAX-ACCESS  not-accessible
   STATUS      current
   DESCRIPTION
       " "
   ::= { sm48tat4xarpIGMPSnooping 12 }

sm48tat4xarpIGMPSnoopingStatusRouterPortEntry OBJECT-TYPE
   SYNTAX      SM48TAT4XARPIGMPSnoopingStatusRouterPortEntry
   MAX-ACCESS  not-accessible
   STATUS      current
   DESCRIPTION
       " "
   INDEX    { sm48tat4xarpIGMPSnoopingStatusRouterPortIndex  }
   ::= { sm48tat4xarpIGMPSnoopingStatusRouterPortTable 1 }

SM48TAT4XARPIGMPSnoopingStatusRouterPortEntry ::= SEQUENCE {
   sm48tat4xarpIGMPSnoopingStatusRouterPortIndex    Integer32,
   sm48tat4xarpIGMPSnoopingStatusRouterPortPort     Integer32
}

sm48tat4xarpIGMPSnoopingStatusRouterPortIndex OBJECT-TYPE
   SYNTAX      Integer32(1..65535)
   MAX-ACCESS  not-accessible
   STATUS      current
   DESCRIPTION
       "Index"
   ::= {     sm48tat4xarpIGMPSnoopingStatusRouterPortEntry 1 }

sm48tat4xarpIGMPSnoopingStatusRouterPortPort OBJECT-TYPE
   SYNTAX      Integer32
   MAX-ACCESS  read-only
   STATUS      current
   DESCRIPTION
       "Switch port number.
       0:DISABLE
       1:IDLE
       2:ACTIVE"
   ::= {     sm48tat4xarpIGMPSnoopingStatusRouterPortEntry 2 }



sm48tat4xarpIGMPSnoopingGroupInfoTable OBJECT-TYPE
   SYNTAX      SEQUENCE OF SM48TAT4XARPIGMPSnoopingGroupInfoEntry
   MAX-ACCESS  not-accessible
   STATUS      current
   DESCRIPTION
       " "
   ::= { sm48tat4xarpIGMPSnooping 13 }

sm48tat4xarpIGMPSnoopingGroupInfoEntry OBJECT-TYPE
   SYNTAX      SM48TAT4XARPIGMPSnoopingGroupInfoEntry
   MAX-ACCESS  not-accessible
   STATUS      current
   DESCRIPTION
       " "
   INDEX    { sm48tat4xarpIGMPSnoopingGroupInfoIndex  }
   ::= { sm48tat4xarpIGMPSnoopingGroupInfoTable 1 }

SM48TAT4XARPIGMPSnoopingGroupInfoEntry ::= SEQUENCE {
   sm48tat4xarpIGMPSnoopingGroupInfoIndex       Integer32,
   sm48tat4xarpIGMPSnoopingGroupInfoVLANID      Integer32,
   sm48tat4xarpIGMPSnoopingGroupInfoGroups      IpAddress,
   sm48tat4xarpIGMPSnoopingGroupInfoPortMembers DisplayString
}

sm48tat4xarpIGMPSnoopingGroupInfoIndex OBJECT-TYPE
   SYNTAX      Integer32(1..65535)
   MAX-ACCESS  not-accessible
   STATUS      current
   DESCRIPTION
       "Index"
   ::= {     sm48tat4xarpIGMPSnoopingGroupInfoEntry 1 }

sm48tat4xarpIGMPSnoopingGroupInfoVLANID OBJECT-TYPE
   SYNTAX      Integer32
   MAX-ACCESS  read-only
   STATUS      current
   DESCRIPTION
       "VLAN ID"
   ::= {     sm48tat4xarpIGMPSnoopingGroupInfoEntry 2 }

sm48tat4xarpIGMPSnoopingGroupInfoGroups OBJECT-TYPE
   SYNTAX      IpAddress
   MAX-ACCESS  read-only
   STATUS      current
   DESCRIPTION
       "Groups"
   ::= {     sm48tat4xarpIGMPSnoopingGroupInfoEntry 3 }

sm48tat4xarpIGMPSnoopingGroupInfoPortMembers OBJECT-TYPE
   SYNTAX      DisplayString
   MAX-ACCESS  read-only
   STATUS      current
   DESCRIPTION
       "Port Members"
   ::= {     sm48tat4xarpIGMPSnoopingGroupInfoEntry 4 }



sm48tat4xarpIGMPSFMInfoTable OBJECT-TYPE
   SYNTAX      SEQUENCE OF SM48TAT4XARPIGMPSFMInfoEntry
   MAX-ACCESS  not-accessible
   STATUS      current
   DESCRIPTION
       " "
   ::= { sm48tat4xarpIGMPSnooping 14 }

sm48tat4xarpIGMPSFMInfoEntry OBJECT-TYPE
   SYNTAX      SM48TAT4XARPIGMPSFMInfoEntry
   MAX-ACCESS  not-accessible
   STATUS      current
   DESCRIPTION
       " "
   INDEX    { sm48tat4xarpIGMPSFMInfoIndex  }
   ::= { sm48tat4xarpIGMPSFMInfoTable 1 }

SM48TAT4XARPIGMPSFMInfoEntry ::= SEQUENCE {
   sm48tat4xarpIGMPSFMInfoIndex                Integer32,
   sm48tat4xarpIGMPSFMInfoVLANID               Integer32,
   sm48tat4xarpIGMPSFMInfoGroup                IpAddress,
   sm48tat4xarpIGMPSFMInfoPort                 Integer32,
   sm48tat4xarpIGMPSFMInfoMode                 Integer32,
   sm48tat4xarpIGMPSFMInfoSourceAddress        DisplayString,
   sm48tat4xarpIGMPSFMInfoType                 Integer32,
   sm48tat4xarpIGMPSFMInfoHardwareFilterSwitch Integer32

}

sm48tat4xarpIGMPSFMInfoIndex OBJECT-TYPE
   SYNTAX      Integer32(1..65535)
   MAX-ACCESS  not-accessible
   STATUS      current
   DESCRIPTION
       "Index"
   ::= {     sm48tat4xarpIGMPSFMInfoEntry 1 }

sm48tat4xarpIGMPSFMInfoVLANID OBJECT-TYPE
   SYNTAX      Integer32
   MAX-ACCESS  read-only
   STATUS      current
   DESCRIPTION
       "VLAN ID"
   ::= {     sm48tat4xarpIGMPSFMInfoEntry 2 }

sm48tat4xarpIGMPSFMInfoGroup OBJECT-TYPE
   SYNTAX      IpAddress
   MAX-ACCESS  read-only
   STATUS      current
   DESCRIPTION
       "Group"
   ::= {     sm48tat4xarpIGMPSFMInfoEntry 3 }

sm48tat4xarpIGMPSFMInfoPort OBJECT-TYPE
   SYNTAX      Integer32
   MAX-ACCESS  read-only
   STATUS      current
   DESCRIPTION
       "Port"
   ::= {     sm48tat4xarpIGMPSFMInfoEntry 4 }

sm48tat4xarpIGMPSFMInfoMode OBJECT-TYPE
   SYNTAX      Integer32
   MAX-ACCESS  read-only
   STATUS      current
   DESCRIPTION
       "Mode
       0:Exclude.
       1:Include"
   ::= {     sm48tat4xarpIGMPSFMInfoEntry 5 }

sm48tat4xarpIGMPSFMInfoSourceAddress OBJECT-TYPE
   SYNTAX      DisplayString
   MAX-ACCESS  read-only
   STATUS      current
   DESCRIPTION
       "Source Address"
   ::= {     sm48tat4xarpIGMPSFMInfoEntry 6 }

sm48tat4xarpIGMPSFMInfoType OBJECT-TYPE
   SYNTAX      Integer32
   MAX-ACCESS  read-only
   STATUS      current
   DESCRIPTION
       "Type
       0:Deny
       1:Allow"
   ::= {     sm48tat4xarpIGMPSFMInfoEntry 7 }

sm48tat4xarpIGMPSFMInfoHardwareFilterSwitch OBJECT-TYPE
   SYNTAX      Integer32
   MAX-ACCESS  read-only
   STATUS      current
   DESCRIPTION
       "Hardware Filter\Switch
       0:No
       1:Yes"
   ::= {     sm48tat4xarpIGMPSFMInfoEntry 8 }

sm48tat4xarpMLDSnooping    OBJECT IDENTIFIER ::= { sm48tat4xarpIPMC 2 }

sm48tat4xarpMLDSnoopingBasicConfigSnoopingEnabled OBJECT-TYPE
   SYNTAX      Integer32(0|1)
   MAX-ACCESS  read-write
   STATUS      current
   DESCRIPTION
       "Snooping Enabled
       0:Disable
       1:Enable"
   ::= {     sm48tat4xarpMLDSnooping 2 }

sm48tat4xarpMLDSnoopingUnregisteredIPMCv6FloodingEnabled OBJECT-TYPE
   SYNTAX      Integer32(0|1)
   MAX-ACCESS  read-write
   STATUS      current
   DESCRIPTION
       "Unregistered IPMCv6 Flooding Enabled
       0:Disable
       1:Enable"
   ::= {     sm48tat4xarpMLDSnooping 3 }

sm48tat4xarpMLDSnoopingBasicConfigMLDSSMRange OBJECT-TYPE
   SYNTAX      DisplayString
   MAX-ACCESS  read-write
   STATUS      current
   DESCRIPTION
       "MLD SSM Range
        IPv6 multicast address."
   ::= {     sm48tat4xarpMLDSnooping 4 }

sm48tat4xarpMLDSnoopingBasicConfigMLDSSMRangeLength OBJECT-TYPE
   SYNTAX      Integer32(8..128)
   MAX-ACCESS  read-write
   STATUS      current
   DESCRIPTION
       "MLD SSM Range prefix. "
   ::= {     sm48tat4xarpMLDSnooping 5 }

sm48tat4xarpMLDSnoopingBasicConfigLeaveProxyEnabled OBJECT-TYPE
   SYNTAX      Integer32(0|1)
   MAX-ACCESS  read-write
   STATUS      current
   DESCRIPTION
       "Leave Proxy Enabled
       0:Disable
       1:Enable"
   ::= {     sm48tat4xarpMLDSnooping 6 }

sm48tat4xarpMLDSnoopingBasicConfigProxyEnabled OBJECT-TYPE
   SYNTAX      Integer32(0|1)
   MAX-ACCESS  read-write
   STATUS      current
   DESCRIPTION
       "Proxy Enabled
       0:Disable
       1:Enable"
   ::= {     sm48tat4xarpMLDSnooping 7 }



sm48tat4xarpMLDSnoopingPortRelatedTable OBJECT-TYPE
   SYNTAX      SEQUENCE OF SM48TAT4XARPMLDSnoopingPortRelatedEntry
   MAX-ACCESS  not-accessible
   STATUS      current
   DESCRIPTION
       " "
   ::= { sm48tat4xarpMLDSnooping 8 }

sm48tat4xarpMLDSnoopingPortRelatedEntry OBJECT-TYPE
   SYNTAX      SM48TAT4XARPMLDSnoopingPortRelatedEntry
   MAX-ACCESS  not-accessible
   STATUS      current
   DESCRIPTION
       " "
   INDEX    { sm48tat4xarpMLDSnoopingPortRelatedPort  }
   ::= { sm48tat4xarpMLDSnoopingPortRelatedTable 1 }

SM48TAT4XARPMLDSnoopingPortRelatedEntry ::= SEQUENCE {
   sm48tat4xarpMLDSnoopingPortRelatedPort       Integer32,
   sm48tat4xarpMLDSnoopingPortRouterPort        Integer32,
   sm48tat4xarpMLDSnoopingPortFastLeave         Integer32,
   sm48tat4xarpMLDSnoopingPortThrottling        Integer32,
   sm48tat4xarpMLDSnoopingPortFilteringProfile  DisplayString
}

sm48tat4xarpMLDSnoopingPortRelatedPort OBJECT-TYPE
   SYNTAX      Integer32(1..65535)
   MAX-ACCESS  not-accessible
   STATUS      current
   DESCRIPTION
       "Index"
   ::= {     sm48tat4xarpMLDSnoopingPortRelatedEntry 1 }

sm48tat4xarpMLDSnoopingPortRouterPort OBJECT-TYPE
   SYNTAX      Integer32(0|1)
   MAX-ACCESS  read-write
   STATUS      current
   DESCRIPTION
       "Router Port
       0:Disable
       1:Enable"
   ::= {     sm48tat4xarpMLDSnoopingPortRelatedEntry 2 }

sm48tat4xarpMLDSnoopingPortFastLeave OBJECT-TYPE
   SYNTAX      Integer32(0|1)
   MAX-ACCESS  read-write
   STATUS      current
   DESCRIPTION
       "Fast Leave
       0:Disable
       1:Enable"
   ::= {     sm48tat4xarpMLDSnoopingPortRelatedEntry 3 }

sm48tat4xarpMLDSnoopingPortThrottling OBJECT-TYPE
   SYNTAX      Integer32(0..10)
   MAX-ACCESS  read-write
   STATUS      current
   DESCRIPTION
       "Throttling.
       Range: 0:unlimited, 1-10"
   ::= {     sm48tat4xarpMLDSnoopingPortRelatedEntry 4 }

sm48tat4xarpMLDSnoopingPortFilteringProfile OBJECT-TYPE
   SYNTAX      DisplayString
   MAX-ACCESS  read-write
   STATUS      current
   DESCRIPTION
       "Filtering Profile"
   ::= {     sm48tat4xarpMLDSnoopingPortRelatedEntry 5 }


sm48tat4xarpMLDSnoopingVLANConfigTable OBJECT-TYPE
   SYNTAX      SEQUENCE OF SM48TAT4XARPMLDSnoopingVLANConfigEntry
   MAX-ACCESS  not-accessible
   STATUS      current
   DESCRIPTION
       " "
   ::= { sm48tat4xarpMLDSnooping 9 }

sm48tat4xarpMLDSnoopingVLANConfigEntry OBJECT-TYPE
   SYNTAX      SM48TAT4XARPMLDSnoopingVLANConfigEntry
   MAX-ACCESS  not-accessible
   STATUS      current
   DESCRIPTION
       " "
   INDEX    { sm48tat4xarpMLDSnoopingVLANConfigIndex  }
   ::= { sm48tat4xarpMLDSnoopingVLANConfigTable 1 }

SM48TAT4XARPMLDSnoopingVLANConfigEntry ::= SEQUENCE {
   sm48tat4xarpMLDSnoopingVLANConfigIndex            Integer32,
   sm48tat4xarpMLDSnoopingVLANConfigVLANID           Integer32,
   sm48tat4xarpMLDSnoopingVLANConfigSnoopingEnabled  Integer32,
   sm48tat4xarpMLDSnoopingVLANConfigQuerierElection  Integer32,
   sm48tat4xarpMLDSnoopingVLANConfigCompatibility    Integer32,
   sm48tat4xarpMLDSnoopingVLANConfigPRI              Integer32,
   sm48tat4xarpMLDSnoopingVLANConfigRV               Integer32,
   sm48tat4xarpMLDSnoopingVLANConfigQI               Integer32,
   sm48tat4xarpMLDSnoopingVLANConfigQRI              Integer32,
   sm48tat4xarpMLDSnoopingVLANConfigLLQI             Integer32,
   sm48tat4xarpMLDSnoopingVLANConfigURI              Integer32
}

sm48tat4xarpMLDSnoopingVLANConfigIndex OBJECT-TYPE
   SYNTAX      Integer32(1..65535)
   MAX-ACCESS  not-accessible
   STATUS      current
   DESCRIPTION
       "Index"
   ::= {     sm48tat4xarpMLDSnoopingVLANConfigEntry 1 }

sm48tat4xarpMLDSnoopingVLANConfigVLANID OBJECT-TYPE
   SYNTAX      Integer32
   MAX-ACCESS  read-only
   STATUS      current
   DESCRIPTION
       "VLAN ID"
   ::= {     sm48tat4xarpMLDSnoopingVLANConfigEntry 2 }

sm48tat4xarpMLDSnoopingVLANConfigSnoopingEnabled OBJECT-TYPE
   SYNTAX      Integer32(0|1)
   MAX-ACCESS  read-write
   STATUS      current
   DESCRIPTION
       "IGMP Snooping Enabled
       0:Disable
       1:Enable"
   ::= {     sm48tat4xarpMLDSnoopingVLANConfigEntry 3 }

sm48tat4xarpMLDSnoopingVLANConfigQuerierElection OBJECT-TYPE
   SYNTAX      Integer32(0|1)
   MAX-ACCESS  read-write
   STATUS      current
   DESCRIPTION
       "Querier Election
       0:Disable
       1:Enable"
   ::= {     sm48tat4xarpMLDSnoopingVLANConfigEntry 4 }

sm48tat4xarpMLDSnoopingVLANConfigCompatibility OBJECT-TYPE
   SYNTAX      Integer32(0..2)
   MAX-ACCESS  read-write
   STATUS      current
   DESCRIPTION
       "Compatibility
       0:MLD-Auto
       1:Forced MLDv1
       2:Forced MLDv2"
   ::= {     sm48tat4xarpMLDSnoopingVLANConfigEntry 6 }

sm48tat4xarpMLDSnoopingVLANConfigPRI OBJECT-TYPE
   SYNTAX      Integer32(0..7)
   MAX-ACCESS  read-write
   STATUS      current
   DESCRIPTION
       "Priority of Interface.
       "
   ::= {     sm48tat4xarpMLDSnoopingVLANConfigEntry 7 }

sm48tat4xarpMLDSnoopingVLANConfigRV OBJECT-TYPE
   SYNTAX      Integer32(1..255)
   MAX-ACCESS  read-write
   STATUS      current
   DESCRIPTION
       "Robustness Variable."
   ::= {     sm48tat4xarpMLDSnoopingVLANConfigEntry 8 }

sm48tat4xarpMLDSnoopingVLANConfigQI OBJECT-TYPE
   SYNTAX      Integer32(1..31744)
   MAX-ACCESS  read-write
   STATUS      current
   DESCRIPTION
       "Query Interval."
   ::= {     sm48tat4xarpMLDSnoopingVLANConfigEntry 9 }

sm48tat4xarpMLDSnoopingVLANConfigQRI OBJECT-TYPE
   SYNTAX      Integer32(0..31744)
   MAX-ACCESS  read-write
   STATUS      current
   DESCRIPTION
       "Query Response Interval."
   ::= {     sm48tat4xarpMLDSnoopingVLANConfigEntry 10 }

sm48tat4xarpMLDSnoopingVLANConfigLLQI OBJECT-TYPE
   SYNTAX      Integer32(0..31744)
   MAX-ACCESS  read-write
   STATUS      current
   DESCRIPTION
       "Last Member Query Interval."
   ::= {     sm48tat4xarpMLDSnoopingVLANConfigEntry 11 }

sm48tat4xarpMLDSnoopingVLANConfigURI OBJECT-TYPE
   SYNTAX      Integer32(0..31744)
   MAX-ACCESS  read-write
   STATUS      current
   DESCRIPTION
       "Unsolicited Report Interval."
   ::= {     sm48tat4xarpMLDSnoopingVLANConfigEntry 12 }


sm48tat4xarpMLDSnoopingStatusClear OBJECT-TYPE
   SYNTAX      Integer32(0|1)
   MAX-ACCESS  read-write
   STATUS      current
   DESCRIPTION
       "Clears all Statistics counters."
   ::= { sm48tat4xarpMLDSnooping 10 }


sm48tat4xarpMLDSnoopingStatusTable OBJECT-TYPE
   SYNTAX      SEQUENCE OF SM48TAT4XARPMLDSnoopingStatusEntry
   MAX-ACCESS  not-accessible
   STATUS      current
   DESCRIPTION
       " "
   ::= { sm48tat4xarpMLDSnooping 11 }

sm48tat4xarpMLDSnoopingStatusEntry OBJECT-TYPE
   SYNTAX      SM48TAT4XARPMLDSnoopingStatusEntry
   MAX-ACCESS  not-accessible
   STATUS      current
   DESCRIPTION
       " "
   INDEX    { sm48tat4xarpMLDSnoopingStatusIndex  }
   ::= { sm48tat4xarpMLDSnoopingStatusTable 1 }

SM48TAT4XARPMLDSnoopingStatusEntry ::= SEQUENCE {
   sm48tat4xarpMLDSnoopingStatusIndex               Integer32,
   sm48tat4xarpMLDSnoopingStatusVLANID              Integer32,
   sm48tat4xarpMLDSnoopingStatusQuerierVersion      DisplayString,
   sm48tat4xarpMLDSnoopingStatusHostVersion         DisplayString,
   sm48tat4xarpMLDSnoopingStatusQuerierStatus       Integer32,
   sm48tat4xarpMLDSnoopingStatusQueriesTransmitted  Integer32,
   sm48tat4xarpMLDSnoopingStatusQueriesReceived     Integer32,
   sm48tat4xarpMLDSnoopingStatusV1ReportsReceived   Integer32,
   sm48tat4xarpMLDSnoopingStatusV2ReportsReceived   Integer32,
   sm48tat4xarpMLDSnoopingStatusV1LeavesReceived    Integer32
}

sm48tat4xarpMLDSnoopingStatusIndex OBJECT-TYPE
   SYNTAX      Integer32(1..65535)
   MAX-ACCESS  not-accessible
   STATUS      current
   DESCRIPTION
       "Index"
   ::= {     sm48tat4xarpMLDSnoopingStatusEntry 1 }

sm48tat4xarpMLDSnoopingStatusVLANID OBJECT-TYPE
   SYNTAX      Integer32
   MAX-ACCESS  read-only
   STATUS      current
   DESCRIPTION
       "VLAN ID"
   ::= {     sm48tat4xarpMLDSnoopingStatusEntry 2 }

sm48tat4xarpMLDSnoopingStatusQuerierVersion OBJECT-TYPE
   SYNTAX      DisplayString
   MAX-ACCESS  read-only
   STATUS      current
   DESCRIPTION
       "Querier Version"
   ::= {     sm48tat4xarpMLDSnoopingStatusEntry 3 }

sm48tat4xarpMLDSnoopingStatusHostVersion OBJECT-TYPE
   SYNTAX      DisplayString
   MAX-ACCESS  read-only
   STATUS      current
   DESCRIPTION
       "Host Version"
   ::= {     sm48tat4xarpMLDSnoopingStatusEntry 4 }

sm48tat4xarpMLDSnoopingStatusQuerierStatus OBJECT-TYPE
   SYNTAX      Integer32
   MAX-ACCESS  read-only
   STATUS      current
   DESCRIPTION
       "Querier Status.
       0:Init
       1:Idle
       2:Active"
   ::= {     sm48tat4xarpMLDSnoopingStatusEntry 5 }

sm48tat4xarpMLDSnoopingStatusQueriesTransmitted OBJECT-TYPE
   SYNTAX      Integer32
   MAX-ACCESS  read-only
   STATUS      current
   DESCRIPTION
       "Queries Transmitted."
   ::= {     sm48tat4xarpMLDSnoopingStatusEntry 6 }

sm48tat4xarpMLDSnoopingStatusQueriesReceived OBJECT-TYPE
   SYNTAX      Integer32
   MAX-ACCESS  read-only
   STATUS      current
   DESCRIPTION
       "Queries Received."
   ::= {     sm48tat4xarpMLDSnoopingStatusEntry 7 }

sm48tat4xarpMLDSnoopingStatusV1ReportsReceived OBJECT-TYPE
   SYNTAX      Integer32
   MAX-ACCESS  read-only
   STATUS      current
   DESCRIPTION
       "V1 Reports Received"
   ::= {     sm48tat4xarpMLDSnoopingStatusEntry 8 }

sm48tat4xarpMLDSnoopingStatusV2ReportsReceived OBJECT-TYPE
   SYNTAX      Integer32
   MAX-ACCESS  read-only
   STATUS      current
   DESCRIPTION
       "V2 Reports Received"
   ::= {     sm48tat4xarpMLDSnoopingStatusEntry 9 }

sm48tat4xarpMLDSnoopingStatusV1LeavesReceived OBJECT-TYPE
   SYNTAX      Integer32
   MAX-ACCESS  read-only
   STATUS      current
   DESCRIPTION
       "V1 Leaves Received"
   ::= {     sm48tat4xarpMLDSnoopingStatusEntry 11 }

sm48tat4xarpMLDSnoopingStatusRouterPortTable OBJECT-TYPE
   SYNTAX      SEQUENCE OF SM48TAT4XARPMLDSnoopingStatusRouterPortEntry
   MAX-ACCESS  not-accessible
   STATUS      current
   DESCRIPTION
       " "
   ::= { sm48tat4xarpMLDSnooping 12 }

sm48tat4xarpMLDSnoopingStatusRouterPortEntry OBJECT-TYPE
   SYNTAX      SM48TAT4XARPMLDSnoopingStatusRouterPortEntry
   MAX-ACCESS  not-accessible
   STATUS      current
   DESCRIPTION
       " "
   INDEX    { sm48tat4xarpMLDSnoopingStatusRouterPortIndex  }
   ::= { sm48tat4xarpMLDSnoopingStatusRouterPortTable 1 }

SM48TAT4XARPMLDSnoopingStatusRouterPortEntry ::= SEQUENCE {
   sm48tat4xarpMLDSnoopingStatusRouterPortIndex    Integer32,
   sm48tat4xarpMLDSnoopingStatusRouterPortPort     Integer32
}

sm48tat4xarpMLDSnoopingStatusRouterPortIndex OBJECT-TYPE
   SYNTAX      Integer32(1..65535)
   MAX-ACCESS  not-accessible
   STATUS      current
   DESCRIPTION
       "Index"
   ::= {     sm48tat4xarpMLDSnoopingStatusRouterPortEntry 1 }

sm48tat4xarpMLDSnoopingStatusRouterPortPort OBJECT-TYPE
   SYNTAX      Integer32
   MAX-ACCESS  read-only
   STATUS      current
   DESCRIPTION
       "Switch port number.
       0:DISABLE
       1:IDLE
       2:ACTIVE"
   ::= {     sm48tat4xarpMLDSnoopingStatusRouterPortEntry 2 }


sm48tat4xarpMLDSnoopingGroupInfoTable OBJECT-TYPE
   SYNTAX      SEQUENCE OF SM48TAT4XARPMLDSnoopingGroupInfoEntry
   MAX-ACCESS  not-accessible
   STATUS      current
   DESCRIPTION
       " "
   ::= { sm48tat4xarpMLDSnooping 13 }

sm48tat4xarpMLDSnoopingGroupInfoEntry OBJECT-TYPE
   SYNTAX      SM48TAT4XARPMLDSnoopingGroupInfoEntry
   MAX-ACCESS  not-accessible
   STATUS      current
   DESCRIPTION
       " "
   INDEX    { sm48tat4xarpMLDSnoopingGroupInfoIndex  }
   ::= { sm48tat4xarpMLDSnoopingGroupInfoTable 1 }

SM48TAT4XARPMLDSnoopingGroupInfoEntry ::= SEQUENCE {
   sm48tat4xarpMLDSnoopingGroupInfoIndex       Integer32,
   sm48tat4xarpMLDSnoopingGroupInfoVLANID      Integer32,
   sm48tat4xarpMLDSnoopingGroupInfoGroups      IpAddress,
   sm48tat4xarpMLDSnoopingGroupInfoPortMembers DisplayString
}

sm48tat4xarpMLDSnoopingGroupInfoIndex OBJECT-TYPE
   SYNTAX      Integer32(1..65535)
   MAX-ACCESS  not-accessible
   STATUS      current
   DESCRIPTION
       "Index"
   ::= {     sm48tat4xarpMLDSnoopingGroupInfoEntry 1 }

sm48tat4xarpMLDSnoopingGroupInfoVLANID OBJECT-TYPE
   SYNTAX      Integer32
   MAX-ACCESS  read-only
   STATUS      current
   DESCRIPTION
       "VLAN ID"
   ::= {     sm48tat4xarpMLDSnoopingGroupInfoEntry 2 }

sm48tat4xarpMLDSnoopingGroupInfoGroups OBJECT-TYPE
   SYNTAX      IpAddress
   MAX-ACCESS  read-only
   STATUS      current
   DESCRIPTION
       "Groups"
   ::= {     sm48tat4xarpMLDSnoopingGroupInfoEntry 3 }

sm48tat4xarpMLDSnoopingGroupInfoPortMembers OBJECT-TYPE
   SYNTAX      DisplayString
   MAX-ACCESS  read-only
   STATUS      current
   DESCRIPTION
       "Port Members"
   ::= {     sm48tat4xarpMLDSnoopingGroupInfoEntry 4 }



sm48tat4xarpMLDSFMInfoTable OBJECT-TYPE
   SYNTAX      SEQUENCE OF SM48TAT4XARPMLDSFMInfoEntry
   MAX-ACCESS  not-accessible
   STATUS      current
   DESCRIPTION
       " "
   ::= { sm48tat4xarpMLDSnooping 14 }

sm48tat4xarpMLDSFMInfoEntry OBJECT-TYPE
   SYNTAX      SM48TAT4XARPMLDSFMInfoEntry
   MAX-ACCESS  not-accessible
   STATUS      current
   DESCRIPTION
       " "
   INDEX    { sm48tat4xarpMLDSFMInfoIndex  }
   ::= { sm48tat4xarpMLDSFMInfoTable 1 }

SM48TAT4XARPMLDSFMInfoEntry ::= SEQUENCE {
   sm48tat4xarpMLDSFMInfoIndex                Integer32,
   sm48tat4xarpMLDSFMInfoVLANID               Integer32,
   sm48tat4xarpMLDSFMInfoGroup                IpAddress,
   sm48tat4xarpMLDSFMInfoPort                 Integer32,
   sm48tat4xarpMLDSFMInfoMode                 Integer32,
   sm48tat4xarpMLDSFMInfoSourceAddress        DisplayString,
   sm48tat4xarpMLDSFMInfoType                 Integer32,
   sm48tat4xarpMLDSFMInfoHardwareFilterSwitch Integer32

}

sm48tat4xarpMLDSFMInfoIndex OBJECT-TYPE
   SYNTAX      Integer32(1..65535)
   MAX-ACCESS  not-accessible
   STATUS      current
   DESCRIPTION
       "Index"
   ::= {     sm48tat4xarpMLDSFMInfoEntry 1 }

sm48tat4xarpMLDSFMInfoVLANID OBJECT-TYPE
   SYNTAX      Integer32
   MAX-ACCESS  read-only
   STATUS      current
   DESCRIPTION
       "VLAN ID"
   ::= {     sm48tat4xarpMLDSFMInfoEntry 2 }

sm48tat4xarpMLDSFMInfoGroup OBJECT-TYPE
   SYNTAX      IpAddress
   MAX-ACCESS  read-only
   STATUS      current
   DESCRIPTION
       "Group"
   ::= {     sm48tat4xarpMLDSFMInfoEntry 3 }

sm48tat4xarpMLDSFMInfoPort OBJECT-TYPE
   SYNTAX      Integer32
   MAX-ACCESS  read-only
   STATUS      current
   DESCRIPTION
       "Port"
   ::= {     sm48tat4xarpMLDSFMInfoEntry 4 }

sm48tat4xarpMLDSFMInfoMode OBJECT-TYPE
   SYNTAX      Integer32
   MAX-ACCESS  read-only
   STATUS      current
   DESCRIPTION
       "Mode
       0:Exclude.
       1:Include"
   ::= {     sm48tat4xarpMLDSFMInfoEntry 5 }

sm48tat4xarpMLDSFMInfoSourceAddress OBJECT-TYPE
   SYNTAX      DisplayString
   MAX-ACCESS  read-only
   STATUS      current
   DESCRIPTION
       "Source Address"
   ::= {     sm48tat4xarpMLDSFMInfoEntry 6 }

sm48tat4xarpMLDSFMInfoType OBJECT-TYPE
   SYNTAX      Integer32
   MAX-ACCESS  read-only
   STATUS      current
   DESCRIPTION
       "Type
       0:Deny
       1:Allow"
   ::= {     sm48tat4xarpMLDSFMInfoEntry 7 }

sm48tat4xarpMLDSFMInfoHardwareFilterSwitch OBJECT-TYPE
   SYNTAX      Integer32
   MAX-ACCESS  read-only
   STATUS      current
   DESCRIPTION
       "Hardware Filter\Switch
       0:No
       1:Yes"
   ::= {     sm48tat4xarpMLDSFMInfoEntry 8 }

sm48tat4xarpMVR    OBJECT IDENTIFIER ::= { sm48tat4xarpConfiguration 33 }

sm48tat4xarpMVRConfig    OBJECT IDENTIFIER ::= { sm48tat4xarpMVR 1 }

sm48tat4xarpMVRConfigMVRMode OBJECT-TYPE
   SYNTAX      Integer32
   MAX-ACCESS  read-write
   STATUS      current
   DESCRIPTION
       "MVR Mode
       0:Disable
       1:Enable"
   ::= { sm48tat4xarpMVRConfig 2 }


sm48tat4xarpVLANInterfaceSettingTable  OBJECT-TYPE
   SYNTAX      SEQUENCE OF SM48TAT4XARPVLANInterfaceSettingEntry
   MAX-ACCESS  not-accessible
   STATUS      current
   DESCRIPTION
       "MVR Config table"
 ::= { sm48tat4xarpMVRConfig 3 }

sm48tat4xarpVLANInterfaceSettingEntry OBJECT-TYPE
    SYNTAX        SM48TAT4XARPVLANInterfaceSettingEntry
    MAX-ACCESS    not-accessible
    STATUS        current
    DESCRIPTION
        "MVR Config table"
    INDEX        { sm48tat4xarpVLANInterfaceSettingIndex }
    ::= { sm48tat4xarpVLANInterfaceSettingTable 1 }

SM48TAT4XARPVLANInterfaceSettingEntry ::=
    SEQUENCE {
        sm48tat4xarpVLANInterfaceSettingIndex                    Integer32,
        sm48tat4xarpVLANInterfaceSettingMVRVID                   Integer32,
        sm48tat4xarpVLANInterfaceSettingMVRName                  DisplayString,
        sm48tat4xarpVLANInterfaceSettingIGMPAddress              IpAddress,
        sm48tat4xarpVLANInterfaceSettingMode                     Integer32,
        sm48tat4xarpVLANInterfaceSettingTagging                  Integer32,
        sm48tat4xarpVLANInterfaceSettingPriority                 Integer32,
        sm48tat4xarpVLANInterfaceSettingLLQI                     Integer32,
        sm48tat4xarpVLANInterfaceSettingInterfaceChannelProfile  DisplayString,
        sm48tat4xarpVLANInterfaceSettingRowStatus                RowStatus
    }

sm48tat4xarpVLANInterfaceSettingIndex OBJECT-TYPE
   SYNTAX      Integer32(1..65535)
   MAX-ACCESS  not-accessible
   STATUS      current
   DESCRIPTION
       "MVR Config index."
   ::= {sm48tat4xarpVLANInterfaceSettingEntry 1 }

sm48tat4xarpVLANInterfaceSettingMVRVID OBJECT-TYPE
   SYNTAX      Integer32
   MAX-ACCESS  read-create
   STATUS      current
   DESCRIPTION
       "MVR VLAN ID"
   ::= {sm48tat4xarpVLANInterfaceSettingEntry 2 }

sm48tat4xarpVLANInterfaceSettingMVRName OBJECT-TYPE
   SYNTAX      DisplayString
   MAX-ACCESS  read-create
   STATUS      current
   DESCRIPTION
       "MVR Name. Length:0-16"
   ::= {sm48tat4xarpVLANInterfaceSettingEntry 3 }

sm48tat4xarpVLANInterfaceSettingIGMPAddress OBJECT-TYPE
   SYNTAX      IpAddress
   MAX-ACCESS  read-create
   STATUS      current
   DESCRIPTION
       "IPv4 IGMP Address"
   ::= {sm48tat4xarpVLANInterfaceSettingEntry 4 }

sm48tat4xarpVLANInterfaceSettingMode OBJECT-TYPE
   SYNTAX      Integer32
   MAX-ACCESS  read-create
   STATUS      current
   DESCRIPTION
      "Mode.
       0:Dynamic
       1:Compatible"
   ::= {sm48tat4xarpVLANInterfaceSettingEntry 5 }

sm48tat4xarpVLANInterfaceSettingTagging OBJECT-TYPE
   SYNTAX      Integer32
   MAX-ACCESS  read-create
   STATUS      current
   DESCRIPTION
      "Tagging.
       0:Untagged
       1:Tagged"
   ::= {sm48tat4xarpVLANInterfaceSettingEntry 6 }

sm48tat4xarpVLANInterfaceSettingPriority OBJECT-TYPE
   SYNTAX      Integer32(0..7)
   MAX-ACCESS  read-create
   STATUS      current
   DESCRIPTION
      "Priority"
   ::= {sm48tat4xarpVLANInterfaceSettingEntry 7 }

sm48tat4xarpVLANInterfaceSettingLLQI OBJECT-TYPE
   SYNTAX      Integer32(0..31744)
   MAX-ACCESS  read-create
   STATUS      current
   DESCRIPTION
      "LLQI"
   ::= {sm48tat4xarpVLANInterfaceSettingEntry 8 }

sm48tat4xarpVLANInterfaceSettingInterfaceChannelProfile OBJECT-TYPE
   SYNTAX      DisplayString
   MAX-ACCESS  read-create
   STATUS      current
   DESCRIPTION
      "Interface Channel Profile."
   ::= {sm48tat4xarpVLANInterfaceSettingEntry 9 }


sm48tat4xarpVLANInterfaceSettingRowStatus OBJECT-TYPE
   SYNTAX      RowStatus
   MAX-ACCESS  read-create
   STATUS      current
   DESCRIPTION
       "Row Status."
   ::= {sm48tat4xarpVLANInterfaceSettingEntry 10 }

sm48tat4xarpMVRVIDIndex OBJECT-TYPE
   SYNTAX      Integer32
   MAX-ACCESS  read-write
   STATUS      current
   DESCRIPTION
       "Set VIDIndex before use VLANInterfaceSettingPortRoleTable table."
   ::= { sm48tat4xarpMVRConfig 4 }

sm48tat4xarpVLANInterfaceSettingPortRoleTable  OBJECT-TYPE
   SYNTAX      SEQUENCE OF SM48TAT4XARPVLANInterfaceSettingPortRoleEntry
   MAX-ACCESS  not-accessible
   STATUS      current
   DESCRIPTION
       "VLAN Interface Setting Port Role table"
 ::= { sm48tat4xarpMVRConfig 5 }

sm48tat4xarpVLANInterfaceSettingPortRoleEntry OBJECT-TYPE
    SYNTAX        SM48TAT4XARPVLANInterfaceSettingPortRoleEntry
    MAX-ACCESS    not-accessible
    STATUS        current
    DESCRIPTION
        "VLAN Interface Setting Port Role table"
    INDEX        { sm48tat4xarpVLANInterfaceSettingPortRoleIndex }
    ::= { sm48tat4xarpVLANInterfaceSettingPortRoleTable 1 }

SM48TAT4XARPVLANInterfaceSettingPortRoleEntry ::=
    SEQUENCE {
        sm48tat4xarpVLANInterfaceSettingPortRoleIndex   Integer32,
        sm48tat4xarpVLANInterfaceSettingPortRolePort    Integer32
    }

sm48tat4xarpVLANInterfaceSettingPortRoleIndex OBJECT-TYPE
   SYNTAX      Integer32(1..65535)
   MAX-ACCESS  not-accessible
   STATUS      current
   DESCRIPTION
       "VLAN Interface Setting Port Role index."
   ::= {sm48tat4xarpVLANInterfaceSettingPortRoleEntry 1 }

sm48tat4xarpVLANInterfaceSettingPortRolePort OBJECT-TYPE
   SYNTAX      Integer32(0..2)
   MAX-ACCESS  read-write
   STATUS      current
   DESCRIPTION
       "Port Role.
       0:Inactive
       1:Source
       2:Receiver"
   ::= {sm48tat4xarpVLANInterfaceSettingPortRoleEntry 2 }



sm48tat4xarpImmediateLeaveSettingTable  OBJECT-TYPE
   SYNTAX      SEQUENCE OF SM48TAT4XARPImmediateLeaveSettingEntry
   MAX-ACCESS  not-accessible
   STATUS      current
   DESCRIPTION
       "Immediate Leave Setting table"
 ::= { sm48tat4xarpMVRConfig 6 }

sm48tat4xarpImmediateLeaveSettingEntry OBJECT-TYPE
    SYNTAX        SM48TAT4XARPImmediateLeaveSettingEntry
    MAX-ACCESS    not-accessible
    STATUS        current
    DESCRIPTION
        "Immediate Leave Setting table"
    INDEX        { sm48tat4xarpImmediateLeaveSettingPort }
    ::= { sm48tat4xarpImmediateLeaveSettingTable 1 }

SM48TAT4XARPImmediateLeaveSettingEntry ::=
    SEQUENCE {
        sm48tat4xarpImmediateLeaveSettingPort            Integer32,
        sm48tat4xarpImmediateLeaveSettingImmediateLeave  Integer32
    }

sm48tat4xarpImmediateLeaveSettingPort OBJECT-TYPE
   SYNTAX      Integer32(1..65535)
   MAX-ACCESS  not-accessible
   STATUS      current
   DESCRIPTION
       "Immediate Leave Setting index."
   ::= {sm48tat4xarpImmediateLeaveSettingEntry 1 }

sm48tat4xarpImmediateLeaveSettingImmediateLeave OBJECT-TYPE
   SYNTAX      Integer32(0|1)
   MAX-ACCESS  read-write
   STATUS      current
   DESCRIPTION
      "Immediate Leave
       0:Disable
       1:Enable"
   ::= {sm48tat4xarpImmediateLeaveSettingEntry 2 }


sm48tat4xarpStatistics    OBJECT IDENTIFIER ::= { sm48tat4xarpMVR 2 }

sm48tat4xarpMVRStatisticsClear OBJECT-TYPE
   SYNTAX      Integer32
   MAX-ACCESS  read-write
   STATUS      current
   DESCRIPTION
       "Statistics Clear.
       1:Clear"
   ::= { sm48tat4xarpStatistics 2 }

sm48tat4xarpMVRStatisticsTable OBJECT-TYPE
   SYNTAX      SEQUENCE OF SM48TAT4XARPMVRStatisticsEntry
   MAX-ACCESS  not-accessible
   STATUS      current
   DESCRIPTION
       " "
   ::= { sm48tat4xarpStatistics 3 }

sm48tat4xarpMVRStatisticsEntry OBJECT-TYPE
   SYNTAX      SM48TAT4XARPMVRStatisticsEntry
   MAX-ACCESS  not-accessible
   STATUS      current
   DESCRIPTION
       " "
   INDEX    { sm48tat4xarpMVRStatisticsIndex  }
   ::= { sm48tat4xarpMVRStatisticsTable 1 }

SM48TAT4XARPMVRStatisticsEntry ::= SEQUENCE {
   sm48tat4xarpMVRStatisticsIndex                       Integer32,
   sm48tat4xarpMVRStatisticsVLANID                      Integer32,
   sm48tat4xarpMVRStatisticsIGMPMLDQueriesReceived      DisplayString,
   sm48tat4xarpMVRStatisticsIGMPMLDQueriesTransmitted   DisplayString,
   sm48tat4xarpMVRStatisticsIGMPv1JoinsReceived         DisplayString,
   sm48tat4xarpMVRStatisticsIGMPv2MLDv1ReportsReceived  DisplayString,
   sm48tat4xarpMVRStatisticsIGMPv3MLDv2ReportsReceived  DisplayString,
   sm48tat4xarpMVRStatisticsIGMPv2MLDv1LeavesReceived   DisplayString
}

sm48tat4xarpMVRStatisticsIndex OBJECT-TYPE
   SYNTAX      Integer32(1..65535)
   MAX-ACCESS  not-accessible
   STATUS      current
   DESCRIPTION
       "Index"
   ::= {     sm48tat4xarpMVRStatisticsEntry 1 }

sm48tat4xarpMVRStatisticsVLANID OBJECT-TYPE
   SYNTAX      Integer32
   MAX-ACCESS  read-only
   STATUS      current
   DESCRIPTION
       "VLAN ID"
   ::= {     sm48tat4xarpMVRStatisticsEntry 2 }

sm48tat4xarpMVRStatisticsIGMPMLDQueriesReceived OBJECT-TYPE
   SYNTAX      DisplayString
   MAX-ACCESS  read-only
   STATUS      current
   DESCRIPTION
       "IGMP/MLD Queries Received"
   ::= {     sm48tat4xarpMVRStatisticsEntry 3 }

sm48tat4xarpMVRStatisticsIGMPMLDQueriesTransmitted OBJECT-TYPE
   SYNTAX      DisplayString
   MAX-ACCESS  read-only
   STATUS      current
   DESCRIPTION
       "IGMP/MLD Queries Transmitted"
   ::= {     sm48tat4xarpMVRStatisticsEntry 4 }

sm48tat4xarpMVRStatisticsIGMPv1JoinsReceived OBJECT-TYPE
   SYNTAX      DisplayString
   MAX-ACCESS  read-only
   STATUS      current
   DESCRIPTION
       "IGMPv1 Joins Received"
   ::= {     sm48tat4xarpMVRStatisticsEntry 5 }

sm48tat4xarpMVRStatisticsIGMPv2MLDv1ReportsReceived OBJECT-TYPE
   SYNTAX      DisplayString
   MAX-ACCESS  read-only
   STATUS      current
   DESCRIPTION
       "IGMPv2/MLDv1 Reports Received"
   ::= {     sm48tat4xarpMVRStatisticsEntry 6 }

sm48tat4xarpMVRStatisticsIGMPv3MLDv2ReportsReceived OBJECT-TYPE
   SYNTAX      DisplayString
   MAX-ACCESS  read-only
   STATUS      current
   DESCRIPTION
       "IGMPv3/MLDv2 Reports Received"
   ::= {     sm48tat4xarpMVRStatisticsEntry 7 }

sm48tat4xarpMVRStatisticsIGMPv2MLDv1LeavesReceived OBJECT-TYPE
   SYNTAX      DisplayString
   MAX-ACCESS  read-only
   STATUS      current
   DESCRIPTION
       "IGMPv2/MLDv1 Leaves Received"
   ::= {     sm48tat4xarpMVRStatisticsEntry 8 }


sm48tat4xarpGroupInformation  OBJECT IDENTIFIER ::= { sm48tat4xarpMVR 3 }

sm48tat4xarpMVRGroupInfoTable OBJECT-TYPE
   SYNTAX      SEQUENCE OF SM48TAT4XARPMVRGroupInfoEntry
   MAX-ACCESS  not-accessible
   STATUS      current
   DESCRIPTION
       " "
   ::= { sm48tat4xarpGroupInformation 1 }

sm48tat4xarpMVRGroupInfoEntry OBJECT-TYPE
   SYNTAX      SM48TAT4XARPMVRGroupInfoEntry
   MAX-ACCESS  not-accessible
   STATUS      current
   DESCRIPTION
       " "
   INDEX    { sm48tat4xarpMVRGroupInfoIndex  }
   ::= { sm48tat4xarpMVRGroupInfoTable 1 }

SM48TAT4XARPMVRGroupInfoEntry ::= SEQUENCE {
   sm48tat4xarpMVRGroupInfoIndex       Integer32,
   sm48tat4xarpMVRGroupInfoVLANID      Integer32,
   sm48tat4xarpMVRGroupInfoGroups      DisplayString,
   sm48tat4xarpMVRGroupInfoPortMembers DisplayString
}

sm48tat4xarpMVRGroupInfoIndex OBJECT-TYPE
   SYNTAX      Integer32(1..65535)
   MAX-ACCESS  not-accessible
   STATUS      current
   DESCRIPTION
       "Index"
   ::= {     sm48tat4xarpMVRGroupInfoEntry 1 }

sm48tat4xarpMVRGroupInfoVLANID OBJECT-TYPE
   SYNTAX      Integer32
   MAX-ACCESS  read-only
   STATUS      current
   DESCRIPTION
       "VLAN ID"
   ::= {     sm48tat4xarpMVRGroupInfoEntry 2 }

sm48tat4xarpMVRGroupInfoGroups OBJECT-TYPE
   SYNTAX      DisplayString
   MAX-ACCESS  read-only
   STATUS      current
   DESCRIPTION
       "Groups"
   ::= {     sm48tat4xarpMVRGroupInfoEntry 3 }

sm48tat4xarpMVRGroupInfoPortMembers OBJECT-TYPE
   SYNTAX      DisplayString
   MAX-ACCESS  read-only
   STATUS      current
   DESCRIPTION
       "Port Members"
   ::= {     sm48tat4xarpMVRGroupInfoEntry 4 }

sm48tat4xarpMVRSFMInformation  OBJECT IDENTIFIER ::= { sm48tat4xarpMVR 4 }

sm48tat4xarpMVRSFMInfoTable OBJECT-TYPE
   SYNTAX      SEQUENCE OF SM48TAT4XARPMVRSFMInfoEntry
   MAX-ACCESS  not-accessible
   STATUS      current
   DESCRIPTION
       " "
   ::= { sm48tat4xarpMVRSFMInformation 2 }

sm48tat4xarpMVRSFMInfoEntry OBJECT-TYPE
   SYNTAX      SM48TAT4XARPMVRSFMInfoEntry
   MAX-ACCESS  not-accessible
   STATUS      current
   DESCRIPTION
       " "
   INDEX    { sm48tat4xarpMVRSFMInfoIndex  }
   ::= { sm48tat4xarpMVRSFMInfoTable 1 }

SM48TAT4XARPMVRSFMInfoEntry ::= SEQUENCE {
   sm48tat4xarpMVRSFMInfoIndex                Integer32,
   sm48tat4xarpMVRSFMInfoVLANID               Integer32,
   sm48tat4xarpMVRSFMInfoGroup                DisplayString,
   sm48tat4xarpMVRSFMInfoPort                 Integer32,
   sm48tat4xarpMVRSFMInfoMode                 Integer32,
   sm48tat4xarpMVRSFMInfoSourceAddress        DisplayString,
   sm48tat4xarpMVRSFMInfoType                 Integer32,
   sm48tat4xarpMVRSFMInfoHardwareFilterSwitch Integer32

}

sm48tat4xarpMVRSFMInfoIndex OBJECT-TYPE
   SYNTAX      Integer32(1..65535)
   MAX-ACCESS  not-accessible
   STATUS      current
   DESCRIPTION
       "Index"
   ::= {     sm48tat4xarpMVRSFMInfoEntry 1 }

sm48tat4xarpMVRSFMInfoVLANID OBJECT-TYPE
   SYNTAX      Integer32
   MAX-ACCESS  read-only
   STATUS      current
   DESCRIPTION
       "VLAN ID"
   ::= {     sm48tat4xarpMVRSFMInfoEntry 2 }

sm48tat4xarpMVRSFMInfoGroup OBJECT-TYPE
   SYNTAX      DisplayString
   MAX-ACCESS  read-only
   STATUS      current
   DESCRIPTION
       "Group"
   ::= {     sm48tat4xarpMVRSFMInfoEntry 3 }

sm48tat4xarpMVRSFMInfoPort OBJECT-TYPE
   SYNTAX      Integer32
   MAX-ACCESS  read-only
   STATUS      current
   DESCRIPTION
       "Port"
   ::= {     sm48tat4xarpMVRSFMInfoEntry 4 }

sm48tat4xarpMVRSFMInfoMode OBJECT-TYPE
   SYNTAX      Integer32
   MAX-ACCESS  read-only
   STATUS      current
   DESCRIPTION
       "Mode
       0:Exclude.
       1:Include"
   ::= {     sm48tat4xarpMVRSFMInfoEntry 5 }

sm48tat4xarpMVRSFMInfoSourceAddress OBJECT-TYPE
   SYNTAX      DisplayString
   MAX-ACCESS  read-only
   STATUS      current
   DESCRIPTION
       "Source Address"
   ::= {     sm48tat4xarpMVRSFMInfoEntry 6 }

sm48tat4xarpMVRSFMInfoType OBJECT-TYPE
   SYNTAX      Integer32
   MAX-ACCESS  read-only
   STATUS      current
   DESCRIPTION
       "Type
       0:Deny
       1:Allow"
   ::= {     sm48tat4xarpMVRSFMInfoEntry 7 }

sm48tat4xarpMVRSFMInfoHardwareFilterSwitch OBJECT-TYPE
   SYNTAX      Integer32
   MAX-ACCESS  read-only
   STATUS      current
   DESCRIPTION
       "Hardware Filter\Switch
       0:No
       1:Yes"
   ::= {     sm48tat4xarpMVRSFMInfoEntry 8 }


sm48tat4xarpIPMCLIB    OBJECT IDENTIFIER ::= { sm48tat4xarpConfiguration 34 }

sm48tat4xarpMulticastFilteringProfileMode OBJECT-TYPE
   SYNTAX      Integer32
   MAX-ACCESS  read-write
   STATUS      current
   DESCRIPTION
       "Multicast Filtering Profile Mode.
       0:Disable
       1:Enable"
   ::= {     sm48tat4xarpIPMCLIB 1 }


sm48tat4xarpMulticastFilteringProfileSettingTable  OBJECT-TYPE
   SYNTAX      SEQUENCE OF SM48TAT4XARPMulticastFilteringProfileSettingEntry
   MAX-ACCESS  not-accessible
   STATUS      current
   DESCRIPTION
       "Multicast Filtering Profile Setting table"
 ::= { sm48tat4xarpIPMCLIB 2 }

sm48tat4xarpMulticastFilteringProfileSettingEntry OBJECT-TYPE
    SYNTAX        SM48TAT4XARPMulticastFilteringProfileSettingEntry
    MAX-ACCESS    not-accessible
    STATUS        current
    DESCRIPTION
        "Multicast Filtering Profile Setting table."
    INDEX        { sm48tat4xarpMulticastFilteringProfileSettingIndex }
    ::= { sm48tat4xarpMulticastFilteringProfileSettingTable 1 }

SM48TAT4XARPMulticastFilteringProfileSettingEntry ::=
    SEQUENCE {
        sm48tat4xarpMulticastFilteringProfileSettingIndex               Integer32,
        sm48tat4xarpMulticastFilteringProfileSettingProfileName         DisplayString,
        sm48tat4xarpMulticastFilteringProfileSettingProfileDescription  DisplayString,
        sm48tat4xarpMulticastFilteringProfileSettingRowStatus           RowStatus
    }

sm48tat4xarpMulticastFilteringProfileSettingIndex OBJECT-TYPE
   SYNTAX      Integer32(1..65535)
   MAX-ACCESS  not-accessible
   STATUS      current
   DESCRIPTION
       "Multicast Filtering Profile Setting index."
   ::= {sm48tat4xarpMulticastFilteringProfileSettingEntry 1 }


sm48tat4xarpMulticastFilteringProfileSettingProfileName OBJECT-TYPE
   SYNTAX      DisplayString
   MAX-ACCESS  read-create
   STATUS      current
   DESCRIPTION
       "Profile Name. Length:1-16"
   ::= {sm48tat4xarpMulticastFilteringProfileSettingEntry 2 }

sm48tat4xarpMulticastFilteringProfileSettingProfileDescription OBJECT-TYPE
   SYNTAX      DisplayString
   MAX-ACCESS  read-create
   STATUS      current
   DESCRIPTION
       "Profile Description. Length:0-64"
   ::= {sm48tat4xarpMulticastFilteringProfileSettingEntry 3 }

sm48tat4xarpMulticastFilteringProfileSettingRowStatus OBJECT-TYPE
   SYNTAX      RowStatus
   MAX-ACCESS  read-create
   STATUS      current
   DESCRIPTION
       "Row Status."
   ::= {sm48tat4xarpMulticastFilteringProfileSettingEntry 4 }



sm48tat4xarpMulticastFilterProfRuleSettingsProfileNameIndex OBJECT-TYPE
   SYNTAX      DisplayString
   MAX-ACCESS  read-write
   STATUS      current
   DESCRIPTION
       "Set this Profile Name value before use MulticastFilteringProfileRuleSettingsTable table"
   ::= {     sm48tat4xarpIPMCLIB 3 }



sm48tat4xarpMulticastFilteringProfileRuleSettingsTable  OBJECT-TYPE
   SYNTAX      SEQUENCE OF SM48TAT4XARPMulticastFilteringProfileRuleSettingsEntry
   MAX-ACCESS  not-accessible
   STATUS      current
   DESCRIPTION
       "Multicast Filtering Profile Rule Setting table"
 ::= { sm48tat4xarpIPMCLIB 4 }

sm48tat4xarpMulticastFilteringProfileRuleSettingsEntry OBJECT-TYPE
    SYNTAX        SM48TAT4XARPMulticastFilteringProfileRuleSettingsEntry
    MAX-ACCESS    not-accessible
    STATUS        current
    DESCRIPTION
        "Multicast Filtering Profile Rule Setting table."
    INDEX        { sm48tat4xarpMulticastFilteringProfileRuleSettingsIndex }
    ::= { sm48tat4xarpMulticastFilteringProfileRuleSettingsTable 1 }

SM48TAT4XARPMulticastFilteringProfileRuleSettingsEntry ::=
    SEQUENCE {
        sm48tat4xarpMulticastFilteringProfileRuleSettingsTableIndex          Integer32,
        sm48tat4xarpMulticastFilteringProfileRuleSettingsProfileName         DisplayString,
        sm48tat4xarpMulticastFilteringProfileRuleSettingsIndex               Integer32,
        sm48tat4xarpMulticastFilteringProfileRuleSettingsEntryName           DisplayString,
        sm48tat4xarpMulticastFilteringProfileRuleSettingsAddressRange        DisplayString,
        sm48tat4xarpMulticastFilteringProfileRuleSettingsAction              Integer32,
        sm48tat4xarpMulticastFilteringProfileRuleSettingsLog                 Integer32,
        sm48tat4xarpMulticastFilteringProfileRuleSettingsRowStatus           RowStatus
    }

sm48tat4xarpMulticastFilteringProfileRuleSettingsTableIndex OBJECT-TYPE
   SYNTAX      Integer32
   MAX-ACCESS  not-accessible
   STATUS      current
   DESCRIPTION
       "Multicast Filtering Profile Rule Setting index."
   ::= {sm48tat4xarpMulticastFilteringProfileRuleSettingsEntry 1 }


sm48tat4xarpMulticastFilteringProfileRuleSettingsProfileName OBJECT-TYPE
   SYNTAX      DisplayString
   MAX-ACCESS  read-only
   STATUS      current
   DESCRIPTION
       "Profile Name"
   ::= {sm48tat4xarpMulticastFilteringProfileRuleSettingsEntry 2 }

sm48tat4xarpMulticastFilteringProfileRuleSettingsIndex OBJECT-TYPE
   SYNTAX      Integer32(1..65535)
   MAX-ACCESS  read-only
   STATUS      current
   DESCRIPTION
       "Index"
   ::= {sm48tat4xarpMulticastFilteringProfileRuleSettingsEntry 3 }

sm48tat4xarpMulticastFilteringProfileRuleSettingsEntryName OBJECT-TYPE
   SYNTAX      DisplayString
   MAX-ACCESS  read-create
   STATUS      current
   DESCRIPTION
       "Entry Name, Length: 1-16"
   ::= {sm48tat4xarpMulticastFilteringProfileRuleSettingsEntry 4 }

sm48tat4xarpMulticastFilteringProfileRuleSettingsAddressRange OBJECT-TYPE
   SYNTAX      DisplayString
   MAX-ACCESS  read-only
   STATUS      current
   DESCRIPTION
       "Address Range"
   ::= {sm48tat4xarpMulticastFilteringProfileRuleSettingsEntry 5 }


sm48tat4xarpMulticastFilteringProfileRuleSettingsAction OBJECT-TYPE
   SYNTAX      Integer32
   MAX-ACCESS  read-create
   STATUS      current
   DESCRIPTION
       "0:Deny
        1:Permit"
   ::= {sm48tat4xarpMulticastFilteringProfileRuleSettingsEntry 6 }

sm48tat4xarpMulticastFilteringProfileRuleSettingsLog OBJECT-TYPE
   SYNTAX      Integer32
   MAX-ACCESS  read-create
   STATUS      current
   DESCRIPTION
       "0:Disable
        1:Enable"
   ::= {sm48tat4xarpMulticastFilteringProfileRuleSettingsEntry 7 }


sm48tat4xarpMulticastFilteringProfileRuleSettingsRowStatus OBJECT-TYPE
   SYNTAX      RowStatus
   MAX-ACCESS  read-create
   STATUS      current
   DESCRIPTION
       "Row Status."
   ::= {sm48tat4xarpMulticastFilteringProfileRuleSettingsEntry 8 }


sm48tat4xarpMulticastFilteringProfileAddressConfigTable  OBJECT-TYPE
   SYNTAX      SEQUENCE OF SM48TAT4XARPMulticastFilteringProfileAddressConfigEntry
   MAX-ACCESS  not-accessible
   STATUS      current
   DESCRIPTION
       "Multicast Filtering Profile Address Config table"
 ::= { sm48tat4xarpIPMCLIB 5 }

sm48tat4xarpMulticastFilteringProfileAddressConfigEntry OBJECT-TYPE
    SYNTAX        SM48TAT4XARPMulticastFilteringProfileAddressConfigEntry
    MAX-ACCESS    not-accessible
    STATUS        current
    DESCRIPTION
        "Multicast Filtering Profile Address Config table."
    INDEX        { sm48tat4xarpMulticastFilteringProfileAddressConfigTableIndex }
    ::= { sm48tat4xarpMulticastFilteringProfileAddressConfigTable 1 }

SM48TAT4XARPMulticastFilteringProfileAddressConfigEntry ::=
    SEQUENCE {
        sm48tat4xarpMulticastFilteringProfileAddressConfigTableIndex     Integer32,
        sm48tat4xarpMulticastFilteringProfileAddressConfigEntryName      DisplayString,
        sm48tat4xarpMulticastFilteringProfileAddressConfigStartAddress   DisplayString,
        sm48tat4xarpMulticastFilteringProfileAddressConfigEndAddress     DisplayString,
        sm48tat4xarpMulticastFilteringProfileAddressConfigRowStatus      RowStatus
    }

sm48tat4xarpMulticastFilteringProfileAddressConfigTableIndex OBJECT-TYPE
   SYNTAX      Integer32(1..65535)
   MAX-ACCESS  not-accessible
   STATUS      current
   DESCRIPTION
       "Multicast Filtering Profile Address Config index."
   ::= {sm48tat4xarpMulticastFilteringProfileAddressConfigEntry 1 }


sm48tat4xarpMulticastFilteringProfileAddressConfigEntryName OBJECT-TYPE
   SYNTAX      DisplayString
   MAX-ACCESS  read-create
   STATUS      current
   DESCRIPTION
       "Entry Name, Length: 1-16"
   ::= {sm48tat4xarpMulticastFilteringProfileAddressConfigEntry 2 }

sm48tat4xarpMulticastFilteringProfileAddressConfigStartAddress OBJECT-TYPE
   SYNTAX      DisplayString
   MAX-ACCESS  read-create
   STATUS      current
   DESCRIPTION
       "IPv4/IPv6 Multicast Group Address"
   ::= {sm48tat4xarpMulticastFilteringProfileAddressConfigEntry 3 }

sm48tat4xarpMulticastFilteringProfileAddressConfigEndAddress OBJECT-TYPE
   SYNTAX      DisplayString
   MAX-ACCESS  read-create
   STATUS      current
   DESCRIPTION
       "IPv4/IPv6 Multicast Group Address"
   ::= {sm48tat4xarpMulticastFilteringProfileAddressConfigEntry 4 }

sm48tat4xarpMulticastFilteringProfileAddressConfigRowStatus OBJECT-TYPE
   SYNTAX      RowStatus
   MAX-ACCESS  read-create
   STATUS      current
   DESCRIPTION
       "Row Status."
   ::= {sm48tat4xarpMulticastFilteringProfileAddressConfigEntry 5 }

sm48tat4xarpEEE    OBJECT IDENTIFIER ::= { sm48tat4xarpConfiguration 35 }

sm48tat4xarpPortPowerSavings   OBJECT IDENTIFIER ::= { sm48tat4xarpEEE 1 }

sm48tat4xarpEnergyEfficientEthernetConfigTable OBJECT-TYPE
   SYNTAX      SEQUENCE OF SM48TAT4XARPEnergyEfficientEthernetConfigEntry
   MAX-ACCESS  not-accessible
   STATUS      current
   DESCRIPTION
       " "
   ::= { sm48tat4xarpPortPowerSavings 2 }

sm48tat4xarpEnergyEfficientEthernetConfigEntry OBJECT-TYPE
   SYNTAX      SM48TAT4XARPEnergyEfficientEthernetConfigEntry
   MAX-ACCESS  not-accessible
   STATUS      current
   DESCRIPTION
       " "
   INDEX    { sm48tat4xarpEnergyEfficientEthernetConfigPort  }
   ::= { sm48tat4xarpEnergyEfficientEthernetConfigTable 1 }

SM48TAT4XARPEnergyEfficientEthernetConfigEntry ::= SEQUENCE {
   sm48tat4xarpEnergyEfficientEthernetConfigPort           Integer32,
   sm48tat4xarpEnergyEfficientEthernetConfigPortConfig     Integer32
}

sm48tat4xarpEnergyEfficientEthernetConfigPort OBJECT-TYPE
   SYNTAX      Integer32(1..65535)
   MAX-ACCESS  not-accessible
   STATUS      current
   DESCRIPTION
       "Index"
   ::= { sm48tat4xarpEnergyEfficientEthernetConfigEntry 1 }

sm48tat4xarpEnergyEfficientEthernetConfigPortConfig OBJECT-TYPE
   SYNTAX      Integer32
   MAX-ACCESS  read-write
   STATUS      current
   DESCRIPTION
       "Controls whether EEE is enabled for this port.
       0:Disable
       1:Enable"
   ::= { sm48tat4xarpEnergyEfficientEthernetConfigEntry 2 }

-- =======================================================================================================================

sm48tat4xarpAggregation    OBJECT IDENTIFIER ::= { sm48tat4xarpConfiguration 36 }

sm48tat4xarpAggregationStatic    OBJECT IDENTIFIER ::= { sm48tat4xarpAggregation 1 }

sm48tat4xarpAggrSourceMACAddress   OBJECT-TYPE
               SYNTAX      Integer32 (0|1)
               MAX-ACCESS  read-write
               STATUS      current
               DESCRIPTION
                   "Source MAC Address"
               ::= { sm48tat4xarpAggregationStatic 2 }

sm48tat4xarpAggrDestinationMACAddress   OBJECT-TYPE
               SYNTAX      Integer32 (0|1)
               MAX-ACCESS  read-write
               STATUS      current
               DESCRIPTION
                   "Destination MAC Address"
               ::= { sm48tat4xarpAggregationStatic 3 }

sm48tat4xarpAggrIPAddress   OBJECT-TYPE
               SYNTAX      Integer32 (0|1)
               MAX-ACCESS  read-write
               STATUS      current
               DESCRIPTION
                   "IP Address"
               ::= { sm48tat4xarpAggregationStatic 4 }

sm48tat4xarpAggrTCPUDPPortNumber   OBJECT-TYPE
               SYNTAX      Integer32 (0|1)
               MAX-ACCESS  read-write
               STATUS      current
               DESCRIPTION
                   "TCP/UDP Port Number"
               ::= { sm48tat4xarpAggregationStatic 5 }


sm48tat4xarpAggrGroupConfigTable OBJECT-TYPE
   SYNTAX      SEQUENCE OF SM48TAT4XARPAggrGroupConfigEntry
   MAX-ACCESS  not-accessible
   STATUS      current
   DESCRIPTION
       " "
   ::= { sm48tat4xarpAggregationStatic 6 }

sm48tat4xarpAggrGroupConfigEntry OBJECT-TYPE
   SYNTAX      SM48TAT4XARPAggrGroupConfigEntry
   MAX-ACCESS  not-accessible
   STATUS      current
   DESCRIPTION
       " "
   INDEX    { sm48tat4xarpAggrGroupConfigPort  }
   ::= { sm48tat4xarpAggrGroupConfigTable 1 }

SM48TAT4XARPAggrGroupConfigEntry ::= SEQUENCE {
   sm48tat4xarpAggrGroupConfigPort                 Integer32,
   sm48tat4xarpAggrGroupConfigGroup                Integer32,
   sm48tat4xarpAggrGroupConfig                     Integer32
}

sm48tat4xarpAggrGroupConfigPort OBJECT-TYPE
   SYNTAX      Integer32(1..65535)
   MAX-ACCESS  not-accessible
   STATUS      current
   DESCRIPTION
       "port index"
   ::= { sm48tat4xarpAggrGroupConfigEntry 1 }

sm48tat4xarpAggrGroupConfigGroup OBJECT-TYPE
   SYNTAX      Integer32
   MAX-ACCESS  not-accessible
   STATUS      current
   DESCRIPTION
       "group index"
   ::= { sm48tat4xarpAggrGroupConfigEntry 2 }

sm48tat4xarpAggrGroupConfig OBJECT-TYPE
   SYNTAX      Integer32 (0|1)
   MAX-ACCESS  read-write
   STATUS      current
   DESCRIPTION
       "Aggregation Group Configuration"
   ::= { sm48tat4xarpAggrGroupConfigEntry 3 }

sm48tat4xarpLACPConfiguration    OBJECT IDENTIFIER ::= { sm48tat4xarpAggregation 2 }

sm48tat4xarpLACPPortConfigTable OBJECT-TYPE
   SYNTAX      SEQUENCE OF SM48TAT4XARPLACPPortConfigEntry
   MAX-ACCESS  not-accessible
   STATUS      current
   DESCRIPTION
       " "
   ::= { sm48tat4xarpLACPConfiguration 1 }

sm48tat4xarpLACPPortConfigEntry OBJECT-TYPE
   SYNTAX      SM48TAT4XARPLACPPortConfigEntry
   MAX-ACCESS  not-accessible
   STATUS      current
   DESCRIPTION
       " "
   INDEX    { sm48tat4xarpLACPPortConfigPort  }
   ::= { sm48tat4xarpLACPPortConfigTable 1 }

SM48TAT4XARPLACPPortConfigEntry ::= SEQUENCE {
   sm48tat4xarpLACPPortConfigPort                  Integer32,
   sm48tat4xarpLACPPortConfigEnabled               Integer32,
   sm48tat4xarpLACPPortConfigKey                   Integer32,
   sm48tat4xarpLACPPortConfigRole                  Integer32,
   sm48tat4xarpLACPPortConfigTimeout               Integer32,
   sm48tat4xarpLACPPortConfigPrio                  Integer32
}

sm48tat4xarpLACPPortConfigPort OBJECT-TYPE
   SYNTAX      Integer32(1..65535)
   MAX-ACCESS  not-accessible
   STATUS      current
   DESCRIPTION
       "port index"
   ::= { sm48tat4xarpLACPPortConfigEntry 1 }

sm48tat4xarpLACPPortConfigEnabled OBJECT-TYPE
   SYNTAX      Integer32 (0|1)
   MAX-ACCESS  read-write
   STATUS      current
   DESCRIPTION
       "Controls whether LACP is enabled on this switch port.
       0:Disable
       1:Enable"
   ::= { sm48tat4xarpLACPPortConfigEntry 2 }

sm48tat4xarpLACPPortConfigKey OBJECT-TYPE
   SYNTAX      Integer32
   MAX-ACCESS  read-write
   STATUS      current
   DESCRIPTION
       "The Key value incurred by the port, range 1-Number of link aggregations.
       0:autokey."
   ::= { sm48tat4xarpLACPPortConfigEntry 3 }

sm48tat4xarpLACPPortConfigRole OBJECT-TYPE
   SYNTAX      Integer32 (0|1)
   MAX-ACCESS  read-write
   STATUS      current
   DESCRIPTION
       "The Role shows the LACP activity status.
       0:Passive
       1:Active"
   ::= { sm48tat4xarpLACPPortConfigEntry 4 }

sm48tat4xarpLACPPortConfigTimeout OBJECT-TYPE
   SYNTAX      Integer32 (0|1)
   MAX-ACCESS  read-write
   STATUS      current
   DESCRIPTION
       "The Timeout controls the period between BPDU transmissions.
       0:Slow
       1:Fast"
   ::= { sm48tat4xarpLACPPortConfigEntry 5 }

sm48tat4xarpLACPPortConfigPrio OBJECT-TYPE
   SYNTAX      Integer32 (1..65535)
   MAX-ACCESS  read-write
   STATUS      current
   DESCRIPTION
       "The Prio controls the priority of the port."
   ::= { sm48tat4xarpLACPPortConfigEntry 6 }


sm48tat4xarpLacpSystemStatus    OBJECT IDENTIFIER ::= { sm48tat4xarpAggregation 3 }

sm48tat4xarpLacpSystemStatusTable OBJECT-TYPE
   SYNTAX      SEQUENCE OF SM48TAT4XARPLacpSystemStatusEntry
   MAX-ACCESS  not-accessible
   STATUS      current
   DESCRIPTION
       " "
   ::= { sm48tat4xarpLacpSystemStatus 1 }

sm48tat4xarpLacpSystemStatusEntry OBJECT-TYPE
   SYNTAX      SM48TAT4XARPLacpSystemStatusEntry
   MAX-ACCESS  not-accessible
   STATUS      current
   DESCRIPTION
       " "
   INDEX    { sm48tat4xarpLacpSystemStatusIndex  }
   ::= { sm48tat4xarpLacpSystemStatusTable 1 }

SM48TAT4XARPLacpSystemStatusEntry ::= SEQUENCE {
   sm48tat4xarpLacpSystemStatusIndex              Integer32,
   sm48tat4xarpLacpSystemStatusAggrID             DisplayString,
   sm48tat4xarpLacpSystemStatusPartnerSystemID    DisplayString,
   sm48tat4xarpLacpSystemStatusPartnerKey         DisplayString,
   sm48tat4xarpLacpSystemStatusPartnerPrio        DisplayString,
   sm48tat4xarpLacpSystemStatusLastChanged        DisplayString,
   sm48tat4xarpLacpSystemStatusLocalPorts         DisplayString
}

sm48tat4xarpLacpSystemStatusIndex OBJECT-TYPE
   SYNTAX      Integer32(1..65535)
   MAX-ACCESS  not-accessible
   STATUS      current
   DESCRIPTION
       "index"
   ::= { sm48tat4xarpLacpSystemStatusEntry 1 }

sm48tat4xarpLacpSystemStatusAggrID OBJECT-TYPE
   SYNTAX      DisplayString
   MAX-ACCESS  read-only
   STATUS      current
   DESCRIPTION
       "The Aggregation ID associated with this aggregation instance."
   ::= { sm48tat4xarpLacpSystemStatusEntry 2 }

sm48tat4xarpLacpSystemStatusPartnerSystemID OBJECT-TYPE
   SYNTAX      DisplayString
   MAX-ACCESS  read-only
   STATUS      current
   DESCRIPTION
       "The system ID (MAC address) of the aggregation partner."
   ::= { sm48tat4xarpLacpSystemStatusEntry 3 }

sm48tat4xarpLacpSystemStatusPartnerKey OBJECT-TYPE
   SYNTAX      DisplayString
   MAX-ACCESS  read-only
   STATUS      current
   DESCRIPTION
       "The Key that the partner has assigned to this aggregation ID."
   ::= { sm48tat4xarpLacpSystemStatusEntry 4 }

sm48tat4xarpLacpSystemStatusPartnerPrio OBJECT-TYPE
   SYNTAX      DisplayString
   MAX-ACCESS  read-only
   STATUS      current
   DESCRIPTION
       "The priority that the partner has assigned to this aggregation ID."
   ::= { sm48tat4xarpLacpSystemStatusEntry 5 }

sm48tat4xarpLacpSystemStatusLastChanged OBJECT-TYPE
   SYNTAX      DisplayString
   MAX-ACCESS  read-only
   STATUS      current
   DESCRIPTION
       "The time since this aggregation changed."
   ::= { sm48tat4xarpLacpSystemStatusEntry 6 }

sm48tat4xarpLacpSystemStatusLocalPorts OBJECT-TYPE
   SYNTAX      DisplayString
   MAX-ACCESS  read-only
   STATUS      current
   DESCRIPTION
       "Shows which ports are a part of this aggregation for this switch."
   ::= { sm48tat4xarpLacpSystemStatusEntry 7 }

sm48tat4xarpLACPInternalPortStatus    OBJECT IDENTIFIER ::= { sm48tat4xarpAggregation 4 }

sm48tat4xarpLACPInternalPortStatusTable OBJECT-TYPE
   SYNTAX      SEQUENCE OF SM48TAT4XARPLACPInternalPortStatusEntry
   MAX-ACCESS  not-accessible
   STATUS      current
   DESCRIPTION
       " "
   ::= { sm48tat4xarpLACPInternalPortStatus 1 }

sm48tat4xarpLACPInternalPortStatusEntry OBJECT-TYPE
   SYNTAX      SM48TAT4XARPLACPInternalPortStatusEntry
   MAX-ACCESS  not-accessible
   STATUS      current
   DESCRIPTION
       " "
   INDEX    { sm48tat4xarpLACPInternalPortStatusIndex  }
   ::= { sm48tat4xarpLACPInternalPortStatusTable 1 }

SM48TAT4XARPLACPInternalPortStatusEntry ::= SEQUENCE {
   sm48tat4xarpLACPInternalPortStatusIndex              Integer32,
   sm48tat4xarpLACPInternalPortStatusPort               DisplayString,
   sm48tat4xarpLACPInternalPortStatusState              DisplayString,
   sm48tat4xarpLACPInternalPortStatusKey                DisplayString,
   sm48tat4xarpLACPInternalPortStatusPriority           DisplayString,
   sm48tat4xarpLACPInternalPortStatusActivity           DisplayString,
   sm48tat4xarpLACPInternalPortStatusTimeout            DisplayString,
   sm48tat4xarpLACPInternalPortStatusAggregation        DisplayString,
   sm48tat4xarpLACPInternalPortStatusSynchronization    DisplayString,
   sm48tat4xarpLACPInternalPortStatusCollecting         DisplayString,
   sm48tat4xarpLACPInternalPortStatusDistributing       DisplayString,
   sm48tat4xarpLACPInternalPortStatusDefaulted          DisplayString,
   sm48tat4xarpLACPInternalPortStatusExpired            DisplayString
}

sm48tat4xarpLACPInternalPortStatusIndex OBJECT-TYPE
   SYNTAX      Integer32(1..65535)
   MAX-ACCESS  not-accessible
   STATUS      current
   DESCRIPTION
       "index"
   ::= { sm48tat4xarpLACPInternalPortStatusEntry 1 }

sm48tat4xarpLACPInternalPortStatusPort OBJECT-TYPE
   SYNTAX      DisplayString
   MAX-ACCESS  read-only
   STATUS      current
   DESCRIPTION
       "The switch port number."
   ::= { sm48tat4xarpLACPInternalPortStatusEntry 2 }

sm48tat4xarpLACPInternalPortStatusState OBJECT-TYPE
   SYNTAX      DisplayString
   MAX-ACCESS  read-only
   STATUS      current
   DESCRIPTION
       "The current port state:
        Down: The port is not active.
        Active: The port is in active state.
        Standby: The port is in standby state."
   ::= { sm48tat4xarpLACPInternalPortStatusEntry 3 }

sm48tat4xarpLACPInternalPortStatusKey OBJECT-TYPE
   SYNTAX      DisplayString
   MAX-ACCESS  read-only
   STATUS      current
   DESCRIPTION
       "The key assigned to this port. Only ports with the same key can aggregate together."
   ::= { sm48tat4xarpLACPInternalPortStatusEntry 4 }

sm48tat4xarpLACPInternalPortStatusPriority OBJECT-TYPE
   SYNTAX      DisplayString
   MAX-ACCESS  read-only
   STATUS      current
   DESCRIPTION
       "The priority assigned to this aggregation group."
   ::= { sm48tat4xarpLACPInternalPortStatusEntry 5 }

sm48tat4xarpLACPInternalPortStatusActivity OBJECT-TYPE
   SYNTAX      DisplayString
   MAX-ACCESS  read-only
   STATUS      current
   DESCRIPTION
       "The LACP mode of the group (Active or Passive)."
   ::= { sm48tat4xarpLACPInternalPortStatusEntry 6 }

sm48tat4xarpLACPInternalPortStatusTimeout OBJECT-TYPE
   SYNTAX      DisplayString
   MAX-ACCESS  read-only
   STATUS      current
   DESCRIPTION
       "The timeout mode configured for the port (Fast or Slow)."
   ::= { sm48tat4xarpLACPInternalPortStatusEntry 7 }

sm48tat4xarpLACPInternalPortStatusAggregation OBJECT-TYPE
   SYNTAX      DisplayString
   MAX-ACCESS  read-only
   STATUS      current
   DESCRIPTION
       "Show whether the system considers this link to be aggregateable. i.e., a potential candidate for aggregation."
   ::= { sm48tat4xarpLACPInternalPortStatusEntry 8 }

sm48tat4xarpLACPInternalPortStatusSynchronization OBJECT-TYPE
   SYNTAX      DisplayString
   MAX-ACCESS  read-only
   STATUS      current
   DESCRIPTION
       "Show whether the system considers this link to be IN_SYNC."
   ::= { sm48tat4xarpLACPInternalPortStatusEntry 9 }

sm48tat4xarpLACPInternalPortStatusCollecting OBJECT-TYPE
   SYNTAX      DisplayString
   MAX-ACCESS  read-only
   STATUS      current
   DESCRIPTION
       "Show if collection of incoming frames on this link is enabled."
   ::= { sm48tat4xarpLACPInternalPortStatusEntry 10 }

sm48tat4xarpLACPInternalPortStatusDistributing OBJECT-TYPE
   SYNTAX      DisplayString
   MAX-ACCESS  read-only
   STATUS      current
   DESCRIPTION
       "Show if distribution of outgoing frames on this link is enabled."
   ::= { sm48tat4xarpLACPInternalPortStatusEntry 11 }

sm48tat4xarpLACPInternalPortStatusDefaulted OBJECT-TYPE
   SYNTAX      DisplayString
   MAX-ACCESS  read-only
   STATUS      current
   DESCRIPTION
       "Show if the Actor's Receive machine is using Defaulted operational Partner information."
   ::= { sm48tat4xarpLACPInternalPortStatusEntry 12 }

sm48tat4xarpLACPInternalPortStatusExpired OBJECT-TYPE
   SYNTAX      DisplayString
   MAX-ACCESS  read-only
   STATUS      current
   DESCRIPTION
       "Show if that the Actor's Receive machine is in the EXPIRED state."
   ::= { sm48tat4xarpLACPInternalPortStatusEntry 13 }


sm48tat4xarpLACPNeighborPortStatus    OBJECT IDENTIFIER ::= { sm48tat4xarpAggregation 5 }

sm48tat4xarpLACPNeighborPortStatusTable OBJECT-TYPE
   SYNTAX      SEQUENCE OF SM48TAT4XARPLACPNeighborPortStatusEntry
   MAX-ACCESS  not-accessible
   STATUS      current
   DESCRIPTION
       " "
   ::= { sm48tat4xarpLACPNeighborPortStatus 1 }

sm48tat4xarpLACPNeighborPortStatusEntry OBJECT-TYPE
   SYNTAX      SM48TAT4XARPLACPNeighborPortStatusEntry
   MAX-ACCESS  not-accessible
   STATUS      current
   DESCRIPTION
       " "
   INDEX    { sm48tat4xarpLACPNeighborPortStatusIndex  }
   ::= { sm48tat4xarpLACPNeighborPortStatusTable 1 }

SM48TAT4XARPLACPNeighborPortStatusEntry ::= SEQUENCE {
   sm48tat4xarpLACPNeighborPortStatusIndex              Integer32,
   sm48tat4xarpLACPNeighborPortStatusPort               DisplayString,
   sm48tat4xarpLACPNeighborPortStatusState              DisplayString,
   sm48tat4xarpLACPNeighborPortStatusAggrID             DisplayString,
   sm48tat4xarpLACPNeighborPortStatusPartnerKey         DisplayString,
   sm48tat4xarpLACPNeighborPortStatusPartnerPort        DisplayString,
   sm48tat4xarpLACPNeighborPortStatusPartnerPortPrio    DisplayString,
   sm48tat4xarpLACPNeighborPortStatusActivity           DisplayString,
   sm48tat4xarpLACPNeighborPortStatusTimeout            DisplayString,
   sm48tat4xarpLACPNeighborPortStatusAggregation        DisplayString,
   sm48tat4xarpLACPNeighborPortStatusSynchronization    DisplayString,
   sm48tat4xarpLACPNeighborPortStatusCollecting         DisplayString,
   sm48tat4xarpLACPNeighborPortStatusDistributing       DisplayString,
   sm48tat4xarpLACPNeighborPortStatusDefaulted          DisplayString,
   sm48tat4xarpLACPNeighborPortStatusExpired            DisplayString
}

sm48tat4xarpLACPNeighborPortStatusIndex OBJECT-TYPE
   SYNTAX      Integer32(1..65535)
   MAX-ACCESS  not-accessible
   STATUS      current
   DESCRIPTION
       "index"
   ::= { sm48tat4xarpLACPNeighborPortStatusEntry 1 }

sm48tat4xarpLACPNeighborPortStatusPort OBJECT-TYPE
   SYNTAX      DisplayString
   MAX-ACCESS  read-only
   STATUS      current
   DESCRIPTION
       "The switch port number."
   ::= { sm48tat4xarpLACPNeighborPortStatusEntry 2 }

sm48tat4xarpLACPNeighborPortStatusState OBJECT-TYPE
   SYNTAX      DisplayString
   MAX-ACCESS  read-only
   STATUS      current
   DESCRIPTION
       "The current port state:
        Down: The port is not active.
        Active: The port is in active state.
        Standby: The port is in standby state."
   ::= { sm48tat4xarpLACPNeighborPortStatusEntry 3 }

sm48tat4xarpLACPNeighborPortStatusAggrID OBJECT-TYPE
   SYNTAX      DisplayString
   MAX-ACCESS  read-only
   STATUS      current
   DESCRIPTION
       "The aggregation group ID which the port is assigned to."
   ::= { sm48tat4xarpLACPNeighborPortStatusEntry 4 }

sm48tat4xarpLACPNeighborPortStatusPartnerKey OBJECT-TYPE
   SYNTAX      DisplayString
   MAX-ACCESS  read-only
   STATUS      current
   DESCRIPTION
       "The key assigned to this port by the partner."
   ::= { sm48tat4xarpLACPNeighborPortStatusEntry 5 }

sm48tat4xarpLACPNeighborPortStatusPartnerPort OBJECT-TYPE
   SYNTAX      DisplayString
   MAX-ACCESS  read-only
   STATUS      current
   DESCRIPTION
       "The partner port number associated with this link."
   ::= { sm48tat4xarpLACPNeighborPortStatusEntry 6 }

sm48tat4xarpLACPNeighborPortStatusPartnerPortPrio OBJECT-TYPE
   SYNTAX      DisplayString
   MAX-ACCESS  read-only
   STATUS      current
   DESCRIPTION
       "The priority assigned to this partner port ."
   ::= { sm48tat4xarpLACPNeighborPortStatusEntry 7 }

sm48tat4xarpLACPNeighborPortStatusActivity OBJECT-TYPE
   SYNTAX      DisplayString
   MAX-ACCESS  read-only
   STATUS      current
   DESCRIPTION
       "The LACP mode of the group (Active or Passive)."
   ::= { sm48tat4xarpLACPNeighborPortStatusEntry 8 }

sm48tat4xarpLACPNeighborPortStatusTimeout OBJECT-TYPE
   SYNTAX      DisplayString
   MAX-ACCESS  read-only
   STATUS      current
   DESCRIPTION
       "The timeout mode configured for the partner port (Fast or Slow)."
   ::= { sm48tat4xarpLACPNeighborPortStatusEntry 9 }

sm48tat4xarpLACPNeighborPortStatusAggregation OBJECT-TYPE
   SYNTAX      DisplayString
   MAX-ACCESS  read-only
   STATUS      current
   DESCRIPTION
       "Show whether the partner considers this link to be aggregateable."
   ::= { sm48tat4xarpLACPNeighborPortStatusEntry 10 }

sm48tat4xarpLACPNeighborPortStatusSynchronization OBJECT-TYPE
   SYNTAX      DisplayString
   MAX-ACCESS  read-only
   STATUS      current
   DESCRIPTION
       "Show whether the partner considers this link to be IN_SYNC"
   ::= { sm48tat4xarpLACPNeighborPortStatusEntry 11 }

sm48tat4xarpLACPNeighborPortStatusCollecting OBJECT-TYPE
   SYNTAX      DisplayString
   MAX-ACCESS  read-only
   STATUS      current
   DESCRIPTION
       "Show if collection of incoming frames on this link is enabled."
   ::= { sm48tat4xarpLACPNeighborPortStatusEntry 12 }

sm48tat4xarpLACPNeighborPortStatusDistributing OBJECT-TYPE
   SYNTAX      DisplayString
   MAX-ACCESS  read-only
   STATUS      current
   DESCRIPTION
       "Show if distribution of outgoing frames on this link is enabled."
   ::= { sm48tat4xarpLACPNeighborPortStatusEntry 13 }

sm48tat4xarpLACPNeighborPortStatusDefaulted OBJECT-TYPE
   SYNTAX      DisplayString
   MAX-ACCESS  read-only
   STATUS      current
   DESCRIPTION
       "Show if the partners Receive machine is using Defaulted operational Partner information."
   ::= { sm48tat4xarpLACPNeighborPortStatusEntry 14 }

sm48tat4xarpLACPNeighborPortStatusExpired OBJECT-TYPE
   SYNTAX      DisplayString
   MAX-ACCESS  read-only
   STATUS      current
   DESCRIPTION
       "Show if that the partners Receive machine is in the EXPIRED state."
   ::= { sm48tat4xarpLACPNeighborPortStatusEntry 15 }


sm48tat4xarpLACPStatus    OBJECT IDENTIFIER ::= { sm48tat4xarpAggregation 6 }

sm48tat4xarpLACPStatusTable OBJECT-TYPE
   SYNTAX      SEQUENCE OF SM48TAT4XARPLACPStatusEntry
   MAX-ACCESS  not-accessible
   STATUS      current
   DESCRIPTION
       " "
   ::= { sm48tat4xarpLACPStatus 1 }

sm48tat4xarpLACPStatusEntry OBJECT-TYPE
   SYNTAX      SM48TAT4XARPLACPStatusEntry
   MAX-ACCESS  not-accessible
   STATUS      current
   DESCRIPTION
       " "
   INDEX    { sm48tat4xarpLACPStatusPort  }
   ::= { sm48tat4xarpLACPStatusTable 1 }

SM48TAT4XARPLACPStatusEntry ::= SEQUENCE {
   sm48tat4xarpLACPStatusPort               Integer32,
   sm48tat4xarpLACPStatusLACP               DisplayString,
   sm48tat4xarpLACPStatusKey                DisplayString,
   sm48tat4xarpLACPStatusAggrID             DisplayString,
   sm48tat4xarpLACPStatusPartnerSystemID    DisplayString,
   sm48tat4xarpLACPStatusPartnerPort        DisplayString,
   sm48tat4xarpLACPStatusPartnerPrio        DisplayString
}

sm48tat4xarpLACPStatusPort OBJECT-TYPE
   SYNTAX      Integer32(1..65535)
   MAX-ACCESS  not-accessible
   STATUS      current
   DESCRIPTION
       "index"
   ::= { sm48tat4xarpLACPStatusEntry 1 }

sm48tat4xarpLACPStatusLACP OBJECT-TYPE
   SYNTAX      DisplayString
   MAX-ACCESS  read-only
   STATUS      current
   DESCRIPTION
       "Yes: means that LACP is enabled and the port link is up.
       No: means that LACP is not enabled or that the port link is down.
       Backup: means that the port could not join the aggregation group but will join if other port leaves. Meanwhile it's LACP status is disabled."
   ::= { sm48tat4xarpLACPStatusEntry 2 }

sm48tat4xarpLACPStatusKey OBJECT-TYPE
   SYNTAX      DisplayString
   MAX-ACCESS  read-only
   STATUS      current
   DESCRIPTION
       "The key assigned to this port. Only ports with the same key can aggregate together."
   ::= { sm48tat4xarpLACPStatusEntry 3 }

sm48tat4xarpLACPStatusAggrID OBJECT-TYPE
   SYNTAX      DisplayString
   MAX-ACCESS  read-only
   STATUS      current
   DESCRIPTION
       "The Aggregation ID assigned to this aggregation group."
   ::= { sm48tat4xarpLACPStatusEntry 4 }

sm48tat4xarpLACPStatusPartnerSystemID OBJECT-TYPE
   SYNTAX      DisplayString
   MAX-ACCESS  read-only
   STATUS      current
   DESCRIPTION
       "The partner's System ID (MAC address)."
   ::= { sm48tat4xarpLACPStatusEntry 5 }

sm48tat4xarpLACPStatusPartnerPort OBJECT-TYPE
   SYNTAX      DisplayString
   MAX-ACCESS  read-only
   STATUS      current
   DESCRIPTION
       "The partner's port number connected to this port."
   ::= { sm48tat4xarpLACPStatusEntry 6 }

sm48tat4xarpLACPStatusPartnerPrio OBJECT-TYPE
   SYNTAX      DisplayString
   MAX-ACCESS  read-only
   STATUS      current
   DESCRIPTION
       "The partner's port priority."
   ::= { sm48tat4xarpLACPStatusEntry 7 }

sm48tat4xarpAggrGroupStateTable OBJECT-TYPE
   SYNTAX      SEQUENCE OF SM48TAT4XARPAggrGroupStateEntry
   MAX-ACCESS  not-accessible
   STATUS      current
   DESCRIPTION
       " "
   ::= { sm48tat4xarpAggregation 7 }

sm48tat4xarpAggrGroupStateEntry OBJECT-TYPE
   SYNTAX      SM48TAT4XARPAggrGroupStateEntry
   MAX-ACCESS  not-accessible
   STATUS      current
   DESCRIPTION
       " "
   INDEX    { sm48tat4xarpAggrGroupStateIndex  }
   ::= { sm48tat4xarpAggrGroupStateTable 1 }

SM48TAT4XARPAggrGroupStateEntry ::= SEQUENCE {
   sm48tat4xarpAggrGroupStateIndex             Integer32,
   sm48tat4xarpAggrGroupStateAggrID            DisplayString,
   sm48tat4xarpAggrGroupStateName              DisplayString,
   sm48tat4xarpAggrGroupStateType              DisplayString,
   sm48tat4xarpAggrGroupStateSpeed             DisplayString,
   sm48tat4xarpAggrGroupStateConfiguredPorts   DisplayString,
   sm48tat4xarpAggrGroupStateAggregatedPorts   DisplayString,
   sm48tat4xarpAggrGroupStateAggregatedBandwidth   DisplayString
}

sm48tat4xarpAggrGroupStateIndex OBJECT-TYPE
   SYNTAX      Integer32(1..65535)
   MAX-ACCESS  not-accessible
   STATUS      current
   DESCRIPTION
       "index"
   ::= { sm48tat4xarpAggrGroupStateEntry 1 }

sm48tat4xarpAggrGroupStateAggrID OBJECT-TYPE
   SYNTAX      DisplayString
   MAX-ACCESS  read-only
   STATUS      current
   DESCRIPTION
       "AggrID"
   ::= { sm48tat4xarpAggrGroupStateEntry 2 }

sm48tat4xarpAggrGroupStateName OBJECT-TYPE
   SYNTAX      DisplayString
   MAX-ACCESS  read-only
   STATUS      current
   DESCRIPTION
       "Name"
   ::= { sm48tat4xarpAggrGroupStateEntry 3 }

sm48tat4xarpAggrGroupStateType OBJECT-TYPE
   SYNTAX      DisplayString
   MAX-ACCESS  read-only
   STATUS      current
   DESCRIPTION
       "Type"
   ::= { sm48tat4xarpAggrGroupStateEntry 4 }

sm48tat4xarpAggrGroupStateSpeed OBJECT-TYPE
   SYNTAX      DisplayString
   MAX-ACCESS  read-only
   STATUS      current
   DESCRIPTION
       "Speed"
   ::= { sm48tat4xarpAggrGroupStateEntry 5 }

sm48tat4xarpAggrGroupStateConfiguredPorts OBJECT-TYPE
   SYNTAX      DisplayString
   MAX-ACCESS  read-only
   STATUS      current
   DESCRIPTION
       "Configured Ports"
   ::= { sm48tat4xarpAggrGroupStateEntry 6 }

sm48tat4xarpAggrGroupStateAggregatedPorts OBJECT-TYPE
   SYNTAX      DisplayString
   MAX-ACCESS  read-only
   STATUS      current
   DESCRIPTION
       "Aggregated Ports"
   ::= { sm48tat4xarpAggrGroupStateEntry 7 }

sm48tat4xarpAggrGroupStateAggregatedBandwidth OBJECT-TYPE
   SYNTAX      DisplayString
   MAX-ACCESS  read-only
   STATUS      current
   DESCRIPTION
       "Aggregated Bandwidth"
   ::= { sm48tat4xarpAggrGroupStateEntry 8 }

-- =======================================================================================================================
sm48tat4xarpSecurity                                              OBJECT IDENTIFIER ::= { sm48tat4xarpProductId 3 }

sm48tat4xarpIPSourceGuard                                         OBJECT IDENTIFIER ::= { sm48tat4xarpSecurity 1 }

sm48tat4xarpIPSourceGuardConf                                     OBJECT IDENTIFIER ::= { sm48tat4xarpIPSourceGuard 1 }

-- RowStatus Info:  createAndGo, notReady not supported.
-- =======================================================================================================================
-- Textual Conventions for the SM48TAT4XARP IP Source Guard Mib
-- =======================================================================================================================
--
--    sm48tat4xarpIPSourceGuard        OBJECT IDENTIFIER  ::= { sm48tat4xarpIPSourceGuardMIB 1 }
--    sm48tat4xarpIPSourceGuardConf    OBJECT IDENTIFIER  ::= { sm48tat4xarpIPSourceGuard 1 }

--
-- =======================================================================================================================
-- Start sm48tat4xarpIPSourceGuard group
-- =======================================================================================================================
--sm48tat4xarpIPSourceGuardConf

    sm48tat4xarpIPSourceGuardMode OBJECT-TYPE
               SYNTAX      AdminMode
               MAX-ACCESS  read-write
               STATUS      current
               DESCRIPTION
                   "Enable the Global IP Source Guard or disable the
                    Global IP Source Guard."
               ::= {     sm48tat4xarpIPSourceGuardConf 1 }

    sm48tat4xarpIPSourceGuardDynamicToStaticCmd OBJECT-TYPE
               SYNTAX      ActivateCmd
               MAX-ACCESS  read-write
               STATUS      current
               DESCRIPTION
                   "Translate all dynamic entries to static entries."
               DEFVAL  { noAction }
               ::= {     sm48tat4xarpIPSourceGuardConf 2 }

--sm48tat4xarpIPSourceGuardPortConfigTable

    sm48tat4xarpIPSourceGuardPortConfigTable OBJECT-TYPE
               SYNTAX      SEQUENCE OF     SM48TAT4XARPIPSourceGuardPortConfigEntry
               MAX-ACCESS  not-accessible
               STATUS      current
               DESCRIPTION
                   "The IP Source Guard Port Configuration Table.
                    INDEX for this table is ifIndex which is
                    equivalent to the panel port number."
               ::= {     sm48tat4xarpIPSourceGuardConf 3 }

    sm48tat4xarpIPSourceGuardPortConfigEntry OBJECT-TYPE
               SYNTAX          SM48TAT4XARPIPSourceGuardPortConfigEntry
               MAX-ACCESS  not-accessible
               STATUS      current
               DESCRIPTION
                   "The IP Source Guard Port Configuration Entry."
               INDEX    {    ifIndex  }
               ::= {     sm48tat4xarpIPSourceGuardPortConfigTable 1 }

    SM48TAT4XARPIPSourceGuardPortConfigEntry             ::= SEQUENCE {
                 sm48tat4xarpIPSourceGuardPortConfigMode            AdminMode,
                 sm48tat4xarpIPSourceGuardPortMaxDynamicClients     Integer32
                 }

    sm48tat4xarpIPSourceGuardPortConfigMode OBJECT-TYPE
               SYNTAX      AdminMode
               MAX-ACCESS  read-write
               STATUS      current
               DESCRIPTION
                   "Specify IP Source Guard is enabled on which ports."
               ::= {     sm48tat4xarpIPSourceGuardPortConfigEntry 2 }

    sm48tat4xarpIPSourceGuardPortMaxDynamicClients OBJECT-TYPE
               SYNTAX      Integer32(0..2|99)
               MAX-ACCESS  read-write
               STATUS      current
               DESCRIPTION
                   "Specify the maximum number of dynamic clients that can
                    be learned on given port.
                    default: 99
                    0~2: Max Dynamic clients
                    99:Unlimited "
               ::= {     sm48tat4xarpIPSourceGuardPortConfigEntry 3 }

--sm48tat4xarpIPSourceGuardStaticTable

    sm48tat4xarpIPSourceGuardStaticTable OBJECT-TYPE
               SYNTAX      SEQUENCE OF     SM48TAT4XARPIPSourceGuardStaticEntry
               MAX-ACCESS  not-accessible
               STATUS      current
               DESCRIPTION
                   "The IP Source Guard Static Table."
               ::= {     sm48tat4xarpIPSourceGuard 2 }

    sm48tat4xarpIPSourceGuardStaticEntry OBJECT-TYPE
               SYNTAX          SM48TAT4XARPIPSourceGuardStaticEntry
               MAX-ACCESS  not-accessible
               STATUS      current
               DESCRIPTION
                   "The IP Source Guard Static Entry."
               INDEX    {    sm48tat4xarpIPSourceGuardStaticIndex  }
               ::= {     sm48tat4xarpIPSourceGuardStaticTable 1 }

    SM48TAT4XARPIPSourceGuardStaticEntry             ::= SEQUENCE {
                 sm48tat4xarpIPSourceGuardStaticSwitchIndex   Integer32,
                 sm48tat4xarpIPSourceGuardStaticIndex         Integer32,
                 sm48tat4xarpIPSourceGuardStaticPort          Integer32,
                 sm48tat4xarpIPSourceGuardStaticVLANId        Integer32,
                 sm48tat4xarpIPSourceGuardStaticIPAddress     IpAddress,
--                 sm48tat4xarpIPSourceGuardStaticIPMask        IpAddress,
                 sm48tat4xarpIPSourceGuardStaticMACAddress    DisplayString,
                 sm48tat4xarpIPSourceGuardStaticRowStatus     RowStatus
                 }

    sm48tat4xarpIPSourceGuardStaticSwitchIndex OBJECT-TYPE
               SYNTAX      Integer32(1..16)
               MAX-ACCESS  not-accessible
               STATUS      current
               DESCRIPTION
                   "Switch Index."
               ::= {     sm48tat4xarpIPSourceGuardStaticEntry 1 }

    sm48tat4xarpIPSourceGuardStaticIndex OBJECT-TYPE
               SYNTAX      Integer32(1..28)
               MAX-ACCESS  not-accessible
               STATUS      current
               DESCRIPTION
                   "The entry of table."
               ::= {     sm48tat4xarpIPSourceGuardStaticEntry 2 }

    sm48tat4xarpIPSourceGuardStaticPort OBJECT-TYPE
               SYNTAX      Integer32(1..255)
               MAX-ACCESS  read-create
               STATUS      current
               DESCRIPTION
                   "The port number of table.
                    range: 1 - port number."
               ::= {     sm48tat4xarpIPSourceGuardStaticEntry 3 }

    sm48tat4xarpIPSourceGuardStaticVLANId OBJECT-TYPE
               SYNTAX      Integer32(1..4095)
               MAX-ACCESS  read-create
               STATUS      current
               DESCRIPTION
                   "VLAN ID, range: 1 - 4095."
               ::= {     sm48tat4xarpIPSourceGuardStaticEntry 4 }

    sm48tat4xarpIPSourceGuardStaticIPAddress OBJECT-TYPE
               SYNTAX      IpAddress
               MAX-ACCESS  read-create
               STATUS      current
               DESCRIPTION
                   "IP address allowed for doing IP source guard."
               ::= {     sm48tat4xarpIPSourceGuardStaticEntry 5 }

--    sm48tat4xarpIPSourceGuardStaticIPMask OBJECT-TYPE
--               SYNTAX      IpAddress
--               MAX-ACCESS  read-create
--               STATUS      current
--               DESCRIPTION
--                   "IP Mask allowed for doing IP source guard."
--               ::= {     sm48tat4xarpIPSourceGuardStaticEntry 6 }

    sm48tat4xarpIPSourceGuardStaticMACAddress OBJECT-TYPE
               SYNTAX      DisplayString
               MAX-ACCESS  read-create
               STATUS      current
               DESCRIPTION
                   "Allowed Source MAC address, format: 0a 1b 2c 3d 4e 5f."
               ::= {     sm48tat4xarpIPSourceGuardStaticEntry 7 }

    sm48tat4xarpIPSourceGuardStaticRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sm48tat4xarpIPSourceGuardStaticEntry 8 }

--sm48tat4xarpIPSourceGuardDynamicTable

    sm48tat4xarpIPSourceGuardDynamicTable OBJECT-TYPE
               SYNTAX      SEQUENCE OF     SM48TAT4XARPIPSourceGuardDynamicEntry
               MAX-ACCESS  not-accessible
               STATUS      current
               DESCRIPTION
                   "The IP Source Guard Dynamic Table."
               ::= {     sm48tat4xarpIPSourceGuard 3 }

    sm48tat4xarpIPSourceGuardDynamicEntry OBJECT-TYPE
               SYNTAX          SM48TAT4XARPIPSourceGuardDynamicEntry
               MAX-ACCESS  not-accessible
               STATUS      current
               DESCRIPTION
                   "The IP Source Guard Dynamic Entry."
               INDEX    {    sm48tat4xarpIPSourceGuardDynamicIndex  }
               ::= {     sm48tat4xarpIPSourceGuardDynamicTable 1 }

    SM48TAT4XARPIPSourceGuardDynamicEntry             ::= SEQUENCE {
                 sm48tat4xarpIPSourceGuardDynamicSwitchIndex    Integer32,
                 sm48tat4xarpIPSourceGuardDynamicIndex          Integer32,
                 sm48tat4xarpIPSourceGuardDynamicPort           Integer32,
                 sm48tat4xarpIPSourceGuardDynamicVLANId         Integer32,
                 sm48tat4xarpIPSourceGuardDynamicIPAddress      IpAddress,
                 sm48tat4xarpIPSourceGuardDynamicMACAddress     DisplayString
                 }

    sm48tat4xarpIPSourceGuardDynamicSwitchIndex OBJECT-TYPE
               SYNTAX      Integer32(1..16)
               MAX-ACCESS  not-accessible
               STATUS      current
               DESCRIPTION
                   "Switch Index."
               ::= {     sm48tat4xarpIPSourceGuardDynamicEntry 1 }

    sm48tat4xarpIPSourceGuardDynamicIndex OBJECT-TYPE
               SYNTAX      Integer32(1..4095)
               MAX-ACCESS  not-accessible
               STATUS      current
               DESCRIPTION
                   "The entry of table."
               ::= {     sm48tat4xarpIPSourceGuardDynamicEntry 2 }

    sm48tat4xarpIPSourceGuardDynamicPort OBJECT-TYPE
               SYNTAX      Integer32(1..255)
               MAX-ACCESS  read-only
               STATUS      current
               DESCRIPTION
                   "The logical port for the settings."
               ::= {     sm48tat4xarpIPSourceGuardDynamicEntry 3 }

    sm48tat4xarpIPSourceGuardDynamicVLANId OBJECT-TYPE
               SYNTAX      Integer32(1..4094)
               MAX-ACCESS  read-only
               STATUS      current
               DESCRIPTION
                   "The vlan id for the settings."
               ::= {     sm48tat4xarpIPSourceGuardDynamicEntry 4 }

    sm48tat4xarpIPSourceGuardDynamicIPAddress OBJECT-TYPE
               SYNTAX      IpAddress
               MAX-ACCESS  read-only
               STATUS      current
               DESCRIPTION
                   "Allowed Source IP address."
               ::= {     sm48tat4xarpIPSourceGuardDynamicEntry 5 }

    sm48tat4xarpIPSourceGuardDynamicMACAddress OBJECT-TYPE
               SYNTAX      DisplayString
               MAX-ACCESS  read-only
               STATUS      current
               DESCRIPTION
                   "Allowed Source MAC address."
               ::= {     sm48tat4xarpIPSourceGuardDynamicEntry 6 }
-- =======================================================================================================================
sm48tat4xarpARPInspection                                          OBJECT IDENTIFIER ::= { sm48tat4xarpSecurity 2 }
-- RowStatus Info:  createAndGo, notReady not supported.
-- =======================================================================================================================
-- Textual Conventions for the sm48tat4xarp Arp Mib
-- =======================================================================================================================
--
    sm48tat4xarpARP                  OBJECT IDENTIFIER  ::= { sm48tat4xarpARPInspection 1 }
    sm48tat4xarpARPConfig            OBJECT IDENTIFIER  ::= { sm48tat4xarpARP 1 }

--
-- =======================================================================================================================
-- Start sm48tat4xarpARP group
-- =======================================================================================================================
--sm48tat4xarpARPConfig

    sm48tat4xarpARPConfMode OBJECT-TYPE
               SYNTAX      AdminMode
               MAX-ACCESS  read-write
               STATUS      current
               DESCRIPTION
                   "Enable the Global ARP Inspection or disable the Global
                    ARP Inspection."
               ::= {     sm48tat4xarpARPConfig 1 }

--sm48tat4xarpARPPortConfTable

    sm48tat4xarpARPPortConfTable OBJECT-TYPE
               SYNTAX      SEQUENCE OF     SM48TAT4XARPARPPortConfEntry
               MAX-ACCESS  not-accessible
               STATUS      current
               DESCRIPTION
                   "The ARP Port Configuration Table."
               ::= {     sm48tat4xarpARPConfig 3 }

    sm48tat4xarpARPPortConfEntry OBJECT-TYPE
               SYNTAX          SM48TAT4XARPARPPortConfEntry
               MAX-ACCESS  not-accessible
               STATUS      current
               DESCRIPTION
                   "The ARP Port Configuration Entry."
               INDEX    {    sm48tat4xarpARPPortConfPort  }
               ::= {     sm48tat4xarpARPPortConfTable 1 }

    SM48TAT4XARPARPPortConfEntry             ::= SEQUENCE {
                 sm48tat4xarpARPPortConfPort            Integer32,
                 sm48tat4xarpARPPortConfMode            AdminMode,
                 sm48tat4xarpARPPortConfCheckVLAN       AdminMode,
                 sm48tat4xarpARPPortConfLogType         INTEGER
                 }

    sm48tat4xarpARPPortConfPort OBJECT-TYPE
               SYNTAX      Integer32(1..255)
               MAX-ACCESS  not-accessible
               STATUS      current
               DESCRIPTION
                   "The port number for which the configuration below applies.
                    range: 1 - port number."
               ::= {     sm48tat4xarpARPPortConfEntry 1 }

    sm48tat4xarpARPPortConfMode OBJECT-TYPE
               SYNTAX      AdminMode
               MAX-ACCESS  read-write
               STATUS      current
               DESCRIPTION
                   "Specify ARP Inspection is enabled on which ports."
               ::= {     sm48tat4xarpARPPortConfEntry 2 }

    sm48tat4xarpARPPortConfCheckVLAN OBJECT-TYPE
               SYNTAX      AdminMode
               MAX-ACCESS  read-write
               STATUS      current
               DESCRIPTION
                   "When the setting of 'Check VLAN' is disabled, the log
                   type of ARP Inspection will refer to the port setting.
                   And the setting of 'Check VLAN' is enabled, the log type
                   of ARP Inspection will refer to the VLAN setting."
               ::= {     sm48tat4xarpARPPortConfEntry 3 }

    sm48tat4xarpARPPortConfLogType OBJECT-TYPE
               SYNTAX      INTEGER{none(0),deny(1),permit(2),all(3)}
               MAX-ACCESS  read-write
               STATUS      current
               DESCRIPTION
                   "The log type of ARP Inspection will refer to the
                    port setting.
                    0: none,
                    1: deny,
                    2: permit,
                    3: all,
                    range: 0-3."
               ::= {     sm48tat4xarpARPPortConfEntry 4 }

--sm48tat4xarpARPVlanConfig

    sm48tat4xarpARPVlanConfigTable OBJECT-TYPE
               SYNTAX      SEQUENCE OF     SM48TAT4XARPARPVlanConfigEntry
               MAX-ACCESS  not-accessible
               STATUS      current
               DESCRIPTION
                   "The ARP Vlan Configuration Table."
               ::= {     sm48tat4xarpARP 2 }

    sm48tat4xarpARPVlanConfigEntry OBJECT-TYPE
               SYNTAX          SM48TAT4XARPARPVlanConfigEntry
               MAX-ACCESS  not-accessible
               STATUS      current
               DESCRIPTION
                   "The ARP Vlan Configuration Entry."
               INDEX    {    sm48tat4xarpARPVlanConfigVlan  }
               ::= {     sm48tat4xarpARPVlanConfigTable 1 }

    SM48TAT4XARPARPVlanConfigEntry             ::= SEQUENCE {
                 sm48tat4xarpARPPortConfigIndex      Integer32,
                 sm48tat4xarpARPVlanConfigVlan       Integer32,
                 sm48tat4xarpARPVlanConfigLogType    INTEGER,
                 sm48tat4xarpARPVlanConfigRowStatus  RowStatus
                 }

    sm48tat4xarpARPPortConfigIndex OBJECT-TYPE
               SYNTAX      Integer32(1..4095)
               MAX-ACCESS  not-accessible
               STATUS      current
               DESCRIPTION
                   "The Index of Vlan config Table"
               ::= {     sm48tat4xarpARPVlanConfigEntry 1 }

    sm48tat4xarpARPVlanConfigVlan OBJECT-TYPE
               SYNTAX      Integer32(1..4095)
               MAX-ACCESS  read-create
               STATUS      current
               DESCRIPTION
                   "Specify ARP Inspection is enabled on which VLANs.
                    range: 1 - 4095."
               ::= {     sm48tat4xarpARPVlanConfigEntry 2 }

    sm48tat4xarpARPVlanConfigLogType OBJECT-TYPE
               SYNTAX      INTEGER{none(0),deny(1),permit(2),all(3)}
               MAX-ACCESS  read-create
               STATUS      current
               DESCRIPTION
                   "The log type also can be configured on per VLAN setting.
                    0: none,
                    1: deny,
                    2: permit,
                    3: all,
                    range: 0-3."
               ::= {     sm48tat4xarpARPVlanConfigEntry 3 }

    sm48tat4xarpARPVlanConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sm48tat4xarpARPVlanConfigEntry 4 }

--sm48tat4xarpARPStaticTable

    sm48tat4xarpARPStaticTable OBJECT-TYPE
               SYNTAX      SEQUENCE OF     SM48TAT4XARPARPStaticEntry
               MAX-ACCESS  not-accessible
               STATUS      current
               DESCRIPTION
                   "The ARP Static Table."
               ::= {     sm48tat4xarpARP 3 }

    sm48tat4xarpARPStaticEntry OBJECT-TYPE
               SYNTAX          SM48TAT4XARPARPStaticEntry
               MAX-ACCESS  not-accessible
               STATUS      current
               DESCRIPTION
                   "The ARP Static Entry."
               INDEX    {    sm48tat4xarpARPStaticIndex  }
               ::= {     sm48tat4xarpARPStaticTable 1 }

    SM48TAT4XARPARPStaticEntry             ::= SEQUENCE {
                 sm48tat4xarpARPStaticSwitchIndex   Integer32,
                 sm48tat4xarpARPStaticIndex         Integer32,
                 sm48tat4xarpARPStaticPort          Integer32,
                 sm48tat4xarpARPStaticVlanID        Integer32,
                 sm48tat4xarpARPStaticMACAddress    DisplayString,
                 sm48tat4xarpARPStaticIPAddress     IpAddress,
                 sm48tat4xarpARPStaticRowStatus     RowStatus
                 }


    sm48tat4xarpARPStaticSwitchIndex OBJECT-TYPE
               SYNTAX      Integer32(1..16)
               MAX-ACCESS  not-accessible
               STATUS      current
               DESCRIPTION
                   "Switch Index."
               ::= {     sm48tat4xarpARPStaticEntry 1 }

    sm48tat4xarpARPStaticIndex OBJECT-TYPE
               SYNTAX      Integer32(1..255)
               MAX-ACCESS  not-accessible
               STATUS      current
               DESCRIPTION
                   "The entry of table."
               ::= {     sm48tat4xarpARPStaticEntry 2 }

    sm48tat4xarpARPStaticPort OBJECT-TYPE
               SYNTAX      Integer32(1..255)
               MAX-ACCESS  read-create
               STATUS      current
               DESCRIPTION
                   "The logical port for the settings.
                    range: 1 - port number."
               ::= {     sm48tat4xarpARPStaticEntry 3 }

    sm48tat4xarpARPStaticVlanID OBJECT-TYPE
               SYNTAX      Integer32(1..4095)
               MAX-ACCESS  read-create
               STATUS      current
               DESCRIPTION
                   "The vlan id for the settings.
                    range: 1-4095."
               ::= {     sm48tat4xarpARPStaticEntry 4 }

    sm48tat4xarpARPStaticMACAddress OBJECT-TYPE
               SYNTAX      DisplayString
               MAX-ACCESS  read-create
               STATUS      current
               DESCRIPTION
                   "Allowed Source MAC address in ARP request packets."
               ::= {     sm48tat4xarpARPStaticEntry 5 }

    sm48tat4xarpARPStaticIPAddress OBJECT-TYPE
               SYNTAX      IpAddress
               MAX-ACCESS  read-create
               STATUS      current
               DESCRIPTION
                   "Allowed Source IP address in ARP request packets."
               ::= {     sm48tat4xarpARPStaticEntry 6 }

    sm48tat4xarpARPStaticRowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sm48tat4xarpARPStaticEntry 7 }

--sm48tat4xarpARPDynamicTable

    sm48tat4xarpARPDynamicTable OBJECT-TYPE
               SYNTAX      SEQUENCE OF     SM48TAT4XARPARPDynamicEntry
               MAX-ACCESS  not-accessible
               STATUS      current
               DESCRIPTION
                   "The ARP Dynamic Table."
               ::= {    sm48tat4xarpARP 4 }

    sm48tat4xarpARPDynamicEntry OBJECT-TYPE
               SYNTAX          SM48TAT4XARPARPDynamicEntry
               MAX-ACCESS  not-accessible
               STATUS      current
               DESCRIPTION
                   "The ARP Dynamic Entry."
               INDEX    {   sm48tat4xarpARPDynamicIndex  }
               ::= {    sm48tat4xarpARPDynamicTable 1 }

    SM48TAT4XARPARPDynamicEntry             ::= SEQUENCE {
                 sm48tat4xarpARPDynamicIndex          Integer32,
                 sm48tat4xarpARPDynamicPort           Integer32,
                 sm48tat4xarpARPDynamicVLANId         Integer32,
                 sm48tat4xarpARPDynamicMACAddress     MacAddress,
                 sm48tat4xarpARPDynamicIPAddress      IpAddress,
                 sm48tat4xarpARPDynamicToStaticCmd    INTEGER
                 }

    sm48tat4xarpARPDynamicIndex OBJECT-TYPE
               SYNTAX      Integer32(1..4095)
               MAX-ACCESS  not-accessible
               STATUS      current
               DESCRIPTION
                   "The entry of table."
               ::= {    sm48tat4xarpARPDynamicEntry 1 }

    sm48tat4xarpARPDynamicPort OBJECT-TYPE
               SYNTAX      Integer32(1..255)
               MAX-ACCESS  read-only
               STATUS      current
               DESCRIPTION
                   "Switch Port Number for which the entries are displayed."
               ::= {    sm48tat4xarpARPDynamicEntry 2 }

    sm48tat4xarpARPDynamicVLANId OBJECT-TYPE
               SYNTAX      Integer32(1..4095)
               MAX-ACCESS  read-only
               STATUS      current
               DESCRIPTION
                   "VLAN-ID in which the ARP traffic is permitted."
               ::= {    sm48tat4xarpARPDynamicEntry 3 }

    sm48tat4xarpARPDynamicMACAddress OBJECT-TYPE
               SYNTAX      MacAddress
               MAX-ACCESS  read-only
               STATUS      current
               DESCRIPTION
                   "User MAC address of the entry."
               ::= {    sm48tat4xarpARPDynamicEntry 4 }

    sm48tat4xarpARPDynamicIPAddress OBJECT-TYPE
               SYNTAX      IpAddress
               MAX-ACCESS  read-only
               STATUS      current
               DESCRIPTION
                   "User IP address of the entry."
               ::= {    sm48tat4xarpARPDynamicEntry 5 }

    sm48tat4xarpARPDynamicToStaticCmd OBJECT-TYPE
               SYNTAX      ActivateCmd
               MAX-ACCESS  read-write
               STATUS      current
               DESCRIPTION
                   "Enable the Global ARP Inspection or disable the Global
                    ARP Inspection."
               ::= {     sm48tat4xarpARPDynamicEntry 6 }


-- =======================================================================================================================
-- sm48tat4xarpARPConformance
-- =======================================================================================================================
sm48tat4xarpARPConformance OBJECT IDENTIFIER ::= { sm48tat4xarpARPInspection 200 }

sm48tat4xarpARPCompliances OBJECT IDENTIFIER ::= { sm48tat4xarpARPConformance 1 }

sm48tat4xarpARPGroups      OBJECT IDENTIFIER ::= { sm48tat4xarpARPConformance 2 }

sm48tat4xarpARPGroup OBJECT-GROUP
    OBJECTS {
                -- sm48tat4xarpARPConfig
                sm48tat4xarpARPConfMode,

                --sm48tat4xarpARPPortConfTable
                sm48tat4xarpARPPortConfMode,
                sm48tat4xarpARPPortConfCheckVLAN,
                sm48tat4xarpARPPortConfLogType,

                --sm48tat4xarpARPVlanConfig
                sm48tat4xarpARPVlanConfigLogType,
                sm48tat4xarpARPVlanConfigRowStatus,

                --sm48tat4xarpARPStaticTable
                sm48tat4xarpARPStaticPort,
                sm48tat4xarpARPStaticVlanID,
                sm48tat4xarpARPStaticMACAddress,
                sm48tat4xarpARPStaticIPAddress,
                sm48tat4xarpARPStaticRowStatus,

                --sm48tat4xarpARPDynamicTable
                sm48tat4xarpARPDynamicPort,
                sm48tat4xarpARPDynamicVLANId,
                sm48tat4xarpARPDynamicMACAddress,
                sm48tat4xarpARPDynamicIPAddress,
                sm48tat4xarpARPDynamicToStaticCmd
            }
     STATUS  current
     DESCRIPTION
            "The collection of objects which are used to indicate
            sm48tat4xarp ARP information."
    ::= { sm48tat4xarpARPGroups 1 }

-- =======================================================================================================================
sm48tat4xarpDHCPSnooping                                          OBJECT IDENTIFIER ::= { sm48tat4xarpSecurity 3 }

sm48tat4xarpDHCPSnoopingConf                                          OBJECT IDENTIFIER ::= { sm48tat4xarpDHCPSnooping 1 }

sm48tat4xarpDHCPSnoopingMode OBJECT-TYPE
   SYNTAX      Integer32(0|1)
   MAX-ACCESS  read-write
   STATUS      current
   DESCRIPTION
       "default: 0
       0: disable
       1: enable"
   ::= { sm48tat4xarpDHCPSnoopingConf 1 }

sm48tat4xarpDHCPSnoopingPortModeConfigurationTable OBJECT-TYPE
   SYNTAX      SEQUENCE OF SM48TAT4XARPDHCPSnoopingPortModeConfigurationEntry
   MAX-ACCESS  not-accessible
   STATUS      current
   DESCRIPTION
       " "
   ::= { sm48tat4xarpDHCPSnoopingConf 2 }

sm48tat4xarpDHCPSnoopingPortModeConfigurationEntry OBJECT-TYPE
   SYNTAX      SM48TAT4XARPDHCPSnoopingPortModeConfigurationEntry
   MAX-ACCESS  not-accessible
   STATUS      current
   DESCRIPTION
       " "
   INDEX    { sm48tat4xarpDHCPSnoopingPortModeConfigurationPort  }
   ::= { sm48tat4xarpDHCPSnoopingPortModeConfigurationTable 1 }

SM48TAT4XARPDHCPSnoopingPortModeConfigurationEntry ::= SEQUENCE {
   sm48tat4xarpDHCPSnoopingPortModeConfigurationPort	Integer32,
   sm48tat4xarpDHCPSnoopingPortModeConfigurationMode	Integer32
}

sm48tat4xarpDHCPSnoopingPortModeConfigurationPort OBJECT-TYPE
   SYNTAX      Integer32(1..4095)
   MAX-ACCESS  not-accessible
   STATUS      current
   DESCRIPTION
       " "
   ::= { sm48tat4xarpDHCPSnoopingPortModeConfigurationEntry 1 }

sm48tat4xarpDHCPSnoopingPortModeConfigurationMode OBJECT-TYPE
   SYNTAX      Integer32 (0|1)
   MAX-ACCESS  read-write
   STATUS      current
   DESCRIPTION
       "default: 1
       0: trust port mode
       1: untrust port mode"
   ::= { sm48tat4xarpDHCPSnoopingPortModeConfigurationEntry 2 }

sm48tat4xarpDHCPSnoopingStatisticsTable OBJECT-TYPE
   SYNTAX      SEQUENCE OF SM48TAT4XARPDHCPSnoopingStatisticsEntry
   MAX-ACCESS  not-accessible
   STATUS      current
   DESCRIPTION
       " "
   ::= { sm48tat4xarpDHCPSnooping 2 }

sm48tat4xarpDHCPSnoopingStatisticsEntry OBJECT-TYPE
   SYNTAX      SM48TAT4XARPDHCPSnoopingStatisticsEntry
   MAX-ACCESS  not-accessible
   STATUS      current
   DESCRIPTION
       " "
   INDEX    { sm48tat4xarpDHCPSnoopingStatisticsPort  }
   ::= { sm48tat4xarpDHCPSnoopingStatisticsTable 1 }

SM48TAT4XARPDHCPSnoopingStatisticsEntry ::= SEQUENCE {
   sm48tat4xarpDHCPSnoopingStatisticsPort         Integer32,
   sm48tat4xarpDHCPSnoopingStatisticsClear        Integer32,
   sm48tat4xarpDHCPSnoopingRxDiscover             Counter32,
   sm48tat4xarpDHCPSnoopingRxOffer                Counter32,
   sm48tat4xarpDHCPSnoopingRxRequest              Counter32,
   sm48tat4xarpDHCPSnoopingRxDecline              Counter32,
   sm48tat4xarpDHCPSnoopingRxACK                  Counter32,
   sm48tat4xarpDHCPSnoopingRxNAK                  Counter32,
   sm48tat4xarpDHCPSnoopingRxRelease              Counter32,
   sm48tat4xarpDHCPSnoopingRxInform               Counter32,
   sm48tat4xarpDHCPSnoopingRxLeaseQuery           Counter32,
   sm48tat4xarpDHCPSnoopingRxLeaseUnassigned      Counter32,
   sm48tat4xarpDHCPSnoopingRxLeaseUnknown         Counter32,
   sm48tat4xarpDHCPSnoopingRxLeaseActive          Counter32,
   sm48tat4xarpDHCPSnoopingTxDiscover             Counter32,
   sm48tat4xarpDHCPSnoopingTxOffer                Counter32,
   sm48tat4xarpDHCPSnoopingTxRequest              Counter32,
   sm48tat4xarpDHCPSnoopingTxDecline              Counter32,
   sm48tat4xarpDHCPSnoopingTxACK                  Counter32,
   sm48tat4xarpDHCPSnoopingTxNAK                  Counter32,
   sm48tat4xarpDHCPSnoopingTxRelease              Counter32,
   sm48tat4xarpDHCPSnoopingTxInform               Counter32,
   sm48tat4xarpDHCPSnoopingTxLeaseQuery           Counter32,
   sm48tat4xarpDHCPSnoopingTxLeaseUnassigned      Counter32,
   sm48tat4xarpDHCPSnoopingTxLeaseUnknown         Counter32,
   sm48tat4xarpDHCPSnoopingTxLeaseActive          Counter32,
   sm48tat4xarpDHCPSnoopingRxDiscardedChecksumError  Counter32,
   sm48tat4xarpDHCPSnoopingRxDiscardedFromUntrusted  Counter32
}

sm48tat4xarpDHCPSnoopingStatisticsPort OBJECT-TYPE
   SYNTAX      Integer32(1..4095)
   MAX-ACCESS  not-accessible
   STATUS      current
   DESCRIPTION
       " "
   ::= { sm48tat4xarpDHCPSnoopingStatisticsEntry 1 }

sm48tat4xarpDHCPSnoopingStatisticsClear OBJECT-TYPE
   SYNTAX      Integer32 (0|1)
   MAX-ACCESS  read-write
   STATUS      current
   DESCRIPTION
       "default: 0
       0: none
       1: clear"
   ::= { sm48tat4xarpDHCPSnoopingStatisticsEntry 2 }

sm48tat4xarpDHCPSnoopingRxDiscover OBJECT-TYPE
   SYNTAX      Counter32
   MAX-ACCESS  read-only
   STATUS      current
   DESCRIPTION
       " "
   ::= { sm48tat4xarpDHCPSnoopingStatisticsEntry 3 }

sm48tat4xarpDHCPSnoopingRxOffer OBJECT-TYPE
   SYNTAX      Counter32
   MAX-ACCESS  read-only
   STATUS      current
   DESCRIPTION
       " "
   ::= { sm48tat4xarpDHCPSnoopingStatisticsEntry 4 }

sm48tat4xarpDHCPSnoopingRxRequest OBJECT-TYPE
   SYNTAX      Counter32
   MAX-ACCESS  read-only
   STATUS      current
   DESCRIPTION
       " "
   ::= { sm48tat4xarpDHCPSnoopingStatisticsEntry 5 }

sm48tat4xarpDHCPSnoopingRxDecline OBJECT-TYPE
   SYNTAX      Counter32
   MAX-ACCESS  read-only
   STATUS      current
   DESCRIPTION
       " "
   ::= { sm48tat4xarpDHCPSnoopingStatisticsEntry 6 }

sm48tat4xarpDHCPSnoopingRxACK OBJECT-TYPE
   SYNTAX      Counter32
   MAX-ACCESS  read-only
   STATUS      current
   DESCRIPTION
       " "
   ::= { sm48tat4xarpDHCPSnoopingStatisticsEntry 7 }

sm48tat4xarpDHCPSnoopingRxNAK OBJECT-TYPE
   SYNTAX      Counter32
   MAX-ACCESS  read-only
   STATUS      current
   DESCRIPTION
       " "
   ::= { sm48tat4xarpDHCPSnoopingStatisticsEntry 8 }

sm48tat4xarpDHCPSnoopingRxRelease OBJECT-TYPE
   SYNTAX      Counter32
   MAX-ACCESS  read-only
   STATUS      current
   DESCRIPTION
       " "
   ::= { sm48tat4xarpDHCPSnoopingStatisticsEntry 9 }

sm48tat4xarpDHCPSnoopingRxInform OBJECT-TYPE
   SYNTAX      Counter32
   MAX-ACCESS  read-only
   STATUS      current
   DESCRIPTION
       " "
   ::= { sm48tat4xarpDHCPSnoopingStatisticsEntry 10 }

sm48tat4xarpDHCPSnoopingRxLeaseQuery OBJECT-TYPE
   SYNTAX      Counter32
   MAX-ACCESS  read-only
   STATUS      current
   DESCRIPTION
       " "
   ::= { sm48tat4xarpDHCPSnoopingStatisticsEntry 11 }

sm48tat4xarpDHCPSnoopingRxLeaseUnassigned OBJECT-TYPE
   SYNTAX      Counter32
   MAX-ACCESS  read-only
   STATUS      current
   DESCRIPTION
       " "
   ::= { sm48tat4xarpDHCPSnoopingStatisticsEntry 12 }

sm48tat4xarpDHCPSnoopingRxLeaseUnknown OBJECT-TYPE
   SYNTAX      Counter32
   MAX-ACCESS  read-only
   STATUS      current
   DESCRIPTION
       " "
   ::= { sm48tat4xarpDHCPSnoopingStatisticsEntry 13 }

sm48tat4xarpDHCPSnoopingRxLeaseActive OBJECT-TYPE
   SYNTAX      Counter32
   MAX-ACCESS  read-only
   STATUS      current
   DESCRIPTION
       " "
   ::= { sm48tat4xarpDHCPSnoopingStatisticsEntry 14 }

sm48tat4xarpDHCPSnoopingTxDiscover OBJECT-TYPE
   SYNTAX      Counter32
   MAX-ACCESS  read-only
   STATUS      current
   DESCRIPTION
       " "
   ::= { sm48tat4xarpDHCPSnoopingStatisticsEntry 15 }

sm48tat4xarpDHCPSnoopingTxOffer OBJECT-TYPE
   SYNTAX      Counter32
   MAX-ACCESS  read-only
   STATUS      current
   DESCRIPTION
       " "
   ::= { sm48tat4xarpDHCPSnoopingStatisticsEntry 16 }

sm48tat4xarpDHCPSnoopingTxRequest OBJECT-TYPE
   SYNTAX      Counter32
   MAX-ACCESS  read-only
   STATUS      current
   DESCRIPTION
       " "
   ::= { sm48tat4xarpDHCPSnoopingStatisticsEntry 17 }

sm48tat4xarpDHCPSnoopingTxDecline OBJECT-TYPE
   SYNTAX      Counter32
   MAX-ACCESS  read-only
   STATUS      current
   DESCRIPTION
       " "
   ::= { sm48tat4xarpDHCPSnoopingStatisticsEntry 18 }

sm48tat4xarpDHCPSnoopingTxACK OBJECT-TYPE
   SYNTAX      Counter32
   MAX-ACCESS  read-only
   STATUS      current
   DESCRIPTION
       " "
   ::= { sm48tat4xarpDHCPSnoopingStatisticsEntry 19 }

sm48tat4xarpDHCPSnoopingTxNAK OBJECT-TYPE
   SYNTAX      Counter32
   MAX-ACCESS  read-only
   STATUS      current
   DESCRIPTION
       " "
   ::= { sm48tat4xarpDHCPSnoopingStatisticsEntry 20 }

sm48tat4xarpDHCPSnoopingTxRelease OBJECT-TYPE
   SYNTAX      Counter32
   MAX-ACCESS  read-only
   STATUS      current
   DESCRIPTION
       " "
   ::= { sm48tat4xarpDHCPSnoopingStatisticsEntry 21 }

sm48tat4xarpDHCPSnoopingTxInform OBJECT-TYPE
   SYNTAX      Counter32
   MAX-ACCESS  read-only
   STATUS      current
   DESCRIPTION
       " "
   ::= { sm48tat4xarpDHCPSnoopingStatisticsEntry 22 }

sm48tat4xarpDHCPSnoopingTxLeaseQuery OBJECT-TYPE
   SYNTAX      Counter32
   MAX-ACCESS  read-only
   STATUS      current
   DESCRIPTION
       " "
   ::= { sm48tat4xarpDHCPSnoopingStatisticsEntry 23 }

sm48tat4xarpDHCPSnoopingTxLeaseUnassigned OBJECT-TYPE
   SYNTAX      Counter32
   MAX-ACCESS  read-only
   STATUS      current
   DESCRIPTION
       " "
   ::= { sm48tat4xarpDHCPSnoopingStatisticsEntry 24 }

sm48tat4xarpDHCPSnoopingTxLeaseUnknown OBJECT-TYPE
   SYNTAX      Counter32
   MAX-ACCESS  read-only
   STATUS      current
   DESCRIPTION
       " "
   ::= { sm48tat4xarpDHCPSnoopingStatisticsEntry 25 }

sm48tat4xarpDHCPSnoopingTxLeaseActive OBJECT-TYPE
   SYNTAX      Counter32
   MAX-ACCESS  read-only
   STATUS      current
   DESCRIPTION
       " "
   ::= { sm48tat4xarpDHCPSnoopingStatisticsEntry 26 }

sm48tat4xarpDHCPSnoopingRxDiscardedChecksumError OBJECT-TYPE
   SYNTAX      Counter32
   MAX-ACCESS  read-only
   STATUS      current
   DESCRIPTION
       " "
   ::= { sm48tat4xarpDHCPSnoopingStatisticsEntry 27 }

sm48tat4xarpDHCPSnoopingRxDiscardedFromUntrusted OBJECT-TYPE
   SYNTAX      Counter32
   MAX-ACCESS  read-only
   STATUS      current
   DESCRIPTION
       " "
   ::= { sm48tat4xarpDHCPSnoopingStatisticsEntry 28 }

sm48tat4xarpDHCPRelay                                             OBJECT IDENTIFIER ::= { sm48tat4xarpSecurity 4 }

sm48tat4xarpDHCPRelayConfiguration                                         OBJECT IDENTIFIER ::= { sm48tat4xarpDHCPRelay 1 }

sm48tat4xarpDHCPRelayMode OBJECT-TYPE
   SYNTAX      Integer32(0|1)
   MAX-ACCESS  read-write
   STATUS      current
   DESCRIPTION
       "default: 0
       0: disable
       1: enable
       We need at least one server"
   ::= { sm48tat4xarpDHCPRelayConfiguration 1 }

sm48tat4xarpDHCPRelayServer OBJECT-TYPE
   SYNTAX      IpAddress
   MAX-ACCESS  read-write
   STATUS      current
   DESCRIPTION
       " "
   ::= { sm48tat4xarpDHCPRelayConfiguration 2 }

sm48tat4xarpDHCPRelayInformationMode OBJECT-TYPE
   SYNTAX      Integer32(0|1)
   MAX-ACCESS  read-write
   STATUS      current
   DESCRIPTION
       "default: 0
       0: disable
       1: enable "
   ::= { sm48tat4xarpDHCPRelayConfiguration 3 }

sm48tat4xarpDHCPRelayInformationPolicy OBJECT-TYPE
   SYNTAX      Integer32(0..2)
   MAX-ACCESS  read-write
   STATUS      current
   DESCRIPTION
       "default: 0
       0: replace
       1: keep
       2: drop "
   ::= { sm48tat4xarpDHCPRelayConfiguration 4 }

sm48tat4xarpDHCPRelayStatistics                                   OBJECT IDENTIFIER ::= { sm48tat4xarpDHCPRelay 2 }

sm48tat4xarpDHCPRelayServerStatistics                                   OBJECT IDENTIFIER ::= { sm48tat4xarpDHCPRelayStatistics 1 }

sm48tat4xarpServerStatTransmitToServer OBJECT-TYPE
   SYNTAX      Counter32
   MAX-ACCESS  read-only
   STATUS      current
   DESCRIPTION
       " "
   ::= { sm48tat4xarpDHCPRelayServerStatistics 1 }

sm48tat4xarpServerStatTransmitError OBJECT-TYPE
   SYNTAX      Counter32
   MAX-ACCESS  read-only
   STATUS      current
   DESCRIPTION
       " "
   ::= { sm48tat4xarpDHCPRelayServerStatistics 2 }

sm48tat4xarpServerStatReceiveFromServer OBJECT-TYPE
   SYNTAX      Counter32
   MAX-ACCESS  read-only
   STATUS      current
   DESCRIPTION
       " "
   ::= { sm48tat4xarpDHCPRelayServerStatistics 3 }

sm48tat4xarpServerStatReceiveMissingAgentOption OBJECT-TYPE
   SYNTAX      Counter32
   MAX-ACCESS  read-only
   STATUS      current
   DESCRIPTION
       " "
   ::= { sm48tat4xarpDHCPRelayServerStatistics 4 }

sm48tat4xarpServerStatReceiveMissingCircuitID OBJECT-TYPE
   SYNTAX      Counter32
   MAX-ACCESS  read-only
   STATUS      current
   DESCRIPTION
       " "
   ::= { sm48tat4xarpDHCPRelayServerStatistics 5 }

sm48tat4xarpServerStatReceiveMissingRemoteID OBJECT-TYPE
   SYNTAX      Counter32
   MAX-ACCESS  read-only
   STATUS      current
   DESCRIPTION
       " "
   ::= { sm48tat4xarpDHCPRelayServerStatistics 6 }

sm48tat4xarpServerStatReceiveBadCircuitID OBJECT-TYPE
   SYNTAX      Counter32
   MAX-ACCESS  read-only
   STATUS      current
   DESCRIPTION
       " "
   ::= { sm48tat4xarpDHCPRelayServerStatistics 7 }

sm48tat4xarpServerStatReceiveBadRemoteID OBJECT-TYPE
   SYNTAX      Counter32
   MAX-ACCESS  read-only
   STATUS      current
   DESCRIPTION
       " "
   ::= { sm48tat4xarpDHCPRelayServerStatistics 8 }

sm48tat4xarpDHCPRelayClientStatistics                                   OBJECT IDENTIFIER ::= { sm48tat4xarpDHCPRelayStatistics 2 }

sm48tat4xarpClientStatTransmitToClient OBJECT-TYPE
   SYNTAX      Counter32
   MAX-ACCESS  read-only
   STATUS      current
   DESCRIPTION
       " "
   ::= { sm48tat4xarpDHCPRelayClientStatistics 1 }

sm48tat4xarpClientStatTransmitError OBJECT-TYPE
   SYNTAX      Counter32
   MAX-ACCESS  read-only
   STATUS      current
   DESCRIPTION
       " "
   ::= { sm48tat4xarpDHCPRelayClientStatistics 2 }

sm48tat4xarpClientStatReceivefromClient OBJECT-TYPE
   SYNTAX      Counter32
   MAX-ACCESS  read-only
   STATUS      current
   DESCRIPTION
       " "
   ::= { sm48tat4xarpDHCPRelayClientStatistics 3 }

sm48tat4xarpClientStatReceiveAgentOption OBJECT-TYPE
   SYNTAX      Counter32
   MAX-ACCESS  read-only
   STATUS      current
   DESCRIPTION
       " "
   ::= { sm48tat4xarpDHCPRelayClientStatistics 4 }

sm48tat4xarpClientStatReplaceAgentOption OBJECT-TYPE
   SYNTAX      Counter32
   MAX-ACCESS  read-only
   STATUS      current
   DESCRIPTION
       " "
   ::= { sm48tat4xarpDHCPRelayClientStatistics 5 }

sm48tat4xarpClientStatKeepAgentOption OBJECT-TYPE
   SYNTAX      Counter32
   MAX-ACCESS  read-only
   STATUS      current
   DESCRIPTION
       " "
   ::= { sm48tat4xarpDHCPRelayClientStatistics 6 }

sm48tat4xarpClientStatDropAgentOption OBJECT-TYPE
   SYNTAX      Counter32
   MAX-ACCESS  read-only
   STATUS      current
   DESCRIPTION
       " "
   ::= { sm48tat4xarpDHCPRelayClientStatistics 7 }

sm48tat4xarpPortSecurity                                          OBJECT IDENTIFIER ::= { sm48tat4xarpSecurity 5 }

sm48tat4xarpPortSecLimitCtrl                                      OBJECT IDENTIFIER ::= { sm48tat4xarpPortSecurity 1 }

sm48tat4xarpPortSecLimitCtrlSystemConf                                      OBJECT IDENTIFIER ::= { sm48tat4xarpPortSecLimitCtrl 1 }

-- sm48tat4xarpPortSecurityMode OBJECT-TYPE
--   SYNTAX      Integer32(0|1)
--   MAX-ACCESS  read-write
--   STATUS      current
--   DESCRIPTION
--       "default: 0
--       0: disable
--       1: enable "
--   ::= { sm48tat4xarpPortSecLimitCtrlSystemConf 1 }

sm48tat4xarpPortSecurityAging OBJECT-TYPE
   SYNTAX      Integer32(0|1)
   MAX-ACCESS  read-write
   STATUS      current
   DESCRIPTION
       "default: 0
       0: disable
       1: enable "
   ::= { sm48tat4xarpPortSecLimitCtrlSystemConf 1 }

sm48tat4xarpPortSecurityAgingPeriod OBJECT-TYPE
   SYNTAX      Integer32(10..10000000)
   MAX-ACCESS  read-write
   STATUS      current
   DESCRIPTION
       "default: 3600, range: 10-10000000 "
   ::= { sm48tat4xarpPortSecLimitCtrlSystemConf 2 }

sm48tat4xarpPortSecurityHoldTime OBJECT-TYPE
   SYNTAX      Integer32(10..10000000)
   MAX-ACCESS  read-write
   STATUS      current
   DESCRIPTION
       "default: 300, range: 10-10000000 "
   ::= { sm48tat4xarpPortSecLimitCtrlSystemConf 3 }

sm48tat4xarpPortSecLimitCtrlTable OBJECT-TYPE
   SYNTAX      SEQUENCE OF SM48TAT4XARPPortSecLimitCtrlEntry
   MAX-ACCESS  not-accessible
   STATUS      current
   DESCRIPTION
       " "
   ::= { sm48tat4xarpPortSecLimitCtrl 2 }

sm48tat4xarpPortSecLimitCtrlEntry OBJECT-TYPE
   SYNTAX      SM48TAT4XARPPortSecLimitCtrlEntry
   MAX-ACCESS  not-accessible
   STATUS      current
   DESCRIPTION
       " "
   INDEX    { sm48tat4xarpPortSecLimitCtrlPort  }
   ::= { sm48tat4xarpPortSecLimitCtrlTable 1 }

SM48TAT4XARPPortSecLimitCtrlEntry ::= SEQUENCE {
   sm48tat4xarpPortSecLimitCtrlPort                Integer32,
   sm48tat4xarpPortSecLimitCtrlPortMode            Integer32,
   sm48tat4xarpPortSecLimitCtrlPortLimit           Integer32,
   sm48tat4xarpPortSecLimitCtrlPortViolationmMode  Integer32,
   sm48tat4xarpPortSecLimitCtrlPortViolationmLimit Integer32,
   sm48tat4xarpPortSecLimitCtrlPortState           DisplayString,
   sm48tat4xarpPortSecLimitCtrlPortReOpen          Integer32,
   sm48tat4xarpPortSecLimitCtrlPortSticky          Integer32,
   sm48tat4xarpPortSecLimitCtrlPortClear           Integer32
}

sm48tat4xarpPortSecLimitCtrlPort OBJECT-TYPE
   SYNTAX      Integer32(1..65535)
   MAX-ACCESS  not-accessible
   STATUS      current
   DESCRIPTION
       " "
   ::= { sm48tat4xarpPortSecLimitCtrlEntry 1 }

sm48tat4xarpPortSecLimitCtrlPortMode OBJECT-TYPE
   SYNTAX      Integer32 (0|1)
   MAX-ACCESS  read-write
   STATUS      current
   DESCRIPTION
       "default: 0
       0: disable
       1: enable"
   ::= { sm48tat4xarpPortSecLimitCtrlEntry 2 }

sm48tat4xarpPortSecLimitCtrlPortLimit OBJECT-TYPE
   SYNTAX      Integer32(1..1024)
   MAX-ACCESS  read-write
   STATUS      current
   DESCRIPTION
       "default: 4, range: 1-1024"
   ::= { sm48tat4xarpPortSecLimitCtrlEntry 3 }

sm48tat4xarpPortSecLimitCtrlPortViolationmMode OBJECT-TYPE
   SYNTAX      Integer32(0..2)
   MAX-ACCESS  read-write
   STATUS      current
   DESCRIPTION
       "default: 0
       0: Protect
       1: Restrict
       2: Shutdown"
   ::= { sm48tat4xarpPortSecLimitCtrlEntry 4 }

sm48tat4xarpPortSecLimitCtrlPortViolationmLimit OBJECT-TYPE
   SYNTAX      Integer32(1..1024)
   MAX-ACCESS  read-write
   STATUS      current
   DESCRIPTION
       "default: 4, range: 1-1024"
   ::= { sm48tat4xarpPortSecLimitCtrlEntry 5 }


sm48tat4xarpPortSecLimitCtrlPortState OBJECT-TYPE
   SYNTAX      DisplayString
   MAX-ACCESS  read-only
   STATUS      current
   DESCRIPTION
       " "
   ::= { sm48tat4xarpPortSecLimitCtrlEntry 6 }

sm48tat4xarpPortSecLimitCtrlPortReOpen OBJECT-TYPE
   SYNTAX      Integer32 (0|1)
   MAX-ACCESS  read-write
   STATUS      current
   DESCRIPTION
       "default: 0
       0: none
       1: reopen"
   ::= { sm48tat4xarpPortSecLimitCtrlEntry 7 }

sm48tat4xarpPortSecLimitCtrlPortSticky OBJECT-TYPE
   SYNTAX      Integer32 (0|1)
   MAX-ACCESS  read-write
   STATUS      current
   DESCRIPTION
       "default: 0
       0: disable
       1: enable"
   ::= { sm48tat4xarpPortSecLimitCtrlEntry 8 }

sm48tat4xarpPortSecLimitCtrlPortClear OBJECT-TYPE
   SYNTAX      Integer32 (0|1)
   MAX-ACCESS  read-write
   STATUS      current
   DESCRIPTION
       "default: 0
       1: clear"
   ::= { sm48tat4xarpPortSecLimitCtrlEntry 9 }


sm48tat4xarpPortSecSwitchStatusTable OBJECT-TYPE
   SYNTAX      SEQUENCE OF SM48TAT4XARPPortSecSwitchStatusEntry
   MAX-ACCESS  not-accessible
   STATUS      current
   DESCRIPTION
       " "
   ::= { sm48tat4xarpPortSecurity 2 }

sm48tat4xarpPortSecSwitchStatusEntry OBJECT-TYPE
   SYNTAX      SM48TAT4XARPPortSecSwitchStatusEntry
   MAX-ACCESS  not-accessible
   STATUS      current
   DESCRIPTION
       " "
   INDEX    { sm48tat4xarpPortSecSwitchStatusPort  }
   ::= { sm48tat4xarpPortSecSwitchStatusTable 1 }

SM48TAT4XARPPortSecSwitchStatusEntry ::= SEQUENCE {
   sm48tat4xarpPortSecSwitchStatusPort                Integer32,
--   sm48tat4xarpPortSecSwitchStatusUsers               DisplayString,
   sm48tat4xarpPortSecSwitchStatusViolationmMode      DisplayString,
   sm48tat4xarpPortSecSwitchStatusState               DisplayString,
   sm48tat4xarpPortSecSwitchStatusMACCountCurrent     Integer32,
   sm48tat4xarpPortSecSwitchStatusMACCountViolating   Integer32,
   sm48tat4xarpPortSecSwitchStatusMACCountLimit       Integer32,
   sm48tat4xarpPortSecSwitchStatusClear               Integer32
}

sm48tat4xarpPortSecSwitchStatusPort OBJECT-TYPE
   SYNTAX      Integer32(1..65535)
   MAX-ACCESS  not-accessible
   STATUS      current
   DESCRIPTION
       " "
   ::= { sm48tat4xarpPortSecSwitchStatusEntry 1 }

-- sm48tat4xarpPortSecSwitchStatusUsers OBJECT-TYPE
--   SYNTAX      DisplayString
--   MAX-ACCESS  read-only
--   STATUS      current
--   DESCRIPTION
--       " Users Abbr: L = Limit Control, 8 = 802.1X, D = DHCP Snooping, V = Voice VLAN,
--         '-' means that the corresponding user module is not enabled. "
--   ::= { sm48tat4xarpPortSecSwitchStatusEntry 2 }

sm48tat4xarpPortSecSwitchStatusViolationmMode OBJECT-TYPE
   SYNTAX      DisplayString
   MAX-ACCESS  read-only
   STATUS      current
   DESCRIPTION
       "Shows the configured Violation Mode of the port."
   ::= { sm48tat4xarpPortSecSwitchStatusEntry 3 }

sm48tat4xarpPortSecSwitchStatusState OBJECT-TYPE
   SYNTAX      DisplayString
   MAX-ACCESS  read-only
   STATUS      current
   DESCRIPTION
       " Shows the current state of the port : Disabled, Ready, Limit Reached, Shutdown. "
   ::= { sm48tat4xarpPortSecSwitchStatusEntry 4 }

sm48tat4xarpPortSecSwitchStatusMACCountCurrent OBJECT-TYPE
   SYNTAX      Integer32
   MAX-ACCESS  read-only
   STATUS      current
   DESCRIPTION
       " "
   ::= { sm48tat4xarpPortSecSwitchStatusEntry 5 }

sm48tat4xarpPortSecSwitchStatusMACCountViolating OBJECT-TYPE
   SYNTAX      Integer32
   MAX-ACCESS  read-only
   STATUS      current
   DESCRIPTION
       " "
   ::= { sm48tat4xarpPortSecSwitchStatusEntry 6 }

sm48tat4xarpPortSecSwitchStatusMACCountLimit OBJECT-TYPE
   SYNTAX      Integer32
   MAX-ACCESS  read-only
   STATUS      current
   DESCRIPTION
       " "
   ::= { sm48tat4xarpPortSecSwitchStatusEntry 7 }

sm48tat4xarpPortSecSwitchStatusClear OBJECT-TYPE
   SYNTAX      Integer32 (0|1)
   MAX-ACCESS  read-write
   STATUS      current
   DESCRIPTION
       "Remove all MAC addresses on all VLANs on this port."
   ::= { sm48tat4xarpPortSecSwitchStatusEntry 8 }

sm48tat4xarpPortSecPortStatus                                      OBJECT IDENTIFIER ::= { sm48tat4xarpPortSecurity 3 }

sm48tat4xarpPortSecPortStatusPort OBJECT-TYPE
   SYNTAX       Integer32
   MAX-ACCESS   read-write
   STATUS       current
   DESCRIPTION
       "port number
        default: 1
        range: 1 - port number."
   ::= { sm48tat4xarpPortSecPortStatus 1 }

sm48tat4xarpPortSecPortStatusTable OBJECT-TYPE
   SYNTAX      SEQUENCE OF SM48TAT4XARPPortSecPortStatusEntry
   MAX-ACCESS  not-accessible
   STATUS      current
   DESCRIPTION
      " "
   ::= { sm48tat4xarpPortSecPortStatus 2 }

sm48tat4xarpPortSecPortStatusEntry OBJECT-TYPE
   SYNTAX      SM48TAT4XARPPortSecPortStatusEntry
   MAX-ACCESS  not-accessible
   STATUS      current
   DESCRIPTION
       " "
   INDEX    { sm48tat4xarpPortSecPortStatusIndex  }
   ::= { sm48tat4xarpPortSecPortStatusTable 1 }

SM48TAT4XARPPortSecPortStatusEntry ::= SEQUENCE {
   sm48tat4xarpPortSecPortStatusIndex              Integer32,
   sm48tat4xarpPortSecPortStatusMACAddress         DisplayString,
   sm48tat4xarpPortSecPortStatusVLANId             Integer32,
   sm48tat4xarpPortSecPortStatusState              DisplayString,
   sm48tat4xarpPortSecPortStatusAgeAndHold         DisplayString,
   sm48tat4xarpPortSecPortStatusClear              Integer32
}

sm48tat4xarpPortSecPortStatusIndex OBJECT-TYPE
   SYNTAX      Integer32(1..65535)
   MAX-ACCESS  not-accessible
   STATUS      current
   DESCRIPTION
       " "
   ::= { sm48tat4xarpPortSecPortStatusEntry 1 }

sm48tat4xarpPortSecPortStatusMACAddress OBJECT-TYPE
   SYNTAX      DisplayString
   MAX-ACCESS  read-only
   STATUS      current
   DESCRIPTION
       "MAC address that is seen on this port."
   ::= { sm48tat4xarpPortSecPortStatusEntry 2 }

sm48tat4xarpPortSecPortStatusVLANId OBJECT-TYPE
   SYNTAX      Integer32(1..4094)
   MAX-ACCESS  read-only
   STATUS      current
   DESCRIPTION
       "VLAN ID that is seen on this port"
   ::= { sm48tat4xarpPortSecPortStatusEntry 3 }

sm48tat4xarpPortSecPortStatusState OBJECT-TYPE
   SYNTAX      DisplayString
   MAX-ACCESS  read-only
   STATUS      current
   DESCRIPTION
       "Indicates whether the corresponding MAC address is violating
	   (administrative user has configured the interface in Restrict mode and the MAC address is blocked),
	   blocked, or forwarding."
   ::= { sm48tat4xarpPortSecPortStatusEntry 4 }

sm48tat4xarpPortSecPortStatusAgeAndHold OBJECT-TYPE
   SYNTAX      DisplayString
   MAX-ACCESS  read-only
   STATUS      current
   DESCRIPTION
       " "
   ::= { sm48tat4xarpPortSecPortStatusEntry 5 }

sm48tat4xarpPortSecPortStatusClear OBJECT-TYPE
   SYNTAX      Integer32(0|1)
   MAX-ACCESS  read-write
   STATUS      current
   DESCRIPTION
       "Remove particular MAC addresses from MAC table
	   1:clear"
   ::= { sm48tat4xarpPortSecPortStatusEntry 6 }

sm48tat4xarpAccessManagement                                      OBJECT IDENTIFIER ::= { sm48tat4xarpSecurity 6 }

sm48tat4xarpAccessMgmtConf                                         OBJECT IDENTIFIER ::= { sm48tat4xarpAccessManagement 1 }

sm48tat4xarpAccessMgmtStatistics                                   OBJECT IDENTIFIER ::= { sm48tat4xarpAccessManagement 2 }
--
-- =======================================================================================================================
-- Start sm48tat4xarpAccessManagement group
-- =======================================================================================================================
--sm48tat4xarpAccessMgmtConf

    sm48tat4xarpAccessMgmtConfMode OBJECT-TYPE
               SYNTAX      AdminMode
               MAX-ACCESS  read-write
               STATUS      current
               DESCRIPTION
                   "Indicates the access management mode operation."
               DEFVAL  { disable }
               ::= {     sm48tat4xarpAccessMgmtConf 1 }

--sm48tat4xarpAccessMgmtConfTable

    sm48tat4xarpAccessMgmtConfTable OBJECT-TYPE
               SYNTAX      SEQUENCE OF     SM48TAT4XARPAccessMgmtConfEntry
               MAX-ACCESS  not-accessible
               STATUS      current
               DESCRIPTION
                   "The Access Mgmt Conf Table. "
               ::= {     sm48tat4xarpAccessMgmtConf 2 }

    sm48tat4xarpAccessMgmtConfEntry OBJECT-TYPE
               SYNTAX          SM48TAT4XARPAccessMgmtConfEntry
               MAX-ACCESS  not-accessible
               STATUS      current
               DESCRIPTION
                   "The Access Mgmt Conf Entry "
               INDEX    {    sm48tat4xarpAccessMgmtIndex  }
               ::= {     sm48tat4xarpAccessMgmtConfTable 1 }

    SM48TAT4XARPAccessMgmtConfEntry             ::= SEQUENCE {
                 sm48tat4xarpAccessMgmtIndex            Integer32,
                 sm48tat4xarpAccessMgmtVlanID           Integer32,
                 sm48tat4xarpAccessMgmtStartIpAddress   IpAddress,
                 sm48tat4xarpAccessMgmtEndIpAddress     IpAddress,
                 sm48tat4xarpAccessMgmtHttpHttps        AdminMode,
                 sm48tat4xarpAccessMgmtSNMP             AdminMode,
                 sm48tat4xarpAccessMgmtTelnetSSH        AdminMode,
                 sm48tat4xarpAccessMgmtRowStatus        RowStatus
                 }

    sm48tat4xarpAccessMgmtIndex OBJECT-TYPE
               SYNTAX      Integer32(1..16)
               MAX-ACCESS  not-accessible
               STATUS      current
               DESCRIPTION
                   "The Access Management config index.
                    range : 1-16."
               ::= {     sm48tat4xarpAccessMgmtConfEntry 1 }

    sm48tat4xarpAccessMgmtVlanID OBJECT-TYPE
               SYNTAX      Integer32 (1..4095)
               MAX-ACCESS  read-create
               STATUS      current
               DESCRIPTION
                   "The VLAN ID for the access management entry.
                    range: 1-4095."
               ::= {     sm48tat4xarpAccessMgmtConfEntry 2 }

    sm48tat4xarpAccessMgmtStartIpAddress OBJECT-TYPE
               SYNTAX      IpAddress
               MAX-ACCESS  read-create
               STATUS      current
               DESCRIPTION
                   "The start IP address for the access management
                    entry."
               ::= {     sm48tat4xarpAccessMgmtConfEntry 3 }

    sm48tat4xarpAccessMgmtEndIpAddress OBJECT-TYPE
               SYNTAX      IpAddress
               MAX-ACCESS  read-create
               STATUS      current
               DESCRIPTION
                   "The end IP address for the access management
                    entry. "
               ::= {     sm48tat4xarpAccessMgmtConfEntry 4 }

    sm48tat4xarpAccessMgmtHttpHttps OBJECT-TYPE
               SYNTAX      AdminMode
               MAX-ACCESS  read-create
               STATUS      current
               DESCRIPTION
                   "Indicates that the host can access the switch from
                    HTTP/HTTPS interface if the host IP address matches the IP
                    address range provided in the entry."
               DEFVAL  { disable }
               ::= {     sm48tat4xarpAccessMgmtConfEntry 5 }

    sm48tat4xarpAccessMgmtSNMP OBJECT-TYPE
               SYNTAX      AdminMode
               MAX-ACCESS  read-create
               STATUS      current
               DESCRIPTION
                   "Indicates that the host can access the switch from SNMP
                    interface if the host IP address matches the IP address
                    range provided in the entry."
               DEFVAL  { disable }
               ::= {     sm48tat4xarpAccessMgmtConfEntry 6 }

    sm48tat4xarpAccessMgmtTelnetSSH OBJECT-TYPE
               SYNTAX      AdminMode
               MAX-ACCESS  read-create
               STATUS      current
               DESCRIPTION
                   "Indicates that the host can access the switch from
                    TELNET/SSH interface if the host IP address matches
                    the IP address range provided in the entry."
               DEFVAL  { disable }
               ::= {     sm48tat4xarpAccessMgmtConfEntry 7 }

    sm48tat4xarpAccessMgmtRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sm48tat4xarpAccessMgmtConfEntry 8 }

--sm48tat4xarpAccessMgmtStatistics

    sm48tat4xarpAccessMgmtStatisticsClear OBJECT-TYPE
               SYNTAX      ActivateCmd
               MAX-ACCESS  read-write
               STATUS      current
               DESCRIPTION
                   "Clear all statistics."
               ::= {     sm48tat4xarpAccessMgmtStatistics 1 }

--sm48tat4xarpAccessMgmtStatisticsTable

    sm48tat4xarpAccessMgmtStatisticsTable OBJECT-TYPE
               SYNTAX      SEQUENCE OF     SM48TAT4XARPAccessMgmtStatisticsEntry
               MAX-ACCESS  not-accessible
               STATUS      current
               DESCRIPTION
                   "The Access Mgmt Statistics Table. "
               ::= {     sm48tat4xarpAccessMgmtStatistics 2 }

    sm48tat4xarpAccessMgmtStatisticsEntry OBJECT-TYPE
               SYNTAX          SM48TAT4XARPAccessMgmtStatisticsEntry
               MAX-ACCESS  not-accessible
               STATUS      current
               DESCRIPTION
                   "The Access Mgmt Statistics Entry. "
               INDEX    {    sm48tat4xarpAccessMgmtStatisticsInterface  }
               ::= {     sm48tat4xarpAccessMgmtStatisticsTable 1 }

    SM48TAT4XARPAccessMgmtStatisticsEntry ::= SEQUENCE {
                 sm48tat4xarpAccessMgmtStatisticsInterface         INTEGER,
                 sm48tat4xarpAccessMgmtStatisticsReceivedPackets   Integer32,
                 sm48tat4xarpAccessMgmtStatisticsAllowedPackets    Integer32,
                 sm48tat4xarpAccessMgmtStatisticsDiscardedPackets  Integer32
                 }

    sm48tat4xarpAccessMgmtStatisticsInterface OBJECT-TYPE
               SYNTAX      INTEGER { http(1), https(2), snmp(3), telnet(4), ssh (5) }
               MAX-ACCESS  not-accessible
               STATUS      current
               DESCRIPTION
                   "The interface type through which the remote host can
                    access the switch.
                    1: HTTP,
                    2: HTTPs,
                    3: SNMP,
                    4: TELNET,
                    5: SSH"
               ::= {     sm48tat4xarpAccessMgmtStatisticsEntry 1 }

    sm48tat4xarpAccessMgmtStatisticsReceivedPackets OBJECT-TYPE
               SYNTAX      Integer32(1..10000000)
               MAX-ACCESS  read-only
               STATUS      current
               DESCRIPTION
                   "Number of received packets from the interface when
                    access management mode is enabled. "
               ::= {     sm48tat4xarpAccessMgmtStatisticsEntry 2 }

    sm48tat4xarpAccessMgmtStatisticsAllowedPackets OBJECT-TYPE
               SYNTAX      Integer32(1..10000000)
               MAX-ACCESS  read-only
               STATUS      current
               DESCRIPTION
                   "Number of allowed packets from the interface when
                    access management mode is enabled. "
               ::= {     sm48tat4xarpAccessMgmtStatisticsEntry 3 }

    sm48tat4xarpAccessMgmtStatisticsDiscardedPackets OBJECT-TYPE
               SYNTAX      Integer32(1..10000000)
               MAX-ACCESS  read-only
               STATUS      current
               DESCRIPTION
                   "Number of discarded packets from the interface when
                    access management mode is enabled. "
               ::= {     sm48tat4xarpAccessMgmtStatisticsEntry 4 }

-- =======================================================================================================================

--sm48tat4xarpSSH                                                   OBJECT IDENTIFIER ::= { sm48tat4xarpSecurity 7 }
--
--sm48tat4xarpSSHMode OBJECT-TYPE
--   SYNTAX      Integer32(0|1)
--   MAX-ACCESS  read-write
--   STATUS      current
--   DESCRIPTION
--       "default: 1
--        0: disable
--        1: enable"
--   ::= { sm48tat4xarpSSH 1 }

--sm48tat4xarpSSHPort OBJECT-TYPE
--   SYNTAX      Integer32(1..65535)
--   MAX-ACCESS  read-write
--   STATUS      current
--   DESCRIPTION
--       "SSH service port number.
--        range : 1-65535, default : 22."
--   ::= { sm48tat4xarpSSH 2 }

sm48tat4xarpHTTPS                                                 OBJECT IDENTIFIER ::= { sm48tat4xarpSecurity 8 }
--
--sm48tat4xarpHTTPSMode OBJECT-TYPE
--   SYNTAX      Integer32(0|1)
--   MAX-ACCESS  read-write
--   STATUS      current
--   DESCRIPTION
--       "default: 1
--        0: disable
--        1: enable"
--   ::= { sm48tat4xarpHTTPS 1 }
--
--sm48tat4xarpHTTPSAutoRedirect OBJECT-TYPE
--   SYNTAX      Integer32(0|1)
--   MAX-ACCESS  read-write
--   STATUS      current
--   DESCRIPTION
--       "default: 0
--        0: disable
--        1: enable"
--   ::= { sm48tat4xarpHTTPS 2 }
--
--sm48tat4xarpHTTPSPort OBJECT-TYPE
--   SYNTAX      Integer32(1..65535)
--   MAX-ACCESS  read-write
--   STATUS      current
--   DESCRIPTION
--       "HTTPS service port number.
--        range : 1-65535, default : 443."
--   ::= { sm48tat4xarpHTTPS 3 }
--
sm48tat4xarpHTTPSCertificateMaintain OBJECT-TYPE
   SYNTAX      Integer32(2..3)
   MAX-ACCESS  read-write
   STATUS      current
   DESCRIPTION
       "2: Upload
		3: Generate"
   ::= { sm48tat4xarpHTTPS 4 }

sm48tat4xarpHTTPSCertificatePassPhrase OBJECT-TYPE
   SYNTAX      DisplayString
   MAX-ACCESS  read-write
   STATUS      current
   DESCRIPTION
       "Enter the pass phrase in this field if your uploading certificate is protected by a specific passphrase."
   ::= { sm48tat4xarpHTTPS 5 }

sm48tat4xarpHTTPSCertificateUpload OBJECT-TYPE
   SYNTAX      Integer32(0|1)
   MAX-ACCESS  read-write
   STATUS      current
   DESCRIPTION
       "default: 0
        0: TFTP
        1: URL"
   ::= { sm48tat4xarpHTTPS 6 }

sm48tat4xarpHTTPSFileUploadFileURL OBJECT-TYPE
   SYNTAX      DisplayString
   MAX-ACCESS  read-write
   STATUS      current
   DESCRIPTION
       "TFTP: filename
	    URL: URL"
   ::= { sm48tat4xarpHTTPS 7 }

sm48tat4xarpHTTPSFileUploadTFTPServer OBJECT-TYPE
   SYNTAX       IpAddress
   MAX-ACCESS   read-write
   STATUS       current
   DESCRIPTION
		"TFTP server IP address"
   ::= { sm48tat4xarpHTTPS 8 }

sm48tat4xarpHTTPSApply OBJECT-TYPE
   SYNTAX      Integer32(0|1)
   MAX-ACCESS  read-write
   STATUS      current
   DESCRIPTION
       "1: apply the above https settings"
   ::= { sm48tat4xarpHTTPS 9 }

sm48tat4xarpHTTPSCertificateStatus OBJECT-TYPE
   SYNTAX      DisplayString
   MAX-ACCESS  read-only
   STATUS      current
   DESCRIPTION
       "Display the current status of certificate on the switch."
   ::= { sm48tat4xarpHTTPS 10 }

sm48tat4xarpAuthMethod                                            OBJECT IDENTIFIER ::= { sm48tat4xarpSecurity 9 }

--
-- =======================================================================================================================
-- Start sm48tat4xarpAuthMethodConfig group
-- =======================================================================================================================
--sm48tat4xarpAuthMethodConfigTable

    sm48tat4xarpAuthMethodConfigTable OBJECT-TYPE
               SYNTAX      SEQUENCE OF     SM48TAT4XARPAuthMethodConfigEntry
               MAX-ACCESS  not-accessible
               STATUS      current
               DESCRIPTION
                   "The Auth Method Config Table."
               ::= {     sm48tat4xarpAuthMethod 1 }

    sm48tat4xarpAuthMethodConfigEntry OBJECT-TYPE
               SYNTAX          SM48TAT4XARPAuthMethodConfigEntry
               MAX-ACCESS  not-accessible
               STATUS      current
               DESCRIPTION
                   "The Auth Method Config Entry."
               INDEX    {    sm48tat4xarpAuthMethodConfigClient  }
               ::= {     sm48tat4xarpAuthMethodConfigTable 1 }

    SM48TAT4XARPAuthMethodConfigEntry             ::= SEQUENCE {
                 sm48tat4xarpAuthMethodConfigClient        INTEGER,
                 sm48tat4xarpAuthMethodConfigMethod1       INTEGER,
                 sm48tat4xarpAuthMethodConfigMethod2       INTEGER,
                 sm48tat4xarpAuthMethodConfigMethod3       INTEGER,
                 sm48tat4xarpAuthMethodConfigMethod4       INTEGER,
                 sm48tat4xarpAuthMethodConfigServicePort   Integer32
                 }

    sm48tat4xarpAuthMethodConfigClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sm48tat4xarpAuthMethodConfigEntry 1 }

    sm48tat4xarpAuthMethodConfigMethod1 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sm48tat4xarpAuthMethodConfigEntry 2 }

    sm48tat4xarpAuthMethodConfigMethod2 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sm48tat4xarpAuthMethodConfigEntry 3 }

    sm48tat4xarpAuthMethodConfigMethod3 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sm48tat4xarpAuthMethodConfigEntry 4 }

    sm48tat4xarpAuthMethodConfigMethod4 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sm48tat4xarpAuthMethodConfigEntry 5 }

    sm48tat4xarpAuthMethodConfigServicePort OBJECT-TYPE
               SYNTAX      Integer32 (1..65535)
               MAX-ACCESS  read-write
               STATUS      current
               DESCRIPTION
                   "The network port number this client bound to provide service."
               ::= {     sm48tat4xarpAuthMethodConfigEntry 6 }

    sm48tat4xarpCommandAuthorizationMethodTable OBJECT-TYPE
               SYNTAX      SEQUENCE OF     SM48TAT4XARPCommandAuthorizationMethodEntry
               MAX-ACCESS  not-accessible
               STATUS      current
               DESCRIPTION
                   "The Command Authorized Method Config Table."
               ::= {     sm48tat4xarpAuthMethod 2 }

    sm48tat4xarpCommandAuthorizationMethodEntry OBJECT-TYPE
               SYNTAX          SM48TAT4XARPCommandAuthorizationMethodEntry
               MAX-ACCESS  not-accessible
               STATUS      current
               DESCRIPTION
                   "The Command Authorized Method Config Entry."
               INDEX    {    sm48tat4xarpCommandAuthorizationMethodClient  }
               ::= {     sm48tat4xarpCommandAuthorizationMethodTable 1 }

    SM48TAT4XARPCommandAuthorizationMethodEntry             ::= SEQUENCE {
                 sm48tat4xarpCommandAuthorizationMethodClient       INTEGER,
                 sm48tat4xarpCommandAuthorizationMethodMethod       Integer32,
                 sm48tat4xarpCommandAuthorizationMethodCmdLvl       Integer32,
                 sm48tat4xarpCommandAuthorizationMethodCfgCmd       Integer32
                 }

    sm48tat4xarpCommandAuthorizationMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sm48tat4xarpCommandAuthorizationMethodEntry 1 }

    sm48tat4xarpCommandAuthorizationMethodMethod OBJECT-TYPE
               SYNTAX      Integer32
               MAX-ACCESS  read-write
               STATUS      current
               DESCRIPTION
                   "Method can be set to one of the following values:
                    0:no: Command authorization is disabled.
					  User is granted access to CLI commands according to his privilege level.
                    4:tacacs: Use remote TACACS+ server(s) for command authorization.
					  If all remote servers are offline, the user is granted access to CLI commands
					  according to his privilege level."
               ::= {     sm48tat4xarpCommandAuthorizationMethodEntry 2 }

    sm48tat4xarpCommandAuthorizationMethodCmdLvl OBJECT-TYPE
               SYNTAX      Integer32
               MAX-ACCESS  read-write
               STATUS      current
               DESCRIPTION
                   "Authorize all commands with a privilege level higher than or equal to this level.
                    Valid values are in the range 0 to 15."
               ::= {     sm48tat4xarpCommandAuthorizationMethodEntry 3 }

    sm48tat4xarpCommandAuthorizationMethodCfgCmd OBJECT-TYPE
               SYNTAX      Integer32
               MAX-ACCESS  read-write
               STATUS      current
               DESCRIPTION
                   "Also authorize configuration commands.
				   0:Disable
				   1:Enable"
               ::= {     sm48tat4xarpCommandAuthorizationMethodEntry 4 }


    sm48tat4xarpAccountingMethodTable OBJECT-TYPE
               SYNTAX      SEQUENCE OF     SM48TAT4XARPAccountingMethodEntry
               MAX-ACCESS  not-accessible
               STATUS      current
               DESCRIPTION
                   "The Accounting Method Config Table."
               ::= {     sm48tat4xarpAuthMethod 3 }

    sm48tat4xarpAccountingMethodEntry OBJECT-TYPE
               SYNTAX          SM48TAT4XARPAccountingMethodEntry
               MAX-ACCESS  not-accessible
               STATUS      current
               DESCRIPTION
                   "The Accounting Method Config Entry."
               INDEX    {    sm48tat4xarpAccountingMethodClient  }
               ::= {     sm48tat4xarpAccountingMethodTable 1 }

    SM48TAT4XARPAccountingMethodEntry             ::= SEQUENCE {
                 sm48tat4xarpAccountingMethodClient       INTEGER,
                 sm48tat4xarpAccountingMethodMethod       Integer32,
                 sm48tat4xarpAccountingMethodCmdLvl       Integer32,
                 sm48tat4xarpAccountingMethodCfgCmd       Integer32
                 }

    sm48tat4xarpAccountingMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sm48tat4xarpAccountingMethodEntry 1 }

    sm48tat4xarpAccountingMethodMethod OBJECT-TYPE
               SYNTAX      Integer32
               MAX-ACCESS  read-write
               STATUS      current
               DESCRIPTION
                   "Method can be set to one of the following values:
                    0:no: Accounting is disabled.
                    4:tacacs: Use remote TACACS+ server(s) for accounting."
               ::= {     sm48tat4xarpAccountingMethodEntry 2 }

    sm48tat4xarpAccountingMethodCmdLvl OBJECT-TYPE
               SYNTAX      Integer32
               MAX-ACCESS  read-write
               STATUS      current
               DESCRIPTION
                   "Enable accounting of all commands with a privilege level higher than or equal to this level.
                    Valid values are in the range 0 to 15. Leave the field empty to disable command accounting."
               ::= {     sm48tat4xarpAccountingMethodEntry 3 }

    sm48tat4xarpAccountingMethodCfgCmd OBJECT-TYPE
               SYNTAX      Integer32
               MAX-ACCESS  read-write
               STATUS      current
               DESCRIPTION
                   "Enable exec (login) accounting.
				   0:Disable
				   1:Enable"
               ::= {     sm48tat4xarpAccountingMethodEntry 4 }

-- sm48tat4xarpTELNET                                                 OBJECT IDENTIFIER ::= { sm48tat4xarpSecurity 10 }

-- sm48tat4xarpTELNETPort OBJECT-TYPE
--   SYNTAX      Integer32(1..65535)
--   MAX-ACCESS  read-write
--   STATUS      current
--   DESCRIPTION
--       "TELNET service port number.
--        range : 1-65535, default : 23."
--   ::= { sm48tat4xarpTELNET 1 }

-- =======================================================================================================================
sm48tat4xarpMaintenance                                           OBJECT IDENTIFIER ::= { sm48tat4xarpProductId 4 }

sm48tat4xarpSoftware                      OBJECT IDENTIFIER   ::= {  sm48tat4xarpMaintenance 3 }
sm48tat4xarpConfig                        OBJECT IDENTIFIER   ::= {  sm48tat4xarpMaintenance 4 }

--
-- =======================================================================================================================
-- Objects in the sm48tat4xarpMaintenance Group
-- =======================================================================================================================
    sm48tat4xarpRestartDevice OBJECT-TYPE
               SYNTAX      ActivateCmd
               MAX-ACCESS  read-write
               STATUS      current
               DESCRIPTION
                   "Command to restart the device."
               DEFVAL  { noAction }
               ::= {     sm48tat4xarpMaintenance 1 }

    sm48tat4xarpFactoryDefaults OBJECT-TYPE
               SYNTAX      ActivateCmd
               MAX-ACCESS  read-write
               STATUS      current
               DESCRIPTION
                   "Reset the configuration to Factory Defaults keep-ip."
               DEFVAL  { noAction }
               ::= {     sm48tat4xarpMaintenance 2 }

--sm48tat4xarpSoftware

    sm48tat4xarpSoftwareUsername OBJECT-TYPE
               SYNTAX       DisplayString
               MAX-ACCESS   read-write
               STATUS       current
               DESCRIPTION
                    "Get/Set the username for 'tftp' firmware upgrading."
               ::= {     sm48tat4xarpSoftware 1 }

    sm48tat4xarpSoftwarePassword OBJECT-TYPE
               SYNTAX       DisplayString
               MAX-ACCESS   read-write
               STATUS       current
               DESCRIPTION
                    "Get/Set the password for 'tftp' firmware upgrading."
               ::= {     sm48tat4xarpSoftware 2 }

    sm48tat4xarpSoftwareIpAddress OBJECT-TYPE
               SYNTAX       IpAddress
               MAX-ACCESS   read-write
               STATUS       current
               DESCRIPTION
                    "Get/Set the firmware tftp server."
               ::= {     sm48tat4xarpSoftware 3 }

    sm48tat4xarpSoftwareFileName OBJECT-TYPE
               SYNTAX       DisplayString
               MAX-ACCESS   read-write
               STATUS       current
               DESCRIPTION
                    "Get/Set the path and filename for firmware upgrading."
               ::= {     sm48tat4xarpSoftware 4 }

    sm48tat4xarpSoftwareUpgradeCmd OBJECT-TYPE
               SYNTAX       INTEGER  {  noAction ( 0 ),
                                        tftpUpgrade ( 1 ),
                                        ftpUpgrade ( 2 )
                                     }
               MAX-ACCESS   read-write
               STATUS       current
               DESCRIPTION
                    "Firmware upgrade command.
                     noAction(0 )- do nothing   (read only).
                     tftpUpgrade (1) - activate 'tftp' firmware upgrade"

               DEFVAL  { noAction }
               ::= {     sm48tat4xarpSoftware 5 }

    sm48tat4xarpSoftwareImageSelectionCmd OBJECT-TYPE
               SYNTAX       ActivateCmd
               MAX-ACCESS   read-write
               STATUS       current
               DESCRIPTION
                    "Activate firmware image selection.
                     noAction(0) - do nothing - returned upon get.
                     activate(1) - activate firmware image selection."
               DEFVAL  { noAction }
               ::= {     sm48tat4xarpSoftware 6 }

    sm48tat4xarpSaveStartCmd OBJECT-TYPE
               SYNTAX      ActivateCmd
               MAX-ACCESS  read-write
               STATUS      current
               DESCRIPTION
                   "This copies running-config to startup-config,
                   thereby ensuring that the currently active
                   configuration will be used at the next reboot. "
               DEFVAL  { noAction }
               ::= {     sm48tat4xarpConfig 1 }

    sm48tat4xarpConfigUsername OBJECT-TYPE
               SYNTAX       DisplayString
               MAX-ACCESS   read-write
               STATUS       current
               DESCRIPTION
                    "Get/Set the username for 'tftp' 'upload config' or 'download config'."
               ::= {     sm48tat4xarpConfig 2 }

    sm48tat4xarpConfigPassword OBJECT-TYPE
               SYNTAX       DisplayString
               MAX-ACCESS   read-write
               STATUS       current
               DESCRIPTION
                    "Get/Set the password for 'tftp' 'upload config' or 'download config'."
               ::= {     sm48tat4xarpConfig 3 }

    sm48tat4xarpConfigIpAddress OBJECT-TYPE
               SYNTAX       IpAddress
               MAX-ACCESS   read-write
               STATUS       current
               DESCRIPTION
                    "Get/Set the IP address for 'tftp' 'upload config'
                    or 'download config'."
               ::= {     sm48tat4xarpConfig 4 }

    sm48tat4xarpConfigFilename OBJECT-TYPE
               SYNTAX       DisplayString
               MAX-ACCESS   read-write
               STATUS       current
               DESCRIPTION
                    "Get/Set the filename in switch for 'tftp'
                    'upload config' or 'download config'."
               ::= {     sm48tat4xarpConfig 5 }

    sm48tat4xarpConfigFileTable OBJECT-TYPE
               SYNTAX      SEQUENCE OF     SM48TAT4XARPConfigFileEntry
               MAX-ACCESS  not-accessible
               STATUS      current
               DESCRIPTION
                   "The config file tabe."
               ::= {     sm48tat4xarpConfig 6 }

    sm48tat4xarpConfigFileEntry OBJECT-TYPE
               SYNTAX          SM48TAT4XARPConfigFileEntry
               MAX-ACCESS  not-accessible
               STATUS      current
               DESCRIPTION
                   "an entry in the config file tabe."
               INDEX    {     sm48tat4xarpConfigFileIndex }
               ::= {     sm48tat4xarpConfigFileTable 1 }

    SM48TAT4XARPConfigFileEntry             ::= SEQUENCE {
                sm48tat4xarpConfigFileIndex         Integer32,
                sm48tat4xarpShowConfigFileName      DisplayString,
                sm48tat4xarpActivateConfigCmd       ActivateCmd,
                sm48tat4xarpDeleteConfigCmd         ActivateCmd,
                sm48tat4xarpUploadConfigCmd         INTEGER,
                sm48tat4xarpDownloadConfigCmd       INTEGER
                }

    sm48tat4xarpConfigFileIndex OBJECT-TYPE
               SYNTAX      Integer32(1..255)
               MAX-ACCESS  not-accessible
               STATUS      current
               DESCRIPTION
                   "The config file index."
               ::= {     sm48tat4xarpConfigFileEntry 1 }

    sm48tat4xarpShowConfigFileName OBJECT-TYPE
               SYNTAX      DisplayString
               MAX-ACCESS  read-write
               STATUS      current
               DESCRIPTION
                   "Shows the config file name. Without config filename:'NewConfig'
                   is temp file when 'activate download
                   config' can 'create new file' and 'change create filename'."
               ::= {     sm48tat4xarpConfigFileEntry 2 }

    sm48tat4xarpActivateConfigCmd OBJECT-TYPE
               SYNTAX       ActivateCmd
               MAX-ACCESS   read-write
               STATUS       current
               DESCRIPTION
                    "Activate config command.
                     noAction(0) : do nothing  (read only).
                     activate(1) : activate the config"
               DEFVAL  { noAction }
               ::= {     sm48tat4xarpConfigFileEntry 3 }

    sm48tat4xarpDeleteConfigCmd OBJECT-TYPE
               SYNTAX       ActivateCmd
               MAX-ACCESS   read-write
               STATUS       current
               DESCRIPTION
                    "Delete config command.
                     noAction(0) : do nothing  (read only).
                     activate(1) : delete the config"
               DEFVAL  { noAction }
               ::= {     sm48tat4xarpConfigFileEntry 4 }

    sm48tat4xarpDownloadConfigCmd OBJECT-TYPE
               SYNTAX       INTEGER  {  noAction ( 0 ),
                                        tftpUpload ( 1 )
                                        --ftpUpload ( 2 )
                                     }
               MAX-ACCESS   read-write
               STATUS       current
               DESCRIPTION
                    "Download config command.
                     noAction   (0) - do nothing   (read only).
                     tftpUpload (1) - activate 'tftp' config download."
               DEFVAL  { noAction }
               ::= {     sm48tat4xarpConfigFileEntry 5 }

    sm48tat4xarpUploadConfigCmd OBJECT-TYPE
               SYNTAX       INTEGER  {  noAction ( 0 ),
                                        tftpDownload ( 1 )
                                        --ftpDownload ( 2 )
                                     }
               MAX-ACCESS   read-write
               STATUS       current
               DESCRIPTION
                    "Upload config command.
                     noAction   (0) - do nothing   (read only).
                     tftpDownload (1) - activate 'tftp' config upload.
					 For merge/replace running-config:
					 1:merge
					 3:replace"
               DEFVAL  { noAction }
               ::= {     sm48tat4xarpConfigFileEntry 6 }

-- =======================================================================================================================
sm48tat4xarpDiagnostics                                           OBJECT IDENTIFIER ::= { sm48tat4xarpMaintenance 5 }

sm48tat4xarpPingIpAddress OBJECT-TYPE
   SYNTAX      IpAddress
   MAX-ACCESS  read-write
   STATUS      current
   DESCRIPTION
       " The destination IP Address. "
   ::= { sm48tat4xarpDiagnostics 1 }

sm48tat4xarpPingSize OBJECT-TYPE
   SYNTAX      Integer32(60..1400)
   MAX-ACCESS  read-write
   STATUS      current
   DESCRIPTION
       " Size of ICMP echo packet.
         range : 60-1400, default : 64. "
   ::= { sm48tat4xarpDiagnostics 2 }

sm48tat4xarpDoPingConfig OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sm48tat4xarpDiagnostics 3 }

sm48tat4xarpPingResult OBJECT-TYPE
   SYNTAX      DisplayString
   MAX-ACCESS  read-only
   STATUS      current
   DESCRIPTION
       " Show ping result. "
   ::= { sm48tat4xarpDiagnostics 4 }

sm48tat4xarpPing6IpAddress OBJECT-TYPE
   SYNTAX      DisplayString
   MAX-ACCESS  read-write
   STATUS      current
   DESCRIPTION
       " The destination IPv6 Address. "
   ::= { sm48tat4xarpDiagnostics 5 }

sm48tat4xarpPing6Size OBJECT-TYPE
   SYNTAX      Integer32(60..1400)
   MAX-ACCESS  read-write
   STATUS      current
   DESCRIPTION
       " Size of ICMP echo packet.
         range : 60-1400. "
   ::= { sm48tat4xarpDiagnostics 6 }

sm48tat4xarpPing6EgressInterface OBJECT-TYPE
   SYNTAX      Integer32(1..4095)
   MAX-ACCESS  read-write
   STATUS      current
   DESCRIPTION
       "The VLAN ID (VID) of the specific egress IPv6 interface which ICMP packet goes."
   ::= { sm48tat4xarpDiagnostics 7 }

sm48tat4xarpDoPing6Config OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sm48tat4xarpDiagnostics 8 }

sm48tat4xarpPing6Result OBJECT-TYPE
   SYNTAX      DisplayString
   MAX-ACCESS  read-only
   STATUS      current
   DESCRIPTION
       " Show ping result. "
   ::= { sm48tat4xarpDiagnostics 9 }

sm48tat4xarptracerouteIpAddress OBJECT-TYPE
   SYNTAX      IpAddress
   MAX-ACCESS  read-write
   STATUS      current
   DESCRIPTION
       " The destination IP Address. "
   ::= { sm48tat4xarpDiagnostics 10 }

--sm48tat4xarptracerouteProtocol OBJECT-TYPE
--   SYNTAX      Integer32(0..2)
--   MAX-ACCESS  read-write
--   STATUS      current
--   DESCRIPTION
--       " Specify protocol including icmp=0, udp=1 and tcp=2.
--         range : 0-2, default : 0. "
--   ::= { sm48tat4xarpDiagnostics 11 }

sm48tat4xarptracerouteWaittime OBJECT-TYPE
   SYNTAX      Integer32(1..60)
   MAX-ACCESS  read-write
   STATUS      current
   DESCRIPTION
       " Specify wait time for waiting probe packets come back.
         range : 1-60(sec), default : 5(sec). "
   ::= { sm48tat4xarpDiagnostics 12 }

sm48tat4xarptracerouteMaxTTL OBJECT-TYPE
   SYNTAX      Integer32(1..255)
   MAX-ACCESS  read-write
   STATUS      current
   DESCRIPTION
       " Specify max TTL.
         range : 1-255, default : 30. "
   ::= { sm48tat4xarpDiagnostics 13 }

sm48tat4xarptracerouteNqueries OBJECT-TYPE
   SYNTAX      Integer32(1..10)
   MAX-ACCESS  read-write
   STATUS      current
   DESCRIPTION
       " Specify number of probe packets.
         range : 1-10, default : 3. "
   ::= { sm48tat4xarpDiagnostics 14 }

sm48tat4xarpDotracerouteConfig OBJECT-TYPE
   SYNTAX      Integer32(1)
   MAX-ACCESS  read-write
   STATUS      current
   DESCRIPTION
       "Do traceroute-config.
         Get this OID always return zero.
         1 - ping. Uses the traceroute program to get
         ip address of the middle gateway. "
   ::= { sm48tat4xarpDiagnostics 15 }

sm48tat4xarptracerouteResult OBJECT-TYPE
   SYNTAX      DisplayString
   MAX-ACCESS  read-only
   STATUS      current
   DESCRIPTION
       " Show traceroute result. "
   ::= { sm48tat4xarpDiagnostics 16 }

sm48tat4xarpCableDiagnostics                                           OBJECT IDENTIFIER ::= { sm48tat4xarpDiagnostics 17 }

sm48tat4xarpCableDiagnosticsTest OBJECT-TYPE
   SYNTAX      Integer32
   MAX-ACCESS  read-write
   STATUS      current
   DESCRIPTION
       "Run Cable Diagnostics.
        port, range : 1 - port number."
   ::= { sm48tat4xarpCableDiagnostics 1 }

sm48tat4xarpCableDiagnosticsTable OBJECT-TYPE
   SYNTAX      SEQUENCE OF SM48TAT4XARPCableDiagnosticsEntry
   MAX-ACCESS  not-accessible
   STATUS      current
   DESCRIPTION
       " "
   ::= { sm48tat4xarpCableDiagnostics 2 }

sm48tat4xarpCableDiagnosticsEntry OBJECT-TYPE
   SYNTAX      SM48TAT4XARPCableDiagnosticsEntry
   MAX-ACCESS  not-accessible
   STATUS      current
   DESCRIPTION
       " "
   INDEX    { sm48tat4xarpCableDiagnosticsPort  }
   ::= { sm48tat4xarpCableDiagnosticsTable 1 }

SM48TAT4XARPCableDiagnosticsEntry ::= SEQUENCE {
   sm48tat4xarpCableDiagnosticsPort        Integer32,
   sm48tat4xarpCableDiagnosticsLinkStatus  DisplayString,
   sm48tat4xarpCableDiagnosticsTestResult  DisplayString,
   sm48tat4xarpCableDiagnosticsLength      DisplayString
}

sm48tat4xarpCableDiagnosticsPort OBJECT-TYPE
   SYNTAX      Integer32(1..65535)
   MAX-ACCESS  not-accessible
   STATUS      current
   DESCRIPTION
       "port index"
   ::= { sm48tat4xarpCableDiagnosticsEntry 1 }

sm48tat4xarpCableDiagnosticsLinkStatus OBJECT-TYPE
   SYNTAX      DisplayString
   MAX-ACCESS  read-only
   STATUS      current
   DESCRIPTION
       "The status of the cable."
   ::= { sm48tat4xarpCableDiagnosticsEntry 2 }

sm48tat4xarpCableDiagnosticsTestResult OBJECT-TYPE
   SYNTAX      DisplayString
   MAX-ACCESS  read-only
   STATUS      current
   DESCRIPTION
       "Test Result of the cable."
   ::= { sm48tat4xarpCableDiagnosticsEntry 3 }

sm48tat4xarpCableDiagnosticsLength OBJECT-TYPE
   SYNTAX      DisplayString
   MAX-ACCESS  read-only
   STATUS      current
   DESCRIPTION
       "The length (in meters) of the cable."
   ::= { sm48tat4xarpCableDiagnosticsEntry 4 }

sm48tat4xarpSwitchRebootSchedule OBJECT IDENTIFIER ::= { sm48tat4xarpMaintenance 6 }

sm48tat4xarpSwitchRebootMode OBJECT-TYPE
   SYNTAX      Integer32
   MAX-ACCESS  read-write
   STATUS      current
   DESCRIPTION
       "Switch Reboot Mode.
	    0:disable
		1:enable"
   ::= { sm48tat4xarpSwitchRebootSchedule 1 }

sm48tat4xarpSwitchRebootTimeTable OBJECT-TYPE
   SYNTAX      SEQUENCE OF SM48TAT4XARPSwitchRebootTimeEntry
   MAX-ACCESS  not-accessible
   STATUS      current
   DESCRIPTION
       " Configure the Switch reboot time. "
   ::= { sm48tat4xarpSwitchRebootSchedule 2 }

sm48tat4xarpSwitchRebootTimeEntry OBJECT-TYPE
   SYNTAX      SM48TAT4XARPSwitchRebootTimeEntry
   MAX-ACCESS  not-accessible
   STATUS      current
   DESCRIPTION
       " "
   INDEX    { sm48tat4xarpSwitchRebootWeekIndex  }
   ::= { sm48tat4xarpSwitchRebootTimeTable 1 }

SM48TAT4XARPSwitchRebootTimeEntry ::= SEQUENCE {
   sm48tat4xarpSwitchRebootWeekIndex	       Integer32,
   sm48tat4xarpSwitchRebootTimeHour           Integer32,
   sm48tat4xarpSwitchRebootTimeMinute         Integer32
}

sm48tat4xarpSwitchRebootWeekIndex OBJECT-TYPE
   SYNTAX      Integer32 (1..7)
   MAX-ACCESS  not-accessible
   STATUS      current
   DESCRIPTION
       "Switch reboot week index.
	   1: Sun, 2: Mon, 3:Tue, 4: Wed, 5: Thu, 6: Fri, 7: Sat"
   ::= { sm48tat4xarpSwitchRebootTimeEntry 1 }

sm48tat4xarpSwitchRebootTimeHour OBJECT-TYPE
   SYNTAX      Integer32 (-1..23)
   MAX-ACCESS  read-write
   STATUS      current
   DESCRIPTION
       "Switch Reboot Time (Hour). Range: 0-23.
	   -1:disable"
   ::= { sm48tat4xarpSwitchRebootTimeEntry 2 }

sm48tat4xarpSwitchRebootTimeMinute OBJECT-TYPE
   SYNTAX      Integer32 (-1..55)
   MAX-ACCESS  read-write
   STATUS      current
   DESCRIPTION
       "Switch Reboot Time (Minute). Range:0,5,10,...,55.
	   -1:disable"
   ::= { sm48tat4xarpSwitchRebootTimeEntry 3 }

sm48tat4xarpiPerf OBJECT IDENTIFIER ::= { sm48tat4xarpMaintenance 7 }

sm48tat4xarpiPerfMethod OBJECT-TYPE
   SYNTAX      Integer32
   MAX-ACCESS  read-write
   STATUS      current
   DESCRIPTION
       "The measuring method of iPerf.
	    2:iPerf version 2
		3:iPerf version 3"
   ::= { sm48tat4xarpiPerf 2 }

sm48tat4xarpiPerfHost OBJECT-TYPE
   SYNTAX      IpAddress
   MAX-ACCESS  read-write
   STATUS      current
   DESCRIPTION
       "The address of iPerf server. "
   ::= { sm48tat4xarpiPerf 3 }

sm48tat4xarpiPerfPort OBJECT-TYPE
   SYNTAX      Integer32
   MAX-ACCESS  read-write
   STATUS      current
   DESCRIPTION
       "The listen port of iPerf server. The default value is 5001 for iPerf, 5201 for iPerf3. "
   ::= { sm48tat4xarpiPerf 4 }

sm48tat4xarpiPerfTime OBJECT-TYPE
   SYNTAX      Integer32
   MAX-ACCESS  read-write
   STATUS      current
   DESCRIPTION
       "The time in seconds to transmit for (default 10 secs). "
   ::= { sm48tat4xarpiPerf 5 }

sm48tat4xarpiPerfInterval OBJECT-TYPE
   SYNTAX      Integer32
   MAX-ACCESS  read-write
   STATUS      current
   DESCRIPTION
       "The time in seconds between periodic bandwidth reports (default no periodic reports). "
   ::= { sm48tat4xarpiPerf 6 }

sm48tat4xarpiPerfTTL OBJECT-TYPE
   SYNTAX      Integer32
   MAX-ACCESS  read-write
   STATUS      current
   DESCRIPTION
       "The time-to-live, for multicast (default 1). "
   ::= { sm48tat4xarpiPerf 7 }

sm48tat4xarpiPerfStart OBJECT-TYPE
   SYNTAX      Integer32
   MAX-ACCESS  read-write
   STATUS      current
   DESCRIPTION
       "Start iPerf
	   1:Start."
   ::= { sm48tat4xarpiPerf 8 }

sm48tat4xarpiPerfResult OBJECT-TYPE
   SYNTAX      DisplayString
   MAX-ACCESS  read-only
   STATUS      current
   DESCRIPTION
       "Test result of iPerf"
   ::= { sm48tat4xarpiPerf 9 }

-- =======================================================================================================================
sm48tat4xarpTrap                                                  OBJECT IDENTIFIER ::= { sm48tat4xarpProductId 5 }

sm48tat4xarpTrapEvent                                             OBJECT IDENTIFIER ::= { sm48tat4xarpTrap 1 }

sm48tat4xarpEmergency NOTIFICATION-TYPE
  OBJECTS   { sm48tat4xarpInformation }
  STATUS        current
    DESCRIPTION
        "The severity level is Emergency. Emergency conditions."
    ::= { sm48tat4xarpTrapEvent 1 }

sm48tat4xarpAlert NOTIFICATION-TYPE
  OBJECTS   { sm48tat4xarpInformation }
  STATUS        current
    DESCRIPTION
        "The severity level is Alert. Alert conditions."
    ::= { sm48tat4xarpTrapEvent 2 }

sm48tat4xarpCritical NOTIFICATION-TYPE
  OBJECTS   { sm48tat4xarpInformation }
  STATUS        current
    DESCRIPTION
        "The severity level is Critical. Critical conditions."
    ::= { sm48tat4xarpTrapEvent 3 }

sm48tat4xarpError NOTIFICATION-TYPE
  OBJECTS   { sm48tat4xarpInformation }
  STATUS        current
    DESCRIPTION
        "The severity level is Error. Error conditions."
    ::= { sm48tat4xarpTrapEvent 4 }

sm48tat4xarpWarning NOTIFICATION-TYPE
  OBJECTS   { sm48tat4xarpInformation }
  STATUS        current
    DESCRIPTION
        "The severity level is Warning. Warning conditions."
    ::= { sm48tat4xarpTrapEvent 5 }

sm48tat4xarpNotice NOTIFICATION-TYPE
  OBJECTS   { sm48tat4xarpInformation }
  STATUS        current
    DESCRIPTION
        "The severity level is Notice. Notice conditions."
    ::= { sm48tat4xarpTrapEvent 6 }

sm48tat4xarpInformational NOTIFICATION-TYPE
  OBJECTS   { sm48tat4xarpInformation }
  STATUS        current
    DESCRIPTION
        "The severity level is Informational. Informational conditions."
    ::= { sm48tat4xarpTrapEvent 7 }

sm48tat4xarpDebug NOTIFICATION-TYPE
  OBJECTS   { sm48tat4xarpInformation }
  STATUS        current
    DESCRIPTION
        "The severity level is Debug. Debug conditions."
    ::= { sm48tat4xarpTrapEvent 8 }

sm48tat4xarpTrapVariable                                          OBJECT IDENTIFIER ::= { sm48tat4xarpTrap 2 }

sm48tat4xarpInformation OBJECT-TYPE
    SYNTAX      DisplayString
    MAX-ACCESS  read-only
    STATUS      current
    DESCRIPTION
        "Trap information."
    ::= { sm48tat4xarpTrapVariable 1 }

sm48tat4xarpZTPTrap                                             OBJECT IDENTIFIER ::= { sm48tat4xarpTrap 3 }

sm48tat4xarpZTPTrapEvent                                        OBJECT IDENTIFIER ::= { sm48tat4xarpZTPTrap 0 }

sm48tat4xarpZTPOnboardTrap NOTIFICATION-TYPE
  OBJECTS   { sysObjectID, sm48tat4xarpSnmpSystemVersion, sm48tat4xarpSnmpSystemReadCommunity,
              sm48tat4xarpSnmpSystemWriteCommunity, sm48tat4xarpSystemInfoSeriesNumber,
              sm48tat4xarpSystemInfoHostMACAddress, sm48tat4xarpIPInterfacesIPv4Address }
  STATUS        current
    DESCRIPTION
        "The switch information."
    ::= { sm48tat4xarpZTPTrapEvent 1 }

END
