-- =======================================================================================================================
-- SISPM10403166L-MIB
-- =======================================================================================================================

SISPM10403166L-MIB DEFINITIONS ::= BEGIN

IMPORTS
    DisplayString,MacAddress,TEXTUAL-CONVENTION,RowStatus                                              FROM SNMPv2-TC
    MODULE-COMPLIANCE,OBJECT-GROUP, NOTIFICATION-GROUP                                                 FROM SNMPv2-CONF
    ifIndex                                                                                            FROM IF-MIB
    enterprises,MODULE-IDENTITY,OBJECT-TYPE,NOTIFICATION-TYPE,Unsigned32,Integer32,Counter32,Counter64,IpAddress  FROM SNMPv2-SMI
--  PortList                                                                                           FROM Q-BRIDGE-MIB
    InetAddress, InetAddressType                                                                       FROM INET-ADDRESS-MIB
    OwnerString                                                                                        FROM RMON-MIB
    sysObjectID                                                                                        FROM SNMPv2-MIB
    SnmpAdminString                                                                                    FROM SNMP-FRAMEWORK-MIB;
--  MacAddress FROM BRIDGE-MIB;

transition MODULE-IDENTITY
        LAST-UPDATED "202112300214Z"
        ORGANIZATION "Corp."
        CONTACT-INFO
            " "
        DESCRIPTION "Managed Hardened PoE+ Switch, (24) 10/100/1000Base-T PoE+ ports + (4) 100/1000Base-X SFP + (4) 1G/10G SFP+"
        REVISION      "202112300214Z"
        DESCRIPTION " "
		REVISION      "201405300000Z"
        DESCRIPTION
		"Rev 1.0 Initial version."
        ::= { enterprises 868 }


-- =======================================================================================================================

     OperState ::= TEXTUAL-CONVENTION
       STATUS         current
       DESCRIPTION
                      "Oper state."
       SYNTAX         INTEGER  { up ( 1 ) , down ( 2 ) }

     AdminMode ::= TEXTUAL-CONVENTION
       STATUS      current
       DESCRIPTION
            "The Admin state - default: disable(0)."
       SYNTAX  INTEGER { disable(0), enable(1) }

     AdminMode2 ::= TEXTUAL-CONVENTION
       STATUS      current
       DESCRIPTION
            "The Admin state - default: disable(0)."
       SYNTAX  INTEGER { disable(0), enable(1), notSupported(2) }

     ActivateCmd ::= TEXTUAL-CONVENTION
       STATUS      current
       DESCRIPTION
            "Used to activate commands. default: noAction(0). "
       SYNTAX         INTEGER  {  noAction ( 0 ),
                                  activate ( 1 )
                               }

     KeyType ::= TEXTUAL-CONVENTION
       STATUS      current
       DESCRIPTION
           "The key type specifying the key generated for frames received
            on the port.
            0 : Normal,
            1 : Double Tag,
            2 : IP Address,
            3 : MAC and IP Address."
        SYNTAX      INTEGER  { normal  ( 0 ),
                               doubleTag ( 1 ),
                               ipAddr ( 2 ),
                               macAndIpAddr ( 3 )
                             }

     FrameRate ::= TEXTUAL-CONVENTION
       STATUS      current
       DESCRIPTION
           "The values for frame rate"
       SYNTAX       INTEGER {
                            threeHundredFramesPerSec (0),
                            oneHundredFramesPerSec (1),
                            tenFramesPerSec (2),
                            oneFramePerSec (3),
                            sixFramesPerMin (4),
                            oneFramePerMin  (5),
                            sixFramesPerHour (6)
                            }

     DayOfWeek ::= TEXTUAL-CONVENTION
       STATUS      current
       DESCRIPTION
            "Used to set the days of the week."
       SYNTAX       INTEGER {mon(1),tue(2),wed(3),thur(4),
                             fri(5),sat(6),sun(7) }

     Month ::= TEXTUAL-CONVENTION
       STATUS      current
       DESCRIPTION
            "Used to set the month."
       SYNTAX       INTEGER {jan(1),feb(2),march(3),april(4),
                             may(5),june(6),july(7),aug(8),
                             sept(9),oct(10),nov(11),dec(12)}


switch                                                              OBJECT IDENTIFIER ::= { transition 2 }

sispm10403166lProductLevel1                                         OBJECT IDENTIFIER ::= { switch 80 }
sispm10403166lProductId                                             OBJECT IDENTIFIER ::= { sispm10403166lProductLevel1 4 }

sispm10403166lSystem                                                OBJECT IDENTIFIER ::= { sispm10403166lProductId 1 }

sispm10403166lSystemInformation                                     OBJECT IDENTIFIER ::= { sispm10403166lSystem 1 }

sispm10403166lSystemInfo                                            OBJECT IDENTIFIER ::= { sispm10403166lSystemInformation 1 }

sispm10403166lSystemInfoModelName OBJECT-TYPE
   SYNTAX       DisplayString
   MAX-ACCESS   read-only
   STATUS       current
   DESCRIPTION
       " "
   ::= { sispm10403166lSystemInfo 2 }

sispm10403166lSystemInfoSystemDescript OBJECT-TYPE
   SYNTAX       DisplayString
   MAX-ACCESS   read-only
   STATUS       current
   DESCRIPTION
       " "
   ::= { sispm10403166lSystemInfo 3 }

sispm10403166lSystemInfoLocation OBJECT-TYPE
   SYNTAX       DisplayString
   MAX-ACCESS   read-write
   STATUS       current
   DESCRIPTION
       " "
   ::= { sispm10403166lSystemInfo 4 }

sispm10403166lSystemInfoContact OBJECT-TYPE
   SYNTAX       DisplayString
   MAX-ACCESS   read-write
   STATUS       current
   DESCRIPTION
       " "
   ::= { sispm10403166lSystemInfo 5 }

sispm10403166lSystemInfoSystemName OBJECT-TYPE
   SYNTAX       DisplayString
   MAX-ACCESS   read-write
   STATUS       current
   DESCRIPTION
       " "
   ::= { sispm10403166lSystemInfo 6 }

sispm10403166lSystemInfoSystemDate OBJECT-TYPE
   SYNTAX       DisplayString
   MAX-ACCESS   read-only
   STATUS       current
   DESCRIPTION
       " "
   ::= { sispm10403166lSystemInfo 7 }

sispm10403166lSystemInfoSystemUptime OBJECT-TYPE
   SYNTAX       DisplayString
   MAX-ACCESS   read-only
   STATUS       current
   DESCRIPTION
       " "
   ::= { sispm10403166lSystemInfo 8 }

sispm10403166lSystemInfoBootloaderVersion OBJECT-TYPE
   SYNTAX       DisplayString
   MAX-ACCESS   read-only
   STATUS       current
   DESCRIPTION
       " "
   ::= { sispm10403166lSystemInfo 9 }

sispm10403166lSystemInfoFirmwareVersion OBJECT-TYPE
   SYNTAX       DisplayString
   MAX-ACCESS   read-only
   STATUS       current
   DESCRIPTION
       " "
   ::= { sispm10403166lSystemInfo 10 }

sispm10403166lSystemInfoHardwareVersion OBJECT-TYPE
   SYNTAX       DisplayString
   MAX-ACCESS   read-only
   STATUS       current
   DESCRIPTION
       " "
   ::= { sispm10403166lSystemInfo 11 }

sispm10403166lSystemInfoMechanicalVersion OBJECT-TYPE
   SYNTAX       DisplayString
   MAX-ACCESS   read-only
   STATUS       current
   DESCRIPTION
       " "
   ::= { sispm10403166lSystemInfo 12 }

sispm10403166lSystemInfoSeriesNumber OBJECT-TYPE
   SYNTAX       DisplayString
   MAX-ACCESS   read-only
   STATUS       current
   DESCRIPTION
       " "
   ::= { sispm10403166lSystemInfo 13 }

sispm10403166lSystemInfoHostMACAddress OBJECT-TYPE
   SYNTAX       DisplayString
   MAX-ACCESS   read-only
   STATUS       current
   DESCRIPTION
       " "
   ::= { sispm10403166lSystemInfo 14 }

sispm10403166lSystemInfoMemory OBJECT-TYPE
   SYNTAX       DisplayString
   MAX-ACCESS   read-only
   STATUS       current
   DESCRIPTION
       " "
   ::= { sispm10403166lSystemInfo 15 }

-- sispm10403166lSystemInfoFlash OBJECT-TYPE
--   SYNTAX       DisplayString
--   MAX-ACCESS   read-only
--   STATUS       current
--   DESCRIPTION
--       " "
--   ::= { sispm10403166lSystemInfo 16 }

--sispm10403166lSystemInfoFanSpeed OBJECT-TYPE
--   SYNTAX       DisplayString
--   MAX-ACCESS   read-only
--   STATUS       current
--   DESCRIPTION
--       "Fan Speed"
--   ::= { sispm10403166lSystemInfo 17 }

sispm10403166lSystemInfoPowerStatus OBJECT-TYPE
  SYNTAX       DisplayString
  MAX-ACCESS   read-only
  STATUS       current
  DESCRIPTION
      " "
  ::= { sispm10403166lSystemInfo 19 }

-- sispm10403166lSystemInfoPowers OBJECT-TYPE
--   SYNTAX       DisplayString
--   MAX-ACCESS   read-only
--   STATUS       current
--   DESCRIPTION
--       " "
--   ::= { sispm10403166lSystemInfo 20 }

sispm10403166lSystemInfoTemperatureStatus OBJECT-TYPE
  SYNTAX       DisplayString
  MAX-ACCESS   read-only
  STATUS       current
  DESCRIPTION
      " "
  ::= { sispm10403166lSystemInfo 21 }

--sispm10403166lSystemInfoTemperature1 OBJECT-TYPE
--   SYNTAX       DisplayString
--   MAX-ACCESS   read-only
--   STATUS       current
--   DESCRIPTION
--       " "
--   ::= { sispm10403166lSystemInfo 22 }
--
--sispm10403166lSystemInfoTemperature2 OBJECT-TYPE
--   SYNTAX       DisplayString
--   MAX-ACCESS   read-only
--   STATUS       current
--   DESCRIPTION
--       " "
--   ::= { sispm10403166lSystemInfo 23 }

sispm10403166lSystemInfoCPULoad OBJECT-TYPE
   SYNTAX       DisplayString
   MAX-ACCESS   read-only
   STATUS       current
   DESCRIPTION
       "CPU Utilization."
   ::= { sispm10403166lSystemInfo 24 }

sispm10403166lSystemInfoPoEFirmwareVersion OBJECT-TYPE
   SYNTAX       DisplayString
   MAX-ACCESS   read-only
   STATUS       current
   DESCRIPTION
       " "
   ::= { sispm10403166lSystemInfo 32 }

-- sispm10403166lSystemInfoProductionDate OBJECT-TYPE
--    SYNTAX       DisplayString
--    MAX-ACCESS   read-only
--    STATUS       current
--    DESCRIPTION
--        "Production Date."
--    ::= { sispm10403166lSystemInfo 33 }

sispm10403166lSystemTimeConf                                    OBJECT IDENTIFIER ::= { sispm10403166lSystem 2 }

-- sispm10403166lSystemNTP                                      OBJECT IDENTIFIER ::= { sispm10403166lSystemTimeConf  1 }

sispm10403166lSystemTime                                      OBJECT IDENTIFIER ::= { sispm10403166lSystemTimeConf  2 }
sispm10403166lSystemTimeZone                              OBJECT IDENTIFIER ::= { sispm10403166lSystemTime 1 }
sispm10403166lSystemTimeDaylightSaving             OBJECT IDENTIFIER ::= { sispm10403166lSystemTime 2 }
sispm10403166lSystemTimeConfiguration              OBJECT IDENTIFIER ::= { sispm10403166lSystemTime 3 }

    --
-- =======================================================================================================================
-- Objects in the sispm10403166lSystemNTP Group
-- =======================================================================================================================
--    sispm10403166lSystemNTPMode OBJECT-TYPE
--               SYNTAX       INTEGER {useLocal(0),useNTP(1)}
--               MAX-ACCESS   read-write
--               STATUS       current
--               DESCRIPTION
--                   "The system NTP Mode.
--                    useLocal(0) : Use Local Settings,
--                    useNTP(1)   : Use NTP Server."
--               DEFVAL  { useLocal }
--               ::= {     sispm10403166lSystemNTP 1 }
--
--    sispm10403166lSystemNTPServer1    OBJECT-TYPE
--               SYNTAX            DisplayString
--               MAX-ACCESS        read-write
--               STATUS            current
--               DESCRIPTION
--                   "Get/Set the NTP Time Server1.
--                    You can use the IP address or domain name."
--               ::= {     sispm10403166lSystemNTP 2 }
--
--    sispm10403166lSystemNTPServer2    OBJECT-TYPE
--               SYNTAX            DisplayString
--               MAX-ACCESS        read-write
--               STATUS            current
--               DESCRIPTION
--                   "Get/Set the NTP Time Server2.
--                    You can use the IP address or domain name."
--               ::= {     sispm10403166lSystemNTP 3 }
--
--    sispm10403166lSystemNTPServer3    OBJECT-TYPE
--               SYNTAX            DisplayString
--               MAX-ACCESS        read-write
--               STATUS            current
--               DESCRIPTION
--                   "Get/Set the NTP Time Server3.
--                    You can use the IP address or domain name."
--               ::= {     sispm10403166lSystemNTP 4 }
--
--    sispm10403166lSystemNTPServer4    OBJECT-TYPE
--               SYNTAX            DisplayString
--               MAX-ACCESS        read-write
--               STATUS            current
--               DESCRIPTION
--                   "Get/Set the NTP Time Server4.
--                    You can use the IP address or domain name."
--               ::= {     sispm10403166lSystemNTP 5 }
--
--    sispm10403166lSystemNTPServer5    OBJECT-TYPE
--               SYNTAX            DisplayString
--               MAX-ACCESS        read-write
--               STATUS            current
--               DESCRIPTION
--                   "Get/Set the NTP Time Server5.
--                    You can use the IP address or domain name."
--               ::= {     sispm10403166lSystemNTP 6 }


--
-- =======================================================================================================================
-- Objects in the sispm10403166lSystemTime Group
-- =======================================================================================================================
--sispm10403166lSystemTimeZone

    sispm10403166lSystemTimeZoneConf OBJECT-TYPE
               SYNTAX       Integer32(-7200..7201)
               MAX-ACCESS   read-write
               STATUS       current
               DESCRIPTION
                   "Get/Set the NTP Time Zone.
                    The value range is between -7200 and 7201 (minutes).
                    0 : None.
                    -7200 : (GMT-12:00).
                    -6600 : (GMT-11:00).
                    -6000 : (GMT-10:00).
                    -5400 : (GMT-09:00).
                    -4800 : (GMT-08:00)Pacific Time.
                    -4801 : (GMT-08:00)Tijuana, Baja California.
                    -4200 : (GMT-07:00)Arizona.
                    -4201 : (GMT-07:00)Chihuahua, La Paz, Mazatlan - New.
                    -4202 : (GMT-07:00)Chihuahua, La Paz, Mazatlan - Old.
                    -4203 : (GMT-07:00)Mountain Time.
                    -3600 : (GMT-06:00)Central America.
                    -3601 : (GMT-06:00)Central Time.
                    -3602 : (GMT-06:00)Guadalajara, Mexico City, Monterrey - New.
                    -3603 : (GMT-06:00)Guadalajara, Mexico City, Monterrey - Old.
                    -3604 : (GMT-06:00)Saskatchewan.
                    -3000 : (GMT-05:00)Bogota, Lima, Quito, Rio Branco.
                    -3001 : (GMT-05:00)Eastern Time.
                    -3002 : (GMT-05:00)Indiana.
                    -2700 : (GMT-04:30).
                    -2400 : (GMT-04:00)Atlantic Time.
                    -2401 : (GMT-04:00)La Paz.
                    -2402 : (GMT-04:00)Manaus.
                    -2403 : (GMT-04:00)Santiago.
                    -2100 : (GMT-03:30).
                    -1800 : (GMT-03:00)Brasilia.
                    -1801 : (GMT-03:00)Buenos Aires.
                    -1802 : (GMT-03:00)Georgetown.
                    -1803 : (GMT-03:00)Greenland.
                    -1804 : (GMT-03:00)Montevideo.
                    -1805 : (GMT-02:00).
                    -600 : (GMT-01:00)Azores.
                    -601 : (GMT-01:00)Cape Verde Is.
                    1 : (GMT) Casablanca.
                    2 : (GMT) Greenwich Mean Time.
                    3 : (GMT) Monrovia, Reykjavik.
                    600 : (GMT+01:00) Amsterdam, Berlin, Bern, Rome, Stockholm, Vienna.
                    601 : (GMT+01:00) Belgrade, Bratislava, Budapest, Ljubljana, Prague.
                    602 : (GMT+01:00) Brussels, Copenhagen, Madrid, Paris.
                    603 : (GMT+01:00) Sarajevo, Skopje, Warsaw, Zagreb.
                    604 : (GMT+01:00) West Central Africa.
                    1200 : (GMT+02:00) Amman.
                    1201 : (GMT+02:00) Athens, Bucharest, Istanbul.
                    1202 : (GMT+02:00) Beirut.
                    1203 : (GMT+02:00) Cairo.
                    1204 : (GMT+02:00) Harare, Pretoria.
                    1205 : (GMT+02:00) Helsinki, Kyiv, Riga, Sofia, Tallinn, Vilnius.
                    1206 : (GMT+02:00) Jerusalem.
                    1207 : (GMT+02:00) Minsk.
                    1208 : (GMT+02:00) Windhoek.
                    1800 : (GMT+03:00) Baghdad.
                    1801 : (GMT+03:00) Kuwait, Riyadh.
                    1802 : (GMT+03:00) Moscow, St. Petersburg, Volgograd.
                    1803 : (GMT+03:00) Nairobi.
                    1804 : (GMT+03:00) Tbilisi.
                    2100 : (GMT+03:30) Tehran.
                    2400 : (GMT+04:00) Abu Dhabi, Muscat.
                    2401 : (GMT+04:00) Baku.
                    2402 : (GMT+04:00) Caucasus Standard Time.
                    2403 : (GMT+04:00) Port Louis.
                    2404 : (GMT+04:00) Yerevan.
                    2700 : (GMT+04:30) Kabul.
                    3000 : (GMT+05:00) Ekaterinburg.
                    3001 : (GMT+05:00) Islamabad, Karachi.
                    3002 : (GMT+05:00) Tashkent.
                    3300 : (GMT+05:30) Chennai, Kolkata, Mumbai, New Delhi.
                    3301 : (GMT+05:30) Sri Jayawardenepura.
                    3455 : (GMT+05:45) Kathmandu.
                    3600 : (GMT+06:00) Almaty, Novosibirsk.
                    3601 : (GMT+06:00) Astana, Dhaka.
                    3600 : (GMT+06:30) Yangon (Rangoon).
                    4200 : (GMT+07:00) Bangkok, Hanoi, Jakarta.
                    4201 : (GMT+07:00) Krasnoyarsk.
                    4800 : (GMT+08:00) Beijing, Chongqing, Hong Kong, Urumqi.
                    4801 : (GMT+08:00) Irkutsk, Ulaan Bataar.
                    4802 : (GMT+08:00) Kuala Lumpur, Singapore.
                    4803 : (GMT+08:00) Perth.
                    4804 : (GMT+08:00) Taipei.
                    5400 : (GMT+09:00) Osaka, Sapporo, Tokyo.
                    5401 : (GMT+09:00) Seoul.
                    5402 : (GMT+09:00) Yakutsk.
                    5700 : (GMT+09:30) Adelaide.
                    5701 : (GMT+09:30) Darwin.
                    6000 : (GMT+10:00) Brisbane.
                    6001 : (GMT+10:00) Canberra, Melbourne, Sydney.
                    6002 : (GMT+10:00) Guam, Port Moresby.
                    6003 : (GMT+10:00) Hobart.
                    6004 : (GMT+10:00) Vladivostok.
                    6600 : (GMT+11:00) Magadan, Solomon Is., New Caledonia.
                    7200 : (GMT+12:00) Auckland, Wellington.
                    7201 : (GMT+12:00) Fiji, Kamchatka, Marshall Is."
               ::= {     sispm10403166lSystemTimeZone 1 }

    sispm10403166lSystemTimeZoneAcronym OBJECT-TYPE
               SYNTAX       DisplayString
               MAX-ACCESS   read-write
               STATUS       current
               DESCRIPTION
                   "Acronym - User can set the acronym of the time zone.
                    This is a User configurable acronym to identify the time zone.
                    Range : 0 - 16 characters."
               ::= {     sispm10403166lSystemTimeZone 2 }

--sispm10403166lSystemTimeDaylightSaving

    sispm10403166lSystemTimeDaylightSavingMode OBJECT-TYPE
               SYNTAX       INTEGER { disable(0), recurring(1), nonRecurring(2) }
               MAX-ACCESS   read-write
               STATUS       current
               DESCRIPTION
                   "The system Daylight Savings Mode.
                    disable(0)   : Disable.
                    recurring(1) : Recurring
                        - configure the Daylight Saving Time duration
                        to repeat the configuration every year.
                    nonRecurring(2): Non-Recurring - configure the Daylight Saving Time
                        duration for single time configuration."
               DEFVAL  { disable }
               ::= {     sispm10403166lSystemTimeDaylightSaving 1 }

    sispm10403166lSystemTimeDaylightSavingStartWeek OBJECT-TYPE
               SYNTAX       DisplayString
               MAX-ACCESS   read-write
               STATUS       current
               DESCRIPTION
                   "Start time Week. Use in Recurring Mode.
                    Range : 1 - 5.
                    Default : 1."
               ::= {     sispm10403166lSystemTimeDaylightSaving 2 }

    sispm10403166lSystemTimeDaylightSavingStartDay OBJECT-TYPE
               SYNTAX       DayOfWeek
               MAX-ACCESS   read-write
               STATUS       current
               DESCRIPTION
                   "Start time Day. Use in Recurring Mode."
               DEFVAL  { mon }
               ::= {     sispm10403166lSystemTimeDaylightSaving 3 }

    sispm10403166lSystemTimeDaylightSavingStartMonth OBJECT-TYPE
               SYNTAX       Month
               MAX-ACCESS   read-write
               STATUS       current
               DESCRIPTION
                   "Start time Month."
               DEFVAL  { jan }
               ::= {     sispm10403166lSystemTimeDaylightSaving 4 }

    sispm10403166lSystemTimeDaylightSavingStartDate OBJECT-TYPE
               SYNTAX       Integer32 (1..31)
               MAX-ACCESS   read-write
               STATUS       current
               DESCRIPTION
                   "Start time Date. Use in Non-Recurring Mode.
                    Range : 1 - 31.
                    Default : 1."
               ::= {     sispm10403166lSystemTimeDaylightSaving 5 }

    sispm10403166lSystemTimeDaylightSavingStartYear OBJECT-TYPE
               SYNTAX       Integer32 (2000..2097)
               MAX-ACCESS   read-write
               STATUS       current
               DESCRIPTION
                   "Start time Year. Use in Non-Recurring Mode.
                    Range : 2000 - 2097.
                    Default : 2000."
               ::= {     sispm10403166lSystemTimeDaylightSaving 6 }

    sispm10403166lSystemTimeDaylightSavingStartHours OBJECT-TYPE
               SYNTAX       Integer32 (0..23)
               MAX-ACCESS   read-write
               STATUS       current
               DESCRIPTION
                   "Start time Hours.
                     Range : 0 - 23.
                     Default : 0."
               ::= {     sispm10403166lSystemTimeDaylightSaving 7 }

    sispm10403166lSystemTimeDaylightSavingStartMinutes OBJECT-TYPE
               SYNTAX       Integer32 (0..59)
               MAX-ACCESS   read-write
               STATUS       current
               DESCRIPTION
                   "Start time Minutes.
                    Range : 0 - 59.
                    Default : 0."
               ::= {     sispm10403166lSystemTimeDaylightSaving 8 }

    sispm10403166lSystemTimeDaylightSavingEndWeek OBJECT-TYPE
               SYNTAX       DisplayString
               MAX-ACCESS   read-write
               STATUS       current
               DESCRIPTION
                   "End time Week. Use in Recurring Mode.
                    Range : 1 - 5.
                    Default : 1."
               ::= {     sispm10403166lSystemTimeDaylightSaving 9 }

    sispm10403166lSystemTimeDaylightSavingEndDay OBJECT-TYPE
               SYNTAX       DayOfWeek
               MAX-ACCESS   read-write
               STATUS       current
               DESCRIPTION
                   "End time Day. Use in Recurring Mode."
               DEFVAL  { mon }
               ::= {     sispm10403166lSystemTimeDaylightSaving 10 }

    sispm10403166lSystemTimeDaylightSavingEndMonth OBJECT-TYPE
               SYNTAX       Month
               MAX-ACCESS   read-write
               STATUS       current
               DESCRIPTION
                   "End time Month."
              DEFVAL  { jan }
              ::= {     sispm10403166lSystemTimeDaylightSaving 11 }

    sispm10403166lSystemTimeDaylightSavingEndDate OBJECT-TYPE
               SYNTAX       Integer32 (1..31)
               MAX-ACCESS   read-write
               STATUS       current
               DESCRIPTION
                   "End time Date. Use in Non-Recurring Mode.
                    Range : 1 - 31.
                    Default : 1."
               ::= {     sispm10403166lSystemTimeDaylightSaving 12 }

    sispm10403166lSystemTimeDaylightSavingEndYear OBJECT-TYPE
               SYNTAX       Integer32 (2000..2097)
               MAX-ACCESS   read-write
               STATUS       current
               DESCRIPTION
                   "End time Year. Use in Non-Recurring Mode.
                    Range : 2000 - 2097.
                    Default : 2000."
               ::= {     sispm10403166lSystemTimeDaylightSaving 13 }

    sispm10403166lSystemTimeDaylightSavingEndHours OBJECT-TYPE
               SYNTAX       Integer32 (0..23)
               MAX-ACCESS   read-write
               STATUS       current
               DESCRIPTION
                   "End time Hours.
                    Range : 0 - 23.
                    Default : 0."
               ::= {     sispm10403166lSystemTimeDaylightSaving 14 }

    sispm10403166lSystemTimeDaylightSavingEndMinutes OBJECT-TYPE
               SYNTAX       Integer32 (0..59)
               MAX-ACCESS   read-write
               STATUS       current
               DESCRIPTION
                   "End time Minutes.
                    Range : 0 - 59.
                    Default : 0."
               ::= {     sispm10403166lSystemTimeDaylightSaving 15 }

    sispm10403166lSystemTimeDaylightSavingOffset OBJECT-TYPE
               SYNTAX       Integer32 (1..1440)
               MAX-ACCESS   read-write
               STATUS       current
               DESCRIPTION
                   "Offset - the number of minutes to add during Daylight Saving Time.
                    Range : 1 - 1440(Minutes).
                    Default : 1."
               ::= {     sispm10403166lSystemTimeDaylightSaving 16 }

    sispm10403166lSystemTimeConfigurationClockSource OBJECT-TYPE
               SYNTAX       Integer32
               MAX-ACCESS   read-write
               STATUS       current
               DESCRIPTION
                   "0:Use Local Settings.
                    1:Use NTP Server."
	           ::= {     sispm10403166lSystemTimeConfiguration 1}

    sispm10403166lSystemTimeConfigurationSystemDate OBJECT-TYPE
               SYNTAX       DisplayString
               MAX-ACCESS   read-write
               STATUS       current
               DESCRIPTION
                   "System date. Default format:yyyy-mm-dd.
                    When ClockSource is Use Local Settings, you can set this field."
	           ::= {     sispm10403166lSystemTimeConfiguration 2}

    sispm10403166lSystemTimeConfigurationDateFormat OBJECT-TYPE
               SYNTAX       Integer32 (0|1|2)
               MAX-ACCESS   read-write
               STATUS       current
               DESCRIPTION
                   "The date format of the system.
				   0:yyyy-mm-dd
				   1:mm-dd-yyyy
				   2:dd-mm-yyyy"
	           ::= {     sispm10403166lSystemTimeConfiguration 3}

    sispm10403166lSystemTimeConfigurationTimeFormat OBJECT-TYPE
               SYNTAX       Integer32 (0|1)
               MAX-ACCESS   read-write
               STATUS       current
               DESCRIPTION
                   "The time format of the system.
				   0:24-hr, format:hh:mm:ss
				   1:12-hr, format:hh:mm:ss am/pm"
	           ::= {     sispm10403166lSystemTimeConfiguration 4}

    sispm10403166lSystemTimeConfigurationSystemTime OBJECT-TYPE
               SYNTAX       DisplayString
               MAX-ACCESS   read-write
               STATUS       current
               DESCRIPTION
                   "System date.
				    24-hr, format:hh:mm:ss
				    12-hr, format:hh:mm:ss am/pm
                    When ClockSource is Use Local Settings, you can set this field."
	           ::= {     sispm10403166lSystemTimeConfiguration 5}

-- =======================================================================================================================
sispm10403166lSystemAccount                                         OBJECT IDENTIFIER ::= { sispm10403166lSystem 3 }

sispm10403166lSystemAccountUsers                                     OBJECT IDENTIFIER  ::= { sispm10403166lSystemAccount 1 }

--
-- =======================================================================================================================
-- Start sispm10403166lUserConfig group
-- =======================================================================================================================
--sispm10403166lUserConfigTable

    sispm10403166lUserConfigTable OBJECT-TYPE
               SYNTAX      SEQUENCE OF     SISPM10403166LUserConfigEntry
               MAX-ACCESS  not-accessible
               STATUS      current
               DESCRIPTION
                   "The User Config Table. "
               ::= {     sispm10403166lSystemAccountUsers 1 }

    sispm10403166lUserConfigEntry OBJECT-TYPE
               SYNTAX          SISPM10403166LUserConfigEntry
               MAX-ACCESS  not-accessible
               STATUS      current
               DESCRIPTION
                   "The User Config Entry."
               INDEX    {    sispm10403166lUserConfigIndex  }
               ::= {     sispm10403166lUserConfigTable 1 }

    SISPM10403166LUserConfigEntry             ::= SEQUENCE {
                 sispm10403166lUserConfigIndex            Integer32,
                 sispm10403166lUserConfigUserName         DisplayString,
                 sispm10403166lUserConfigPassword         DisplayString,
                 sispm10403166lUserConfigPrivilegeLevel   Integer32,
                 sispm10403166lUserConfigRowStatus        RowStatus
                }

    sispm10403166lUserConfigIndex OBJECT-TYPE
               SYNTAX      Integer32 (1..4095)
               MAX-ACCESS  not-accessible
               STATUS      current
               DESCRIPTION
                   "The user Config Index. "
               ::= {     sispm10403166lUserConfigEntry 1 }

    sispm10403166lUserConfigUserName OBJECT-TYPE
               SYNTAX      DisplayString(SIZE (1..31))
               MAX-ACCESS  read-create
               STATUS      current
               DESCRIPTION
                   "A string identifying the user name for the entry.
                    string length: 1-31. "
               ::= {     sispm10403166lUserConfigEntry 2 }

    sispm10403166lUserConfigPassword OBJECT-TYPE
               SYNTAX      DisplayString(SIZE (0..31))
               MAX-ACCESS  read-create
               STATUS      current
               DESCRIPTION
                   "The password of the user.
                    string length: 0-31. "
               ::= {     sispm10403166lUserConfigEntry 3 }

    sispm10403166lUserConfigPrivilegeLevel OBJECT-TYPE
               SYNTAX      Integer32(1..15)
               MAX-ACCESS  read-create
               STATUS      current
               DESCRIPTION
                   "The privilege level of the user.If the privilege level
                    value is 15, it can access all groups.range: 1-15. "
               ::= {     sispm10403166lUserConfigEntry 4 }

    sispm10403166lUserConfigRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sispm10403166lUserConfigEntry 5 }


--
-- =======================================================================================================================
-- Start sispm10403166lPrivilegeLevelConfig group
-- =======================================================================================================================
--sispm10403166lPrivilegeLevelConfigTable

    sispm10403166lPrivilegeLevelConfigTable OBJECT-TYPE
               SYNTAX      SEQUENCE OF     SISPM10403166LPrivilegeLevelConfigEntry
               MAX-ACCESS  not-accessible
               STATUS      current
               DESCRIPTION
                   "The Privilege Level Config Table. "
               ::= {     sispm10403166lSystemAccountUsers 2 }

    sispm10403166lPrivilegeLevelConfigEntry OBJECT-TYPE
               SYNTAX          SISPM10403166LPrivilegeLevelConfigEntry
               MAX-ACCESS  not-accessible
               STATUS      current
               DESCRIPTION
                   "The Privilege Level Config Entry."
               INDEX    {    sispm10403166lPrivilegeLevelIndex  }
               ::= {     sispm10403166lPrivilegeLevelConfigTable 1 }

    SISPM10403166LPrivilegeLevelConfigEntry             ::= SEQUENCE {
                 sispm10403166lPrivilegeLevelIndex                Integer32,
                 sispm10403166lPrivilegeLevelGroupName            DisplayString,
                 sispm10403166lPrivilegeLevelConfigReadOnly       Integer32,
                 sispm10403166lPrivilegeLevelConfigReadWrite      Integer32,
                 sispm10403166lPrivilegeLevelStatusReadOnly       Integer32,
                 sispm10403166lPrivilegeLevelStatusReadWrite      Integer32
                 }

    sispm10403166lPrivilegeLevelIndex OBJECT-TYPE
               SYNTAX      Integer32 (1..4095)
               MAX-ACCESS  not-accessible
               STATUS      current
               DESCRIPTION
                   "The Privilege Level Index. "
               ::= {     sispm10403166lPrivilegeLevelConfigEntry 1 }

    sispm10403166lPrivilegeLevelGroupName OBJECT-TYPE
               SYNTAX      DisplayString
               MAX-ACCESS  read-only
               STATUS      current
               DESCRIPTION
                   "The name identifying the privilege group."
               ::= {     sispm10403166lPrivilegeLevelConfigEntry 2 }

    sispm10403166lPrivilegeLevelConfigReadOnly OBJECT-TYPE
               SYNTAX      Integer32(1..15)
               MAX-ACCESS  read-write
               STATUS      current
               DESCRIPTION
                   "The privilege level of configuration read-only.If the
                    privilege level value is 15,it can access all groups.
                    range: 1-15.  "
               ::= {     sispm10403166lPrivilegeLevelConfigEntry 3 }

    sispm10403166lPrivilegeLevelConfigReadWrite OBJECT-TYPE
               SYNTAX      Integer32(1..15)
               MAX-ACCESS  read-write
               STATUS      current
               DESCRIPTION
                   "The privilege level of configuration/execute read/write.
                    If the privilege level value is 15,it can access all groups.
                    range: 1-15. "
               ::= {     sispm10403166lPrivilegeLevelConfigEntry 4 }

    sispm10403166lPrivilegeLevelStatusReadOnly OBJECT-TYPE
               SYNTAX      Integer32(1..15)
               MAX-ACCESS  read-write
               STATUS      current
               DESCRIPTION
                   "The privilege level of status/statistics read-only.
                    If the privilege level value is 15,it can access all groups.
                    range: 1-15. "
               ::= {     sispm10403166lPrivilegeLevelConfigEntry 5 }

    sispm10403166lPrivilegeLevelStatusReadWrite OBJECT-TYPE
               SYNTAX      Integer32(1..15)
               MAX-ACCESS  read-write
               STATUS      current
               DESCRIPTION
                   "The privilege level of status/statistics read-write.
                    If the privilege level value is 15,it can access all groups.
                    range: 1-15. "
               ::= {     sispm10403166lPrivilegeLevelConfigEntry 6 }
-- =======================================================================================================================
sispm10403166lIP                                                    OBJECT IDENTIFIER ::= { sispm10403166lSystem 4 }

sispm10403166lIPConfigurationBasic OBJECT IDENTIFIER ::= { sispm10403166lIP 1 }

sispm10403166lIPConfigIPv4DHCPClientEnable OBJECT-TYPE
   SYNTAX      Integer32 (0|1)
   MAX-ACCESS  read-write
   STATUS      current
   DESCRIPTION
       "IPv4 DHCP Client Enabled
        0: Disable
        1: Enable"
   ::= {sispm10403166lIPConfigurationBasic 1 }

sispm10403166lIPConfigIPv4Address OBJECT-TYPE
   SYNTAX      DisplayString
   MAX-ACCESS  read-write
   STATUS      current
   DESCRIPTION
       "IPv4 Address."
   ::= {sispm10403166lIPConfigurationBasic 2 }

sispm10403166lIPConfigSubnetMask OBJECT-TYPE
   SYNTAX      DisplayString
   MAX-ACCESS  read-write
   STATUS      current
   DESCRIPTION
       "IPv4 SubnetMask."
   ::= {sispm10403166lIPConfigurationBasic 3 }

sispm10403166lIPConfigGateway OBJECT-TYPE
   SYNTAX      DisplayString
   MAX-ACCESS  read-write
   STATUS      current
   DESCRIPTION
       "IPv4 Gateway."
   ::= {sispm10403166lIPConfigurationBasic 4 }

sispm10403166lIPConfigDNSServer OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sispm10403166lIPConfigurationBasic 5 }

sispm10403166lIPConfigDNSServerValue OBJECT-TYPE
   SYNTAX      DisplayString
   MAX-ACCESS  read-write
   STATUS      current
   DESCRIPTION
       "DNS IPv4 Address or VLAN value."
   ::= {sispm10403166lIPConfigurationBasic 6 }

sispm10403166lIPConfiguration OBJECT IDENTIFIER ::= { sispm10403166lIP 2 }

sispm10403166lMode OBJECT-TYPE
   SYNTAX      Integer32 (0|1)
   MAX-ACCESS  read-write
   STATUS      current
   DESCRIPTION
       "IP Configuration Mode.
        default:0
        0: Host
        1: Router"
   ::= {sispm10403166lIPConfiguration 2 }

sispm10403166lDNSServerSource1 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sispm10403166lIPConfiguration 3 }

sispm10403166lDNSServerSource2 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
		4. DNS configuration is derived from DHCPv6.
		5. DNS configuration is derived from DHCPv6 on specific VLAN.
		"
   ::= {sispm10403166lIPConfiguration 4 }

sispm10403166lDNSServerSource3 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sispm10403166lIPConfiguration 5 }

sispm10403166lDNSServerSource4 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sispm10403166lIPConfiguration 6 }

sispm10403166lDNSServerValue1 OBJECT-TYPE
   SYNTAX      DisplayString
   MAX-ACCESS  read-write
   STATUS      current
   DESCRIPTION
       "DNS IPv4/IPv6 Address or VLAN value."
   ::= {sispm10403166lIPConfiguration 7 }

sispm10403166lDNSServerValue2 OBJECT-TYPE
   SYNTAX      DisplayString
   MAX-ACCESS  read-write
   STATUS      current
   DESCRIPTION
      "DNS IPv4/IPv6 Address or VLAN value."
   ::= {sispm10403166lIPConfiguration 8 }

sispm10403166lDNSServerValue3 OBJECT-TYPE
   SYNTAX      DisplayString
   MAX-ACCESS  read-write
   STATUS      current
   DESCRIPTION
       "DNS IPv4/IPv6 Address or VLAN value."
   ::= {sispm10403166lIPConfiguration 9 }

sispm10403166lDNSServerValue4 OBJECT-TYPE
   SYNTAX      DisplayString
   MAX-ACCESS  read-write
   STATUS      current
   DESCRIPTION
       "DNS IPv4/IPv6 Address or VLAN value."
   ::= {sispm10403166lIPConfiguration 10 }

sispm10403166lDNSProxy OBJECT-TYPE
   SYNTAX      Integer32 (0|1)
   MAX-ACCESS  read-write
   STATUS      current
   DESCRIPTION
       "DNS Proxy enable/disable.
        default:0
        0: disable
        1: enable"
   ::= {sispm10403166lIPConfiguration 11 }


sispm10403166lIPInterfaces OBJECT IDENTIFIER ::= { sispm10403166lIP 3 }

sispm10403166lIPInterfacesDHCPPerPortMode OBJECT-TYPE
   SYNTAX      INTEGER { disable(0), enable(1) }
   MAX-ACCESS  read-write
   STATUS      current
   DESCRIPTION
       "The dhcp per-port mode for the interface.
        0: Disable,
        1: Enable,
        default: Disable. "
   ::= { sispm10403166lIPInterfaces 1 }

sispm10403166lIPInterfacesDHCPPerPortIPRangeLow OBJECT-TYPE
   SYNTAX      IpAddress
   MAX-ACCESS  read-write
   STATUS      current
   DESCRIPTION
       "The dhcp per-port ip low for the interface."
   ::= { sispm10403166lIPInterfaces 2 }

sispm10403166lIPInterfacesDHCPPerPortIPRangeHigh OBJECT-TYPE
   SYNTAX      IpAddress
   MAX-ACCESS  read-write
   STATUS      current
   DESCRIPTION
       "The dhcp per-port ip high for the interface."
   ::= { sispm10403166lIPInterfaces 3 }

sispm10403166lIPInterfacesDHCPPerPortApply OBJECT-TYPE
   SYNTAX      Integer32 (1)
   MAX-ACCESS  read-write
   STATUS      current
   DESCRIPTION
       "1: Apply DHCP Per Port settings."
   ::= { sispm10403166lIPInterfaces 4 }

sispm10403166lIPInterfacesDHCPPerPortVLAN OBJECT-TYPE
   SYNTAX      Integer32 (1..4095)
   MAX-ACCESS  read-write
   STATUS      current
   DESCRIPTION
       "dhcp per-port VLAN."
   ::= { sispm10403166lIPInterfaces 6 }

sispm10403166lIPInterfacesTable OBJECT-TYPE
   SYNTAX      SEQUENCE OF SISPM10403166LIPInterfacesEntry
   MAX-ACCESS  not-accessible
   STATUS      current
   DESCRIPTION
       "A table of IP interface for switch."
    ::= { sispm10403166lIPInterfaces 5 }

sispm10403166lIPInterfacesEntry OBJECT-TYPE
    SYNTAX        SISPM10403166LIPInterfacesEntry
    MAX-ACCESS    not-accessible
    STATUS        current
    DESCRIPTION
        "An entry in the sispm10403166lIPInterfacesTable."
    INDEX        { sispm10403166lIPInterfacesIndex }
    ::= { sispm10403166lIPInterfacesTable 1 }

SISPM10403166LIPInterfacesEntry ::=
    SEQUENCE {
        sispm10403166lIPInterfacesIndex                       Integer32,
        sispm10403166lIPInterfacesVLAN                        Integer32,
        sispm10403166lIPInterfacesIPv4DHCP                    Integer32,
        sispm10403166lIPInterfacesIPv4DHCPFallback            DisplayString,
        sispm10403166lIPInterfacesIPv4DHCPCurrentLease        IpAddress,
        sispm10403166lIPInterfacesIPv4Address                 IpAddress,
        sispm10403166lIPInterfacesIPv4Mask                    Integer32,
	sispm10403166lIPInterfacesIPv6DHCP                    Integer32,
	sispm10403166lIPInterfacesIPv6RapidCommit             Integer32,
	sispm10403166lIPInterfacesIPv6CurrentLease            DisplayString,
        sispm10403166lIPInterfacesIPv6Address                 DisplayString,
        sispm10403166lIPInterfacesIPv6Mask                    Integer32,
	sispm10403166lIPInterfacesRowStatus                   RowStatus
    }

sispm10403166lIPInterfacesIndex OBJECT-TYPE
   SYNTAX      Integer32 (1..128)
   MAX-ACCESS  not-accessible
   STATUS      current
   DESCRIPTION
       "interface table index"
   ::= {sispm10403166lIPInterfacesEntry 1 }

sispm10403166lIPInterfacesVLAN OBJECT-TYPE
   SYNTAX      Integer32 (1..4095)
   MAX-ACCESS  read-write
   STATUS      current
   DESCRIPTION
       "VLAN ID for interface, range: 1-4095."
   ::= {sispm10403166lIPInterfacesEntry 2 }

sispm10403166lIPInterfacesIPv4DHCP OBJECT-TYPE
   SYNTAX      Integer32 (0|1)
   MAX-ACCESS  read-write
   STATUS      current
   DESCRIPTION
       "IPv4 DHCP Setting for interface.
        default:0
        0: disable
        1: enable"
   ::= {sispm10403166lIPInterfacesEntry 3 }

sispm10403166lIPInterfacesIPv4DHCPFallback OBJECT-TYPE
   SYNTAX      DisplayString
   MAX-ACCESS  read-write
   STATUS      current
   DESCRIPTION
       "IPv4 DHCP fallbcak. range: 1-4294967295 seconds."
   ::= {sispm10403166lIPInterfacesEntry 4 }


sispm10403166lIPInterfacesIPv4DHCPCurrentLease OBJECT-TYPE
   SYNTAX      IpAddress
   MAX-ACCESS  read-only
   STATUS      current
   DESCRIPTION
       "IPv4 DHCP Current Lease Address for interface."
   ::= {sispm10403166lIPInterfacesEntry 5 }


sispm10403166lIPInterfacesIPv4Address OBJECT-TYPE
   SYNTAX      IpAddress
   MAX-ACCESS  read-write
   STATUS      current
   DESCRIPTION
       "IPv4 address for interface."
   ::= {sispm10403166lIPInterfacesEntry 6 }

sispm10403166lIPInterfacesIPv4Mask OBJECT-TYPE
   SYNTAX      Integer32 (1..32)
   MAX-ACCESS  read-write
   STATUS      current
   DESCRIPTION
       "IPv4 mask for interface."
   ::= { sispm10403166lIPInterfacesEntry 7 }

sispm10403166lIPInterfacesIPv6DHCP OBJECT-TYPE
   SYNTAX      Integer32 (0|1)
   MAX-ACCESS  read-write
   STATUS      current
   DESCRIPTION
       "IPv6 DHCP Setting for interface.
        default:0
        0: disable
        1: enable"
   ::= {sispm10403166lIPInterfacesEntry 8 }

sispm10403166lIPInterfacesIPv6RapidCommit OBJECT-TYPE
   SYNTAX      Integer32 (0|1)
   MAX-ACCESS  read-write
   STATUS      current
   DESCRIPTION
       "Enable the DHCPv6 Rapid-Commit option.
        default:0
        0: disable
        1: enable"
   ::= {sispm10403166lIPInterfacesEntry 9 }

sispm10403166lIPInterfacesIPv6CurrentLease OBJECT-TYPE
   SYNTAX      DisplayString
   MAX-ACCESS  read-only
   STATUS      current
   DESCRIPTION
       "IPv6 DHCP Current Lease Address for interface."
   ::= {sispm10403166lIPInterfacesEntry 10 }


sispm10403166lIPInterfacesIPv6Address OBJECT-TYPE
   SYNTAX      DisplayString (SIZE (0..30))
   MAX-ACCESS  read-write
   STATUS      current
   DESCRIPTION
       "IPv6 address for interface."
   ::= { sispm10403166lIPInterfacesEntry 11 }

sispm10403166lIPInterfacesIPv6Mask OBJECT-TYPE
   SYNTAX      Integer32 (1..128)
   MAX-ACCESS  read-write
   STATUS      current
   DESCRIPTION
       "IPv6 mask for interface."
   ::= { sispm10403166lIPInterfacesEntry 12 }

sispm10403166lIPInterfacesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sispm10403166lIPInterfacesEntry 13 }


sispm10403166lIPRoutes OBJECT IDENTIFIER ::= { sispm10403166lIP 4 }

sispm10403166lIPRoutesTable OBJECT-TYPE
   SYNTAX      SEQUENCE OF SISPM10403166LIPRoutesEntry
   MAX-ACCESS  not-accessible
   STATUS      current
   DESCRIPTION
       "IP routes table for switch."
    ::= { sispm10403166lIPRoutes 1 }

sispm10403166lIPRoutesEntry OBJECT-TYPE
    SYNTAX        SISPM10403166LIPRoutesEntry
    MAX-ACCESS    not-accessible
    STATUS        current
    DESCRIPTION
        "Entry in the sispm10403166lIPRoutesTable."
    INDEX        { sispm10403166lIPRoutesIndex }
    ::= { sispm10403166lIPRoutesTable 1 }

SISPM10403166LIPRoutesEntry ::=
    SEQUENCE {
        sispm10403166lIPRoutesIndex                       Integer32,
        sispm10403166lIPRoutesNetwork                     DisplayString,
        sispm10403166lIPRoutesMaskLength                  Integer32,
        sispm10403166lIPRoutesGateway                     DisplayString,
        sispm10403166lIPRoutesNextHopVLAN                 Integer32,
	sispm10403166lIPRoutesRowStatus                   RowStatus
    }

sispm10403166lIPRoutesIndex OBJECT-TYPE
   SYNTAX      Integer32 (1..32)
   MAX-ACCESS  not-accessible
   STATUS      current
   DESCRIPTION
       "routes table index"
   ::= {sispm10403166lIPRoutesEntry 2 }

sispm10403166lIPRoutesNetwork OBJECT-TYPE
   SYNTAX      DisplayString (SIZE (0..30))
   MAX-ACCESS  read-write
   STATUS      current
   DESCRIPTION
       "IPv4/IPv6 Network address.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry.
        If Set IPRoutesNetwork, please also set IPRoutesMaskLength, IPRoutesGateway, IPRoutesNextHopVLAN."
   ::= {sispm10403166lIPRoutesEntry 3 }

sispm10403166lIPRoutesMaskLength OBJECT-TYPE
   SYNTAX      Integer32 (1..32)
   MAX-ACCESS  read-write
   STATUS      current
   DESCRIPTION
       "IPv4/IPv6 mask length.
        Please set IPRoutesNetwork first.
        Note: All entries in routes table will be sort by 1.network address 2.mask length 3. gateway 4. next hop VLAN, if you add/modify an entry, all entries will be reordered. Please check all entries in table to find your modified entry after set/add an entry."
   ::= { sispm10403166lIPRoutesEntry 4 }

sispm10403166lIPRoutesGateway OBJECT-TYPE
   SYNTAX      DisplayString (SIZE (0..30))
   MAX-ACCESS  read-write
   STATUS      current
   DESCRIPTION
       "IPv4/IPv6 Gateway.
        Please set IPRoutesNetwork first.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry."
   ::= {sispm10403166lIPRoutesEntry 5 }

sispm10403166lIPRoutesNextHopVLAN OBJECT-TYPE
   SYNTAX      Integer32 (1..4095)
   MAX-ACCESS  read-write
   STATUS      current
   DESCRIPTION
       "Next Hop VLAN ID, range: 1-4095.
        Please set IPRoutesNetwork first.
        This entry only work when 1.network address is IPv6, 2.Gateway is link-local, 3.Interface of specific VLAN ID is IPv6.
        Note: All entries in routes table will be sort by 1.network address 2.mask length 3. gateway 4. next hop VLAN, if you add/modify an entry, all entries will be reordered. Please check all entries in table to find your modified entry after set/add an entry."
   ::= {sispm10403166lIPRoutesEntry 6 }

sispm10403166lIPRoutesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sispm10403166lIPRoutesEntry 7 }

sispm10403166lIPStatusInterface OBJECT IDENTIFIER ::= { sispm10403166lIP 8 }

sispm10403166lIPStatusInterfaceTable OBJECT-TYPE
              SYNTAX      SEQUENCE OF     SISPM10403166LIPStatusInterfaceEntry
              MAX-ACCESS  not-accessible
              STATUS      current
              DESCRIPTION
                       "The system IP Status table to show all IP interfaces."
                   ::= {     sispm10403166lIPStatusInterface 1 }

    sispm10403166lIPStatusInterfaceEntry OBJECT-TYPE
               SYNTAX          SISPM10403166LIPStatusInterfaceEntry
               MAX-ACCESS  not-accessible
               STATUS      current
               DESCRIPTION
                       "An entry in the IP Status Table."
               INDEX    {    sispm10403166lIPStatusInterfaceIndex  }
               ::= {     sispm10403166lIPStatusInterfaceTable 1 }

    SISPM10403166LIPStatusInterfaceEntry             ::= SEQUENCE {
            sispm10403166lIPStatusInterfaceIndex         Integer32,
            sispm10403166lIPStatusInterfaceName          DisplayString,
            sispm10403166lIPStatusInterfaceType          DisplayString,
            sispm10403166lIPStatusInterfaceAddress       DisplayString,
            sispm10403166lIPStatusInterfaceStatus        DisplayString
            }

    sispm10403166lIPStatusInterfaceIndex OBJECT-TYPE
               SYNTAX      Integer32(1..1024)
               MAX-ACCESS  not-accessible
               STATUS      current
               DESCRIPTION
                   "The entry of table to show all IP interfaces."
               ::= {     sispm10403166lIPStatusInterfaceEntry 1 }

    sispm10403166lIPStatusInterfaceName OBJECT-TYPE
               SYNTAX      DisplayString
               MAX-ACCESS  read-only
               STATUS      current
               DESCRIPTION
                   "The name of the interface."
               ::= {     sispm10403166lIPStatusInterfaceEntry 2 }

    sispm10403166lIPStatusInterfaceType OBJECT-TYPE
               SYNTAX      DisplayString
               MAX-ACCESS  read-only
               STATUS      current
               DESCRIPTION
                   "The address type of the entry. This may be LINK or IPv4."
               ::= {     sispm10403166lIPStatusInterfaceEntry 3 }

    sispm10403166lIPStatusInterfaceAddress OBJECT-TYPE
               SYNTAX      DisplayString
               MAX-ACCESS  read-only
               STATUS      current
               DESCRIPTION
                   "The current address of the interface (of the given type)."
               ::= {     sispm10403166lIPStatusInterfaceEntry 4 }

    sispm10403166lIPStatusInterfaceStatus OBJECT-TYPE
               SYNTAX      DisplayString
               MAX-ACCESS  read-only
               STATUS      current
               DESCRIPTION
                   "The status flags of the interface (and/or address)."
               ::= {     sispm10403166lIPStatusInterfaceEntry 5 }

sispm10403166lIPStatusRoute OBJECT IDENTIFIER ::= { sispm10403166lIP 9 }

    sispm10403166lIPStatusRouteTable OBJECT-TYPE
              SYNTAX      SEQUENCE OF     SISPM10403166LIPStatusRouteEntry
              MAX-ACCESS  not-accessible
              STATUS      current
              DESCRIPTION
                       "The IP Status Route table show all routing entries."
                   ::= {     sispm10403166lIPStatusRoute 1 }

    sispm10403166lIPStatusRouteEntry OBJECT-TYPE
               SYNTAX          SISPM10403166LIPStatusRouteEntry
               MAX-ACCESS  not-accessible
               STATUS      current
               DESCRIPTION
                       "an entry in the IP Status route table."
               INDEX    {     sispm10403166lIPStatusRouteIndex  }
               ::= {     sispm10403166lIPStatusRouteTable 1 }

    SISPM10403166LIPStatusRouteEntry             ::= SEQUENCE {
            sispm10403166lIPStatusRouteIndex          Integer32,
            sispm10403166lIPStatusRouteNetwork        DisplayString,
            sispm10403166lIPStatusRouteGateway        DisplayString,
            sispm10403166lIPStatusRouteAddress        DisplayString
     }

    sispm10403166lIPStatusRouteIndex OBJECT-TYPE
               SYNTAX      Integer32(1..2048)
               MAX-ACCESS  not-accessible
               STATUS      current
               DESCRIPTION
                   "The entry of table to show all routing entries."
               ::= {     sispm10403166lIPStatusRouteEntry 1 }

    sispm10403166lIPStatusRouteNetwork OBJECT-TYPE
               SYNTAX      DisplayString
               MAX-ACCESS  read-only
               STATUS      current
               DESCRIPTION
                   "The destination IP network or host address of this route."
               ::= {     sispm10403166lIPStatusRouteEntry 2 }

    sispm10403166lIPStatusRouteGateway OBJECT-TYPE
               SYNTAX      DisplayString
               MAX-ACCESS  read-only
               STATUS      current
               DESCRIPTION
                   "The gateway address of this route."
               ::= {     sispm10403166lIPStatusRouteEntry 3 }

    sispm10403166lIPStatusRouteAddress OBJECT-TYPE
               SYNTAX      DisplayString
               MAX-ACCESS  read-only
               STATUS      current
               DESCRIPTION
                   "The route address."
               ::= {     sispm10403166lIPStatusRouteEntry 4 }

sispm10403166lIPStatusNeighborCache OBJECT IDENTIFIER ::= { sispm10403166lIP 10 }

    sispm10403166lIPStatusNeighborCacheTable OBJECT-TYPE
               SYNTAX      SEQUENCE OF     SISPM10403166LIPStatusNeighborCacheEntry
               MAX-ACCESS  not-accessible
               STATUS      current
               DESCRIPTION
                       "The Ip Status Neighbor Cache Table."
                   ::= {     sispm10403166lIPStatusNeighborCache 1 }

    sispm10403166lIPStatusNeighborCacheEntry OBJECT-TYPE
               SYNTAX          SISPM10403166LIPStatusNeighborCacheEntry
               MAX-ACCESS  not-accessible
               STATUS      current
               DESCRIPTION
                       "An entry in the Ip Status Neighbor Cache Table."
               INDEX    {     sispm10403166lIPStatusNeighborCacheIndex  }
               ::= {     sispm10403166lIPStatusNeighborCacheTable 1 }

    SISPM10403166LIPStatusNeighborCacheEntry             ::= SEQUENCE {
            sispm10403166lIPStatusNeighborCacheIndex            Integer32,
            sispm10403166lIPStatusNeighborCacheIPAddress        DisplayString,
            sispm10403166lIPStatusNeighborCacheLinkAddress      DisplayString
            }

    sispm10403166lIPStatusNeighborCacheIndex OBJECT-TYPE
               SYNTAX      Integer32(1..1024)
               MAX-ACCESS  not-accessible
               STATUS      current
               DESCRIPTION
                   "The index for the Ip Status Neighbor Cache Table."
               ::= {     sispm10403166lIPStatusNeighborCacheEntry 1 }

    sispm10403166lIPStatusNeighborCacheIPAddress OBJECT-TYPE
               SYNTAX      DisplayString
               MAX-ACCESS  read-only
               STATUS      current
               DESCRIPTION
                   "The IP address of the entry."
               ::= {     sispm10403166lIPStatusNeighborCacheEntry 2 }

    sispm10403166lIPStatusNeighborCacheLinkAddress OBJECT-TYPE
               SYNTAX      DisplayString
               MAX-ACCESS  read-only
               STATUS      current
               DESCRIPTION
                   "The Link (MAC) address for which a binding to the
                    IP address given exist."
               ::= {     sispm10403166lIPStatusNeighborCacheEntry 3 }

sispm10403166lIPStatusDNSServer OBJECT IDENTIFIER ::= { sispm10403166lIP 11 }

    sispm10403166lIPStatusDNSServerType OBJECT-TYPE
               SYNTAX      DisplayString
               MAX-ACCESS  read-only
               STATUS      current
               DESCRIPTION
                   "The configuration type of DNS server."
               ::= {     sispm10403166lIPStatusDNSServer 1 }

    sispm10403166lIPStatusDNSServerIPAddress OBJECT-TYPE
               SYNTAX      DisplayString
               MAX-ACCESS  read-only
               STATUS      current
               DESCRIPTION
                   "The IP address of the DNS server."
               ::= {     sispm10403166lIPStatusDNSServer 2 }

    sispm10403166lIPStatusDNSServerInterface OBJECT-TYPE
               SYNTAX      DisplayString
               MAX-ACCESS  read-only
               STATUS      current
               DESCRIPTION
                   "The name of the interface."
               ::= {     sispm10403166lIPStatusDNSServer 3 }

-- =======================================================================================================================
sispm10403166lSyslog                                                OBJECT IDENTIFIER ::= { sispm10403166lSystem 5 }

sispm10403166lSyslogConf                                            OBJECT IDENTIFIER ::= { sispm10403166lSyslog 1 }

sispm10403166lSysLogInfo                                            OBJECT IDENTIFIER   ::= {  sispm10403166lSyslog 2 }
--
-- =======================================================================================================================
-- Objects in the sispm10403166lSystemLog Group
-- =======================================================================================================================
--sispm10403166lSystemLogConf

    sispm10403166lSystemLogServerMode OBJECT-TYPE
               SYNTAX      AdminMode
               MAX-ACCESS  read-write
               STATUS      current
               DESCRIPTION
                   "The System log server mode admin state."
               DEFVAL  { disable }
               ::= {     sispm10403166lSyslogConf 1 }

    sispm10403166lSystemLogServerAddress OBJECT-TYPE
               SYNTAX      DisplayString
               MAX-ACCESS  read-write
               STATUS      current
               DESCRIPTION
                   "The Host address of syslog server."
               ::= {     sispm10403166lSyslogConf 2 }

--    sispm10403166lSystemLogSyslogLevel OBJECT-TYPE
--               SYNTAX      INTEGER {
--                    info(0),
--                    warning(1),
--                    error(2)
--               }
--               MAX-ACCESS  read-write
--               STATUS      current
--               DESCRIPTION
--                   "The syslog level.
--                       info(0)   : Info.
--                       warning(1): Warning.
--                       error(2)  : Error."
--               DEFVAL  { info }
--               ::= {     sispm10403166lSyslogConf 3 }

    sispm10403166lSystemLogServerPort OBJECT-TYPE
                 SYNTAX      Integer32(1..65535)
                 MAX-ACCESS  read-write
                 STATUS      current
                 DESCRIPTION
                      "syslog service port number.
                 range : 1-65535, default : 514."
               ::= {     sispm10403166lSyslogConf 4 }

--sispm10403166lSystemLogInfo
    sispm10403166lSystemLogInfoLevel OBJECT-TYPE
               SYNTAX      INTEGER { emergency(0), alert(1), critical(2), error(3), warning(4), notice(5), information(6), debug(7), all(8) }
               MAX-ACCESS  read-write
               STATUS      current
               DESCRIPTION
                  "The Level input field is used to filter the display system log entries.
                   0: Emergency.
                   1: Alert.
                   2: Critical.
                   3: Error.
                   4: Warning.
                   5: Notice.
                   6: Information.
                   7: Debug.
                   8: All."
               DEFVAL  { all }
               ::= {     sispm10403166lSysLogInfo 1 }

    sispm10403166lSystemLogInfoClearLevel OBJECT-TYPE
               SYNTAX      INTEGER { emergency(0), alert(1), critical(2), error(3), warning(4), notice(5), information(6), debug(7), all(8) }
               MAX-ACCESS  read-write
               STATUS      current
               DESCRIPTION
                  "The Clear Level input field is used to specify which
                  system log entries will be cleared.
                  default: 8 (All).
                   0: Emergency.
                   1: Alert.
                   2: Critical.
                   3: Error.
                   4: Warning.
                   5: Notice.
                   6: Information.
                   7: Debug.
                   8: All."
               DEFVAL  { all }
               ::= {     sispm10403166lSysLogInfo 2 }

    sispm10403166lSystemLogInfoClearCmd OBJECT-TYPE
               SYNTAX      ActivateCmd
               MAX-ACCESS  read-write
               STATUS      current
               DESCRIPTION
                  "Command to clear the syslog.
                   noAction(0) : do nothing  (read only).
                   activate(1) : Clear Syslog."
               DEFVAL  { noAction }
               ::= {     sispm10403166lSysLogInfo 3 }

    sispm10403166lSystemLogDetailedInfoTable OBJECT-TYPE
              SYNTAX      SEQUENCE OF     SISPM10403166LSystemLogDetailedInfoEntry
              MAX-ACCESS  not-accessible
              STATUS      current
              DESCRIPTION
                       "The system detailed Log Info table."
                   ::= {     sispm10403166lSysLogInfo 4 }

    sispm10403166lSystemLogDetailedInfoEntry OBJECT-TYPE
               SYNTAX          SISPM10403166LSystemLogDetailedInfoEntry
               MAX-ACCESS  not-accessible
               STATUS      current
               DESCRIPTION
                       "An entry in the system detailed Log Info table."
               INDEX    {     sispm10403166lSystemLogDetailedInfoID  }
               ::= {     sispm10403166lSystemLogDetailedInfoTable 1 }

    SISPM10403166LSystemLogDetailedInfoEntry             ::= SEQUENCE {
                sispm10403166lSystemLogDetailedSwitchIndex       Integer32,
                sispm10403166lSystemLogDetailedInfoID            Integer32,
                sispm10403166lSystemLogDetailedInfoLevel         DisplayString,
                sispm10403166lSystemLogDetailedInfoTime          DisplayString,
                sispm10403166lSystemLogDetailedInfoMessage       DisplayString
                }

    sispm10403166lSystemLogDetailedSwitchIndex OBJECT-TYPE
               SYNTAX      Integer32(1..16)
               MAX-ACCESS  not-accessible
               STATUS      current
               DESCRIPTION
                   "The switch index for the system detailed Log Info table."
               ::= {     sispm10403166lSystemLogDetailedInfoEntry 1 }

    sispm10403166lSystemLogDetailedInfoID OBJECT-TYPE
               SYNTAX      Integer32(1..999)
               MAX-ACCESS  not-accessible
               STATUS      current
               DESCRIPTION
                   "The index for the system detailed Log Info table."
               ::= {     sispm10403166lSystemLogDetailedInfoEntry 2 }

    sispm10403166lSystemLogDetailedInfoLevel OBJECT-TYPE
               SYNTAX      DisplayString
               MAX-ACCESS  read-only
               STATUS      current
               DESCRIPTION
                   "The Info Level."
               ::= {     sispm10403166lSystemLogDetailedInfoEntry 3 }

    sispm10403166lSystemLogDetailedInfoTime OBJECT-TYPE
               SYNTAX      DisplayString(SIZE (0..20))
               MAX-ACCESS  read-only
               STATUS      current
               DESCRIPTION
                   "The time"
               ::= {     sispm10403166lSystemLogDetailedInfoEntry 4 }

    sispm10403166lSystemLogDetailedInfoMessage OBJECT-TYPE
               SYNTAX      DisplayString
               MAX-ACCESS  read-only
               STATUS      current
               DESCRIPTION
                   "The message of this entry."
               ::= {     sispm10403166lSystemLogDetailedInfoEntry 5 }

    sispm10403166lSystemDORelayOpenClose OBJECT-TYPE
               SYNTAX      Integer32
               MAX-ACCESS  read-write
               STATUS      current
               DESCRIPTION
                  "DO Relay Open/Close.
				  1:Open
				  0:Close"
               ::= {     sispm10403166lSysLogInfo 5 }
-- =======================================================================================================================
sispm10403166lSnmp                                                OBJECT IDENTIFIER ::= { sispm10403166lSystem 6 }

sispm10403166lSnmpSystem                                            OBJECT IDENTIFIER ::= { sispm10403166lSnmp 1 }

sispm10403166lSnmpSystemMode OBJECT-TYPE
   SYNTAX       Integer32
   MAX-ACCESS   read-write
   STATUS       current
   DESCRIPTION
       "SNMP mode operation.
        default : 1, 0: disable, 1: enable. "
   ::= { sispm10403166lSnmpSystem 1 }

sispm10403166lSnmpSystemVersion OBJECT-TYPE
   SYNTAX       Integer32
   MAX-ACCESS   read-write
   STATUS       current
   DESCRIPTION
       "SNMP supported version.
       default : snmpv2c.
       1: snmpv1
       2: snmpv2c
       3: snmpv3."
   ::= { sispm10403166lSnmpSystem 2 }

sispm10403166lSnmpSystemReadCommunity OBJECT-TYPE
   SYNTAX       DisplayString
   MAX-ACCESS   read-write
   STATUS       current
   DESCRIPTION
       "Indicates the community read access string to permit access to SNMP agent.
       The allowed string length is 0 to 255.
       The field is applicable only when SNMP version is SNMPv1 or SNMPv2c."
   ::= { sispm10403166lSnmpSystem 3 }

sispm10403166lSnmpSystemWriteCommunity OBJECT-TYPE
   SYNTAX       DisplayString
   MAX-ACCESS   read-write
   STATUS       current
   DESCRIPTION
       "Indicates the community write access string to permit access to SNMP agent.
       The allowed string length is 0 to 255.
       The field is applicable only when SNMP version is SNMPv1 or SNMPv2c."
   ::= { sispm10403166lSnmpSystem 4 }

--sispm10403166lSnmpSystemEngineID OBJECT-TYPE
--   SYNTAX       DisplayString
--   MAX-ACCESS   read-write
--   STATUS       current
--   DESCRIPTION
--       "Indicates the SNMPv3 engine ID.
--        The string must contain an even number(in hexadecimal format) with number of digits between 10 and 64,
--	but all-zeros and all-'F's are not allowed.
--	Allow string length is 10 to 32.
--	Change of the Engine ID will clear all original local users."
--   ::= { sispm10403166lSnmpSystem 5 }

sispm10403166lSnmpSystemWriteCommunityMode OBJECT-TYPE
   SYNTAX       Integer32
   MAX-ACCESS   read-write
   STATUS       current
   DESCRIPTION
       "SNMP write community mode operation.
        default : 1, 0: disable, 1: enable. "
   ::= { sispm10403166lSnmpSystem 6 }

sispm10403166lSnmpSystemReadCommunityMode OBJECT-TYPE
   SYNTAX       Integer32
   MAX-ACCESS   read-write
   STATUS       current
   DESCRIPTION
       "SNMP read community mode operation.
        default : 1, 0: disable, 1: enable. "
   ::= { sispm10403166lSnmpSystem 7 }


--sispm10403166lSnmpTrapGlobalMode OBJECT-TYPE
--   SYNTAX       Integer32
--   MAX-ACCESS   read-write
--   STATUS       current
--   DESCRIPTION
--       "Indicates the trap mode operation.
--        0:Disable.
--	1:Enable."
--   ::= { sispm10403166lSnmp 2 }

sispm10403166lTrapDestinationConfTable OBJECT-TYPE
   SYNTAX      SEQUENCE OF SISPM10403166LTrapDestinationConfEntry
   MAX-ACCESS  not-accessible
   STATUS      current
   DESCRIPTION
       "A list of trap host entry. The numbers of entries are given by the value of TrapHostConfNumber."
   ::= { sispm10403166lSnmp 3 }

sispm10403166lTrapDestinationConfEntry OBJECT-TYPE
   SYNTAX      SISPM10403166LTrapDestinationConfEntry
   MAX-ACCESS  not-accessible
   STATUS      current
   DESCRIPTION
       "This is the entry information for trap host."
   INDEX    { sispm10403166lTrapDestinationConfIndex  }
   ::= { sispm10403166lTrapDestinationConfTable 1 }

SISPM10403166LTrapDestinationConfEntry ::= SEQUENCE {
    sispm10403166lTrapDestinationConfIndex                      Integer32,
    sispm10403166lTrapDestinationConfTrapConfigName             DisplayString,
    sispm10403166lTrapDestinationConfTrapMode                   Integer32,
    sispm10403166lTrapDestinationConfTrapVersion                Integer32,
    sispm10403166lTrapDestinationConfTrapCommunity              DisplayString,
    sispm10403166lTrapDestinationConfTrapDestinationAddres      DisplayString,
    sispm10403166lTrapDestinationConfTrapDestinationPort        Integer32,
--  sispm10403166lTrapDestinationConfTrapInformMode             Integer32,
--  sispm10403166lTrapDestinationConfTrapInformTimeout          Integer32,
--  sispm10403166lTrapDestinationConfTrapInformRetryTimes       Integer32,
--  sispm10403166lTrapDestinationConfTrapProbeSecurityEngineID  Integer32,
    sispm10403166lTrapDestinationConfTrapSecurityEngineID       DisplayString,
    sispm10403166lTrapDestinationConfTrapSecurityName           DisplayString,
    sispm10403166lTrapDestinationConfTrapRowStatus              Integer32
}

sispm10403166lTrapDestinationConfIndex OBJECT-TYPE
   SYNTAX       Integer32(1..65535)
   MAX-ACCESS   not-accessible
   STATUS       current
   DESCRIPTION
       "Index of tarp destination configurations."
   ::= { sispm10403166lTrapDestinationConfEntry 1 }

sispm10403166lTrapDestinationConfTrapConfigName OBJECT-TYPE
   SYNTAX       DisplayString
   MAX-ACCESS   read-write
   STATUS       current
   DESCRIPTION
       "Indicates which trap Configuration's name for configuring.
       The allowed string length is 0 to 255, and the allowed content is
       ASCII characters from 33 to 126."
   ::= { sispm10403166lTrapDestinationConfEntry 2 }

sispm10403166lTrapDestinationConfTrapMode OBJECT-TYPE
   SYNTAX       Integer32
   MAX-ACCESS   read-write
   STATUS       current
   DESCRIPTION
       "Indicates the SNMP mode operation. Possible modes are:
        2: Enable TCP SNMP mode operation.
        1: Enable UDP SNMP mode operation.
        0: Disable SNMP mode operation. "
   ::= { sispm10403166lTrapDestinationConfEntry 3 }

sispm10403166lTrapDestinationConfTrapVersion OBJECT-TYPE
   SYNTAX       Integer32
   MAX-ACCESS   read-write
   STATUS       current
   DESCRIPTION
       "0: snmpv1
        1: snmpv2c
        3: snmpv3.
        "
   ::= { sispm10403166lTrapDestinationConfEntry 4 }

sispm10403166lTrapDestinationConfTrapCommunity OBJECT-TYPE
   SYNTAX       DisplayString
   MAX-ACCESS   read-write
   STATUS       current
   DESCRIPTION
       "Indicates the community access string when sending SNMP trap packet.
       The allowed string length is 0 to 255, and the allowed content is
       ASCII characters from 33 to 126."
   ::= { sispm10403166lTrapDestinationConfEntry 5 }

sispm10403166lTrapDestinationConfTrapDestinationAddres OBJECT-TYPE
   SYNTAX       DisplayString
   MAX-ACCESS   read-write
   STATUS       current
   DESCRIPTION
       "Indicates the SNMP trap destination address.
       It allow a valid IP address in dotted decimal notation ('x.y.z.w').
    And it also allow a valid hostname.
    A valid hostname is a string drawn from the alphabet (A-Za-z), digits (0-9),
    dot (.), dash (-). Spaces are not allowed, the first character must be an alpha character,
    and the first and last characters must not be a dot or a dash.
    Indicates the SNMP trap destination IPv6 address.
    IPv6 address is in 128-bit records represented as eight fields of up to four hexadecimal digits
    with a colon separating each field (:).
    For example, 'fe80::215:c5ff:fe03:4dc7'. The symbol '::' is a special syntax
    that can be used as a shorthand way of representing multiple 16-bit groups of contiguous zeros;
    but it can appear only once.
    It can also represent a legally valid IPv4 address.
    For example, '::192.1.2.34'."
   ::= { sispm10403166lTrapDestinationConfEntry 6 }

sispm10403166lTrapDestinationConfTrapDestinationPort OBJECT-TYPE
   SYNTAX       Integer32
   MAX-ACCESS   read-write
   STATUS       current
   DESCRIPTION
       "Indicates the SNMP trap destination port.
       SNMP Agent will send SNMP message via this port,
       the port range is 1~65535."
   ::= { sispm10403166lTrapDestinationConfEntry 7 }

--sispm10403166lTrapDestinationConfTrapInformMode OBJECT-TYPE
--   SYNTAX       Integer32
--   MAX-ACCESS   read-write
--   STATUS       current
--   DESCRIPTION
--       "Indicates the SNMP trap inform mode operation. Possible modes are:
--        1: Enable SNMP trap inform mode operation.
--        0: Disable SNMP trap inform mode operation. "
--   ::= { sispm10403166lTrapDestinationConfEntry 8 }
--
--sispm10403166lTrapDestinationConfTrapInformTimeout OBJECT-TYPE
--   SYNTAX       Integer32
--   MAX-ACCESS   read-write
--   STATUS       current
--   DESCRIPTION
--       "Indicates the SNMP trap inform timeout. The allowed range is 0 to 2147."
--   ::= { sispm10403166lTrapDestinationConfEntry 9 }
--
--sispm10403166lTrapDestinationConfTrapInformRetryTimes OBJECT-TYPE
--   SYNTAX       Integer32
--   MAX-ACCESS   read-write
--   STATUS       current
--   DESCRIPTION
--       "Indicates the SNMP trap inform retry times. The allowed range is 0 to 255."
--   ::= { sispm10403166lTrapDestinationConfEntry 10 }
--
--sispm10403166lTrapDestinationConfTrapProbeSecurityEngineID OBJECT-TYPE
--   SYNTAX       Integer32
--   MAX-ACCESS   read-write
--   STATUS       current
--   DESCRIPTION
--       "Indicates the SNMP trap probe security engine ID mode of operation.
--       Possible values are:
--       1: Enable SNMP trap probe security engine ID mode of operation.
--       0: Disable SNMP trap probe security engine ID mode of operation."
--   ::= { sispm10403166lTrapDestinationConfEntry 11 }

sispm10403166lTrapDestinationConfTrapSecurityEngineID OBJECT-TYPE
   SYNTAX       DisplayString
   MAX-ACCESS   read-write
   STATUS       current
   DESCRIPTION
       "Indicates the SNMP trap security engine ID.
       SNMPv3 sends traps and informs using USM for authentication and privacy.
       A unique engine ID for these traps and informs is needed.
       When Trap Probe Security Engine ID is enabled, the ID will be probed automatically.
       Otherwise, the ID specified in this field is used.
       The string must contain an even number(in hexadecimal format) with
       number of digits between 10 and 64, but all-zeros and all-'F's are not allowed."
   ::= { sispm10403166lTrapDestinationConfEntry 12 }

sispm10403166lTrapDestinationConfTrapSecurityName OBJECT-TYPE
   SYNTAX       DisplayString
   MAX-ACCESS   read-write
   STATUS       current
   DESCRIPTION
       "Indicates the SNMP trap security name.
       SNMPv3 traps and informs using USM for authentication and privacy.
       A unique security name is needed when traps and informs are enabled.
       This name from user name of user configuration."
   ::= { sispm10403166lTrapDestinationConfEntry 13 }

sispm10403166lTrapDestinationConfTrapRowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sispm10403166lTrapDestinationConfEntry 14 }


sispm10403166lSNMPCommunityConfTable OBJECT-TYPE
   SYNTAX      SEQUENCE OF SISPM10403166LSNMPCommunityConfEntry
   MAX-ACCESS  not-accessible
   STATUS      current
   DESCRIPTION
       "A list of snmp community configuration entry."
   ::= { sispm10403166lSnmp 5 }

sispm10403166lSNMPCommunityConfEntry OBJECT-TYPE
   SYNTAX      SISPM10403166LSNMPCommunityConfEntry
   MAX-ACCESS  not-accessible
   STATUS      current
   DESCRIPTION
       "This is the entry information for snmp community configuration."
   INDEX    { sispm10403166lSNMPCommunityConfIndex  }
   ::= { sispm10403166lSNMPCommunityConfTable 1 }

SISPM10403166LSNMPCommunityConfEntry ::= SEQUENCE {
    sispm10403166lSNMPCommunityConfIndex                       Integer32,
    sispm10403166lSNMPCommunityConfSNMPv3Community             DisplayString,
    sispm10403166lSNMPCommunityConfSNMPv3SourceIP              IpAddress,
    sispm10403166lSNMPCommunityConfSNMPv3SourceMask            IpAddress,
    sispm10403166lSNMPCommunityConfSNMPv3RowStatus             Integer32
}

sispm10403166lSNMPCommunityConfIndex OBJECT-TYPE
   SYNTAX       Integer32(1..65535)
   MAX-ACCESS   read-write
   STATUS       current
   DESCRIPTION
       "Community configuration index."
   ::= { sispm10403166lSNMPCommunityConfEntry 1 }

sispm10403166lSNMPCommunityConfSNMPv3Community OBJECT-TYPE
   SYNTAX       DisplayString
   MAX-ACCESS   read-write
   STATUS       current
   DESCRIPTION
       "Indicates the community access string to permit access to SNMPv3 agent.
       The allowed string length is 1 to 32, and the allowed content is
       ASCII characters from 33 to 126.
       The community string will be treated as security name and map a SNMPv1
       or SNMPv2c community string."
   ::= { sispm10403166lSNMPCommunityConfEntry 2 }


sispm10403166lSNMPCommunityConfSNMPv3SourceIP OBJECT-TYPE
   SYNTAX      IpAddress
   MAX-ACCESS  read-write
   STATUS      current
   DESCRIPTION
       "Indicates the SNMP access source address.
       A particular range of source addresses can be used to restrict source subnet
       when combined with source mask."
   ::= {sispm10403166lSNMPCommunityConfEntry 3 }

sispm10403166lSNMPCommunityConfSNMPv3SourceMask OBJECT-TYPE
   SYNTAX      IpAddress
   MAX-ACCESS  read-write
   STATUS      current
   DESCRIPTION
       "Indicates the SNMP access source address mask."
   ::= {sispm10403166lSNMPCommunityConfEntry 4 }

sispm10403166lSNMPCommunityConfSNMPv3RowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sispm10403166lSNMPCommunityConfEntry 5 }

sispm10403166lSNMPv3UserConfTable OBJECT-TYPE
   SYNTAX      SEQUENCE OF SISPM10403166LSNMPv3UserConfEntry
   MAX-ACCESS  not-accessible
   STATUS      current
   DESCRIPTION
       "A list of snmpv3 user configuration entry."
   ::= { sispm10403166lSnmp 6 }

sispm10403166lSNMPv3UserConfEntry OBJECT-TYPE
   SYNTAX      SISPM10403166LSNMPv3UserConfEntry
   MAX-ACCESS  not-accessible
   STATUS      current
   DESCRIPTION
       "This is the entry information for snmpv3 user configuration."
   INDEX    { sispm10403166lSNMPv3UserConfIndex  }
   ::= { sispm10403166lSNMPv3UserConfTable 1 }

SISPM10403166LSNMPv3UserConfEntry ::= SEQUENCE {
    sispm10403166lSNMPv3UserConfIndex                     Integer32,
    sispm10403166lSNMPv3UserConfEngineID                  DisplayString,
    sispm10403166lSNMPv3UserConfUserName                  DisplayString,
    sispm10403166lSNMPv3UserConfSecurityLevel             Integer32,
    sispm10403166lSNMPv3UserConfAuthenticationProtocol    Integer32,
    sispm10403166lSNMPv3UserConfAuthenticationPassword    DisplayString,
    sispm10403166lSNMPv3UserConfPrivacyProtocol           Integer32,
    sispm10403166lSNMPv3UserConfPrivacyPassword           DisplayString,
    sispm10403166lSNMPv3UserConfRowStatus                 RowStatus
}

sispm10403166lSNMPv3UserConfIndex OBJECT-TYPE
   SYNTAX       Integer32(1..65535)
   MAX-ACCESS   read-write
   STATUS       current
   DESCRIPTION
       "User configuration index."
   ::= { sispm10403166lSNMPv3UserConfEntry 1 }

sispm10403166lSNMPv3UserConfEngineID OBJECT-TYPE
   SYNTAX       DisplayString
   MAX-ACCESS   read-write
   STATUS       current
   DESCRIPTION
       "An octet string identifying the engine ID that this entry should belong to.
       The string must contain an even number(in hexadecimal format) with
       number of digits between 10 and 64, but all-zeros and all-'F's are not allowed.
       The SNMPv3 architecture uses the User-based Security Model (USM)
       for message security and the View-based Access Control Model (VACM) for access control.
       For the USM entry, the usmUserEngineID and usmUserName are the entry's keys.
       In a simple agent, usmUserEngineID is always that agent's own snmpEngineID value.
       The value can also take the value of the snmpEngineID of a remote SNMP engine with
       which this user can communicate. In other words, if user engine ID equal system engine ID
       then it is local user; otherwise it's remote user. "
   ::= { sispm10403166lSNMPv3UserConfEntry 2 }

sispm10403166lSNMPv3UserConfUserName OBJECT-TYPE
   SYNTAX       DisplayString
   MAX-ACCESS   read-write
   STATUS       current
   DESCRIPTION
       "A string identifying the user name that this entry should belong to.
       The allowed string length is 1 to 32, and the allowed content is
       ASCII characters from 33 to 126."
   ::= { sispm10403166lSNMPv3UserConfEntry 3 }

sispm10403166lSNMPv3UserConfSecurityLevel OBJECT-TYPE
   SYNTAX       Integer32
   MAX-ACCESS   read-write
   STATUS       current
   DESCRIPTION
       "1:NoAuth, NoPriv
        2:Auth, NoPriv
	3:Auth, Priv"
   ::= { sispm10403166lSNMPv3UserConfEntry 4 }

sispm10403166lSNMPv3UserConfAuthenticationProtocol OBJECT-TYPE
   SYNTAX       Integer32
   MAX-ACCESS   read-write
   STATUS       current
   DESCRIPTION
       "0:None
        1:MD5
	2:SHA"
   ::= { sispm10403166lSNMPv3UserConfEntry 5 }

sispm10403166lSNMPv3UserConfAuthenticationPassword OBJECT-TYPE
   SYNTAX       DisplayString
   MAX-ACCESS   read-write
   STATUS       current
   DESCRIPTION
       "A string identifying the authentication password phrase.
       For MD5 authentication protocol, the allowed string length is 8 to 32.
       For SHA authentication protocol, the allowed string length is 8 to 40.
       The allowed content is ASCII characters from 33 to 126."
   ::= { sispm10403166lSNMPv3UserConfEntry 6 }

sispm10403166lSNMPv3UserConfPrivacyProtocol OBJECT-TYPE
   SYNTAX       Integer32
   MAX-ACCESS   read-write
   STATUS       current
   DESCRIPTION
       "0:None
        1:DES
        2:AES"
   ::= { sispm10403166lSNMPv3UserConfEntry 7 }

sispm10403166lSNMPv3UserConfPrivacyPassword OBJECT-TYPE
   SYNTAX       DisplayString
   MAX-ACCESS   read-write
   STATUS       current
   DESCRIPTION
       "A string identifying the privacy password phrase.
       The allowed string length is 8 to 32, and the allowed content is
       ASCII characters from 33 to 126."
   ::= { sispm10403166lSNMPv3UserConfEntry 8 }

sispm10403166lSNMPv3UserConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sispm10403166lSNMPv3UserConfEntry 9 }

sispm10403166lSNMPv3GroupConfTable OBJECT-TYPE
   SYNTAX      SEQUENCE OF SISPM10403166LSNMPv3GroupConfEntry
   MAX-ACCESS  not-accessible
   STATUS      current
   DESCRIPTION
       "A list of snmpv3 group configuration entry."
   ::= { sispm10403166lSnmp 7 }

sispm10403166lSNMPv3GroupConfEntry OBJECT-TYPE
   SYNTAX      SISPM10403166LSNMPv3GroupConfEntry
   MAX-ACCESS  not-accessible
   STATUS      current
   DESCRIPTION
       "This is the entry information for snmpv3 group configuration."
   INDEX    { sispm10403166lSNMPv3GroupConfIndex  }
   ::= { sispm10403166lSNMPv3GroupConfTable 1 }

SISPM10403166LSNMPv3GroupConfEntry ::= SEQUENCE {
    sispm10403166lSNMPv3GroupConfIndex                     Integer32,
    sispm10403166lSNMPv3GroupConfSecurityModel             Integer32,
    sispm10403166lSNMPv3GroupConfSecurityName          DisplayString,
    sispm10403166lSNMPv3GroupConfGroupName             DisplayString,
    sispm10403166lSNMPv3GroupConfRowStatus                 RowStatus
}

sispm10403166lSNMPv3GroupConfIndex OBJECT-TYPE
   SYNTAX       Integer32(1..65535)
   MAX-ACCESS   read-write
   STATUS       current
   DESCRIPTION
       "Group configuration index."
   ::= { sispm10403166lSNMPv3GroupConfEntry 1 }

sispm10403166lSNMPv3GroupConfSecurityModel OBJECT-TYPE
   SYNTAX       Integer32
   MAX-ACCESS   read-write
   STATUS       current
   DESCRIPTION
       "1:v1
        2:v2c
	3:usm"
   ::= { sispm10403166lSNMPv3GroupConfEntry 2 }

sispm10403166lSNMPv3GroupConfSecurityName OBJECT-TYPE
   SYNTAX       DisplayString
   MAX-ACCESS   read-write
   STATUS       current
   DESCRIPTION
       "A string identifying the security name that this entry should belong to.
       The allowed string length is 1 to 32, and the allowed content is
       ASCII characters from 33 to 126.
       This name is from the Community of Community configuration."
   ::= { sispm10403166lSNMPv3GroupConfEntry 3 }

sispm10403166lSNMPv3GroupConfGroupName OBJECT-TYPE
   SYNTAX       DisplayString
   MAX-ACCESS   read-write
   STATUS       current
   DESCRIPTION
       "A string identifying the group name that this entry should belong to.
       The allowed string length is 1 to 32, and the allowed content is
       ASCII characters from 33 to 126. "
   ::= { sispm10403166lSNMPv3GroupConfEntry 4 }


sispm10403166lSNMPv3GroupConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sispm10403166lSNMPv3GroupConfEntry 5 }

sispm10403166lSNMPv3ViewsConfTable OBJECT-TYPE
   SYNTAX      SEQUENCE OF SISPM10403166LSNMPv3ViewsConfEntry
   MAX-ACCESS  not-accessible
   STATUS      current
   DESCRIPTION
       "A list of snmpv3 view configuration entry."
   ::= { sispm10403166lSnmp 8 }

sispm10403166lSNMPv3ViewsConfEntry OBJECT-TYPE
   SYNTAX      SISPM10403166LSNMPv3ViewsConfEntry
   MAX-ACCESS  not-accessible
   STATUS      current
   DESCRIPTION
       "This is the entry information for snmpv3 view configuration."
   INDEX    { sispm10403166lSNMPv3ViewsConfIndex  }
   ::= { sispm10403166lSNMPv3ViewsConfTable 1 }

SISPM10403166LSNMPv3ViewsConfEntry ::= SEQUENCE {
    sispm10403166lSNMPv3ViewsConfIndex                   Integer32,
    sispm10403166lSNMPv3ViewsConfViewName            DisplayString,
    sispm10403166lSNMPv3ViewsConfViewType                Integer32,
    sispm10403166lSNMPv3ViewsConfOIDSubtree          DisplayString,
    sispm10403166lSNMPv3ViewsConfRowStatus               RowStatus
}

sispm10403166lSNMPv3ViewsConfIndex OBJECT-TYPE
   SYNTAX       Integer32(1..65535)
   MAX-ACCESS   read-write
   STATUS       current
   DESCRIPTION
       "view configuration index."
   ::= { sispm10403166lSNMPv3ViewsConfEntry 1 }

sispm10403166lSNMPv3ViewsConfViewName OBJECT-TYPE
   SYNTAX       DisplayString
   MAX-ACCESS   read-write
   STATUS       current
   DESCRIPTION
       "A string identifying the view name that this entry should belong to.
       The allowed string length is 1 to 32, and the allowed content is
       ASCII characters from 33 to 126. "
   ::= { sispm10403166lSNMPv3ViewsConfEntry 2 }

sispm10403166lSNMPv3ViewsConfViewType OBJECT-TYPE
   SYNTAX       Integer32
   MAX-ACCESS   read-write
   STATUS       current
   DESCRIPTION
       "0:included
       1:excluded"
   ::= { sispm10403166lSNMPv3ViewsConfEntry 3 }

sispm10403166lSNMPv3ViewsConfOIDSubtree OBJECT-TYPE
   SYNTAX       DisplayString
   MAX-ACCESS   read-write
   STATUS       current
   DESCRIPTION
       "The OID defining the root of the subtree to add to the named view.
       The allowed OID length is 1 to 128. The allowed string content is
       digital number or asterisk(*)"
   ::= { sispm10403166lSNMPv3ViewsConfEntry 4 }

sispm10403166lSNMPv3ViewsConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sispm10403166lSNMPv3ViewsConfEntry 5 }


sispm10403166lSNMPv3AccessConfTable OBJECT-TYPE
   SYNTAX      SEQUENCE OF SISPM10403166LSNMPv3AccessConfEntry
   MAX-ACCESS  not-accessible
   STATUS      current
   DESCRIPTION
       "A list of snmpv3 access configuration entry."
   ::= { sispm10403166lSnmp 9 }

sispm10403166lSNMPv3AccessConfEntry OBJECT-TYPE
   SYNTAX      SISPM10403166LSNMPv3AccessConfEntry
   MAX-ACCESS  not-accessible
   STATUS      current
   DESCRIPTION
       "This is the entry information for snmpv3 access configuration."
   INDEX    { sispm10403166lSNMPv3AccessConfIndex  }
   ::= { sispm10403166lSNMPv3AccessConfTable 1 }

SISPM10403166LSNMPv3AccessConfEntry ::= SEQUENCE {
    sispm10403166lSNMPv3AccessConfIndex                    Integer32,
    sispm10403166lSNMPv3AccessConfGroupName            DisplayString,
    sispm10403166lSNMPv3AccessConfSecurityModel            Integer32,
    sispm10403166lSNMPv3AccessConfSecurityLevel            Integer32,
    sispm10403166lSNMPv3AccessConfReadViewName         DisplayString,
    sispm10403166lSNMPv3AccessConfWriteViewName        DisplayString,
    sispm10403166lSNMPv3AccessConfRowStatus                RowStatus
}

sispm10403166lSNMPv3AccessConfIndex OBJECT-TYPE
   SYNTAX       Integer32(1..65535)
   MAX-ACCESS   read-write
   STATUS       current
   DESCRIPTION
       "Access configuration index"
   ::= { sispm10403166lSNMPv3AccessConfEntry 1 }

sispm10403166lSNMPv3AccessConfGroupName OBJECT-TYPE
   SYNTAX       DisplayString
   MAX-ACCESS   read-write
   STATUS       current
   DESCRIPTION
       "Group name from Group configuration."
   ::= { sispm10403166lSNMPv3AccessConfEntry 2 }

sispm10403166lSNMPv3AccessConfSecurityModel OBJECT-TYPE
   SYNTAX       Integer32
   MAX-ACCESS   read-write
   STATUS       current
   DESCRIPTION
       "0:any
        1:v1
	2:v2c
	3:usm"
   ::= { sispm10403166lSNMPv3AccessConfEntry 3 }

sispm10403166lSNMPv3AccessConfSecurityLevel OBJECT-TYPE
   SYNTAX       Integer32
   MAX-ACCESS   read-write
   STATUS       current
   DESCRIPTION
       "1:NoAuth, NoPriv
       2:Auth, NoPriv
       3:Auth, Priv"
   ::= { sispm10403166lSNMPv3AccessConfEntry 4 }

sispm10403166lSNMPv3AccessConfReadViewName OBJECT-TYPE
   SYNTAX       DisplayString
   MAX-ACCESS   read-write
   STATUS       current
   DESCRIPTION
       "Read View Name from View configuration."
   ::= { sispm10403166lSNMPv3AccessConfEntry 5 }

sispm10403166lSNMPv3AccessConfWriteViewName OBJECT-TYPE
   SYNTAX       DisplayString
   MAX-ACCESS   read-write
   STATUS       current
   DESCRIPTION
       "Write View Name from View configuration."
   ::= { sispm10403166lSNMPv3AccessConfEntry 6 }

sispm10403166lSNMPv3AccessConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sispm10403166lSNMPv3AccessConfEntry 7 }

-- =======================================================================================================================
sispm10403166lDHCPServer                                     OBJECT IDENTIFIER ::= { sispm10403166lSystem 9 }

sispm10403166lDHCPServerConfig                              OBJECT IDENTIFIER ::= { sispm10403166lDHCPServer 7 }

sispm10403166lDHCPServerConfigTable OBJECT-TYPE
   SYNTAX      SEQUENCE OF SISPM10403166LDHCPServerConfigEntry
   MAX-ACCESS  not-accessible
   STATUS      current
   DESCRIPTION
       " "
    ::= { sispm10403166lDHCPServerConfig 1 }

sispm10403166lDHCPServerConfigEntry OBJECT-TYPE
    SYNTAX        SISPM10403166LDHCPServerConfigEntry
    MAX-ACCESS    not-accessible
    STATUS        current
    DESCRIPTION
        " "
    INDEX        { sispm10403166lDHCPServerConfigIndex }
    ::= { sispm10403166lDHCPServerConfigTable 1 }


SISPM10403166LDHCPServerConfigEntry ::=
    SEQUENCE {
        sispm10403166lDHCPServerConfigIndex                    Integer32,
        sispm10403166lDHCPServerConfigInterfaceVLAN            Integer32,
        sispm10403166lDHCPServerConfigInterfaceMode            Integer32,
        sispm10403166lDHCPServerConfigInterfaceStartIPEndIP    DisplayString,
--      sispm10403166lDHCPServerConfigInterfaceEndIP           IpAddress,
        sispm10403166lDHCPServerConfigInterfaceLeaseTime       Integer32,
        sispm10403166lDHCPServerConfigInterfaceSubnetMask      IpAddress,
        sispm10403166lDHCPServerConfigInterfaceDefaultRouter   IpAddress,
        sispm10403166lDHCPServerConfigInterfaceDNSServer       IpAddress
    }

sispm10403166lDHCPServerConfigIndex OBJECT-TYPE
   SYNTAX      Integer32 (1..4094)
   MAX-ACCESS  not-accessible
   STATUS      current
   DESCRIPTION
       "table index."
   ::= {sispm10403166lDHCPServerConfigEntry 1 }

sispm10403166lDHCPServerConfigInterfaceVLAN OBJECT-TYPE
   SYNTAX      Integer32 (1..4094)
   MAX-ACCESS  read-only
   STATUS      current
   DESCRIPTION
       "The VLAN in which DHCP server is enabled or disabled. "
   ::= {sispm10403166lDHCPServerConfigEntry 2 }

sispm10403166lDHCPServerConfigInterfaceMode OBJECT-TYPE
   SYNTAX      Integer32 (0|1)
   MAX-ACCESS  read-write
   STATUS      current
   DESCRIPTION
       "Indicate the operation mode per VLAN.
       0:disable
       1:enable"
   ::= {sispm10403166lDHCPServerConfigEntry 3 }

sispm10403166lDHCPServerConfigInterfaceStartIPEndIP OBJECT-TYPE
   SYNTAX      DisplayString
   MAX-ACCESS  read-write
   STATUS      current
   DESCRIPTION
       "Please set SubnetMask first.
       Start IP and End IP. Format: x.x.x.x-x.x.x.x"
   ::= {sispm10403166lDHCPServerConfigEntry 4 }

--sispm10403166lDHCPServerConfigInterfaceEndIP OBJECT-TYPE
--   SYNTAX      IpAddress
--   MAX-ACCESS  read-write
--   STATUS      current
--   DESCRIPTION
--       "End IP"
--   ::= {sispm10403166lDHCPServerConfigEntry 5 }

sispm10403166lDHCPServerConfigInterfaceLeaseTime OBJECT-TYPE
   SYNTAX      Integer32
   MAX-ACCESS  read-write
   STATUS      current
   DESCRIPTION
       "The lease time in second."
   ::= {sispm10403166lDHCPServerConfigEntry 6 }

sispm10403166lDHCPServerConfigInterfaceSubnetMask OBJECT-TYPE
   SYNTAX      IpAddress
   MAX-ACCESS  read-write
   STATUS      current
   DESCRIPTION
       "Configure subnet mask of the DHCP address. "
   ::= {sispm10403166lDHCPServerConfigEntry 7 }

sispm10403166lDHCPServerConfigInterfaceDefaultRouter OBJECT-TYPE
   SYNTAX      IpAddress
   MAX-ACCESS  read-write
   STATUS      current
   DESCRIPTION
       "Configure the destination IP network or host address of the default route."
   ::= {sispm10403166lDHCPServerConfigEntry 8 }

sispm10403166lDHCPServerConfigInterfaceDNSServer OBJECT-TYPE
   SYNTAX      IpAddress
   MAX-ACCESS  read-write
   STATUS      current
   DESCRIPTION
       "Configure the default DNS server. "
   ::= {sispm10403166lDHCPServerConfigEntry 9 }

sispm10403166lDHCPServerStatus                              OBJECT IDENTIFIER ::= { sispm10403166lDHCPServer 8 }

sispm10403166lDHCPServerStatusTable OBJECT-TYPE
   SYNTAX      SEQUENCE OF SISPM10403166LDHCPServerStatusEntry
   MAX-ACCESS  not-accessible
   STATUS      current
   DESCRIPTION
       " "
    ::= { sispm10403166lDHCPServerStatus 1 }

sispm10403166lDHCPServerStatusEntry OBJECT-TYPE
    SYNTAX        SISPM10403166LDHCPServerStatusEntry
    MAX-ACCESS    not-accessible
    STATUS        current
    DESCRIPTION
        " "
    INDEX        { sispm10403166lDHCPServerStatusIndex }
    ::= { sispm10403166lDHCPServerStatusTable 1 }


SISPM10403166LDHCPServerStatusEntry ::=
    SEQUENCE {
        sispm10403166lDHCPServerStatusIndex                    Integer32,
        sispm10403166lDHCPServerStatusInterfaceVLAN            Integer32,
        sispm10403166lDHCPServerStatusInterfaceType            DisplayString,
        sispm10403166lDHCPServerStatusInterfaceStartIP         IpAddress,
        sispm10403166lDHCPServerStatusInterfaceEndIP           IpAddress,
        sispm10403166lDHCPServerStatusInterfaceLeaseTime       Integer32,
        sispm10403166lDHCPServerStatusInterfaceSubnetMask      IpAddress,
        sispm10403166lDHCPServerStatusInterfaceDefaultRouter   IpAddress,
        sispm10403166lDHCPServerStatusInterfaceDNSServer       IpAddress
    }

sispm10403166lDHCPServerStatusIndex OBJECT-TYPE
   SYNTAX      Integer32 (1..4094)
   MAX-ACCESS  not-accessible
   STATUS      current
   DESCRIPTION
       "table index."
   ::= {sispm10403166lDHCPServerStatusEntry 1 }

sispm10403166lDHCPServerStatusInterfaceVLAN OBJECT-TYPE
   SYNTAX      Integer32 (1..4094)
   MAX-ACCESS  read-only
   STATUS      current
   DESCRIPTION
       "The VLAN in which DHCP server is enabled or disabled. "
   ::= {sispm10403166lDHCPServerStatusEntry 2 }

sispm10403166lDHCPServerStatusInterfaceType OBJECT-TYPE
   SYNTAX      DisplayString
   MAX-ACCESS  read-only
   STATUS      current
   DESCRIPTION
       " "
   ::= {sispm10403166lDHCPServerStatusEntry 3 }

sispm10403166lDHCPServerStatusInterfaceStartIP OBJECT-TYPE
   SYNTAX      IpAddress
   MAX-ACCESS  read-only
   STATUS      current
   DESCRIPTION
       "Start IP"
   ::= {sispm10403166lDHCPServerStatusEntry 4 }

sispm10403166lDHCPServerStatusInterfaceEndIP OBJECT-TYPE
   SYNTAX      IpAddress
   MAX-ACCESS  read-only
   STATUS      current
   DESCRIPTION
       "End IP"
   ::= {sispm10403166lDHCPServerStatusEntry 5 }

sispm10403166lDHCPServerStatusInterfaceLeaseTime OBJECT-TYPE
   SYNTAX      Integer32
   MAX-ACCESS  read-only
   STATUS      current
   DESCRIPTION
       "The lease time in second."
   ::= {sispm10403166lDHCPServerStatusEntry 6 }

sispm10403166lDHCPServerStatusInterfaceSubnetMask OBJECT-TYPE
   SYNTAX      IpAddress
   MAX-ACCESS  read-only
   STATUS      current
   DESCRIPTION
       "Configure subnet mask of the DHCP address. "
   ::= {sispm10403166lDHCPServerStatusEntry 7 }

sispm10403166lDHCPServerStatusInterfaceDefaultRouter OBJECT-TYPE
   SYNTAX      IpAddress
   MAX-ACCESS  read-only
   STATUS      current
   DESCRIPTION
       "Configure the destination IP network or host address of the default route."
   ::= {sispm10403166lDHCPServerStatusEntry 8 }

sispm10403166lDHCPServerStatusInterfaceDNSServer OBJECT-TYPE
   SYNTAX      IpAddress
   MAX-ACCESS  read-only
   STATUS      current
   DESCRIPTION
       "Configure the default DNS server. "
   ::= {sispm10403166lDHCPServerStatusEntry 9 }

--sispm10403166lDHCPServerConf                                 OBJECT IDENTIFIER ::= { sispm10403166lDHCPServer 1 }
--
--sispm10403166lDHCPServerGlobalMode OBJECT-TYPE
--   SYNTAX      Integer32 (0|1)
--   MAX-ACCESS  read-write
--   STATUS      current
--   DESCRIPTION
--       "default: 0,
--        Global Mode :
--        0: Disable,
--        1: Enable.
--       "
--   ::= { sispm10403166lDHCPServerConf 1 }
--
--sispm10403166lDHCPServerVLANMode OBJECT-TYPE
--   SYNTAX      Integer32 (0|1)
--   MAX-ACCESS  read-write
--   STATUS      current
--   DESCRIPTION
--       "default: 0,
--        0: Disable,
--        1: Enable.
--       "
--   ::= { sispm10403166lDHCPServerConf 2 }
--
--sispm10403166lVLANModeTable OBJECT-TYPE
--   SYNTAX      SEQUENCE OF SISPM10403166LVLANModeEntry
--   MAX-ACCESS  not-accessible
--   STATUS      current
--   DESCRIPTION
--       "A table of VLAN Mode for DHCP Server."
--    ::= { sispm10403166lDHCPServerConf 2 }

--sispm10403166lVLANModeEntry OBJECT-TYPE
--    SYNTAX        SISPM10403166LVLANModeEntry
--    MAX-ACCESS    not-accessible
--    STATUS        current
--    DESCRIPTION
--        "An entry in the sispm10403166lVLANModeTable."
--    INDEX        { sispm10403166lVLANModeIndex }
--    ::= { sispm10403166lVLANModeTable 1 }
--
--SISPM10403166LVLANModeEntry ::=
--    SEQUENCE {
--        sispm10403166lVLANModeIndex                            Integer32,
--        sispm10403166lVLANModeRangeLow                         Integer32,
--        sispm10403166lVLANModeRangeHigh                        Integer32,
--        sispm10403166lVLANModeEnable                           Integer32,
--		sispm10403166lVLANModeRowStatus                        RowStatus
--    }
--
--sispm10403166lVLANModeIndex OBJECT-TYPE
--   SYNTAX      Integer32 (1..2048)
--   MAX-ACCESS  not-accessible
--   STATUS      current
--   DESCRIPTION
--       "VLAN Mode table index, range: 1-2048."
--   ::= {sispm10403166lVLANModeEntry 1 }
--
--sispm10403166lVLANModeRangeLow OBJECT-TYPE
--   SYNTAX      Integer32 (1..4095)
--   MAX-ACCESS  read-create
--   STATUS      current
--   DESCRIPTION
--       "VLAN Mode low range: 1-4095."
--   ::= {sispm10403166lVLANModeEntry 2 }
--
--sispm10403166lVLANModeRangeHigh OBJECT-TYPE
--   SYNTAX      Integer32 (1..4095)
--   MAX-ACCESS  read-create
--   STATUS      current
--   DESCRIPTION
--       "VLAN Mode high range: 1-4095."
--   ::= {sispm10403166lVLANModeEntry 3 }
--
--sispm10403166lVLANModeEnable OBJECT-TYPE
--   SYNTAX      Integer32 (0..1)
--   MAX-ACCESS  read-create
--   STATUS      current
--   DESCRIPTION
--       "VLAN Mode Enable, Enable:1, Disable:0."
--   ::= {sispm10403166lVLANModeEntry 4 }
--
--sispm10403166lVLANModeRowStatus OBJECT-TYPE
--   SYNTAX      RowStatus
--   MAX-ACCESS  read-create
--   STATUS      current
--   DESCRIPTION
--      "This object indicates the status of this entry, and is
--       used to create/delete entries.  Any object in an entry of
--       this table may be modified while the value of the
--       corresponding instance of this object is active(1).
--       createAndGo, notReady not supported."
--   ::= {     sispm10403166lVLANModeEntry 5 }
--


-- sispm10403166lDHCPServerBindingType OBJECT-TYPE
--   SYNTAX      Integer32 (0|1|2|3)
--   MAX-ACCESS  read-only
--   STATUS      current
--   DESCRIPTION
--       "default: None,
--        Global Mode :
--        0: None,
--        1: Automatic,
--        2: Manual,
--        3: Expired.
--       "
--   ::= { sispm10403166lDHCPServerConf 2 }

-- sispm10403166lDHCPServerBindingState OBJECT-TYPE
--   SYNTAX      Integer32 (0|1|2|3)
--   MAX-ACCESS  read-only
--   STATUS      current
--   DESCRIPTION
--       "default: None,
--        Global Mode :
--        0: None,
--        1: Allocated,
--        2: Committed,
--        3: Expired.
--       "
--   ::= { sispm10403166lDHCPServerConf 3 }

-- sispm10403166lDHCPServerBindingIP OBJECT-TYPE
--   SYNTAX      DisplayString
--   MAX-ACCESS  read-only
--   STATUS      current
--   DESCRIPTION
--       "The DHCP Server Binding IP"
--   ::= { sispm10403166lDHCPServerConf 4 }
--
--
--sispm10403166lDHCPServerExcludedIP                                 OBJECT IDENTIFIER ::= { sispm10403166lDHCPServer 2 }
--
--sispm10403166lExcludedIPTable OBJECT-TYPE
--   SYNTAX      SEQUENCE OF SISPM10403166LExcludedIPEntry
--   MAX-ACCESS  not-accessible
--   STATUS      current
--   DESCRIPTION
--       "A table of Excluded IP for DHCP Server."
--    ::= { sispm10403166lDHCPServerExcludedIP 1 }
--
--sispm10403166lExcludedIPEntry OBJECT-TYPE
--    SYNTAX        SISPM10403166LExcludedIPEntry
--    MAX-ACCESS    not-accessible
--    STATUS        current
--    DESCRIPTION
--        "An entry in the sispm10403166lExcludedIPTable."
--    INDEX        { sispm10403166lExcludedIPIndex }
--    ::= { sispm10403166lExcludedIPTable 1 }
--
--SISPM10403166LExcludedIPEntry ::=
--    SEQUENCE {
--        sispm10403166lExcludedIPIndex                            Integer32,
--        sispm10403166lExcludedIPRangeLow                         IpAddress,
--        sispm10403166lExcludedIPRangeHigh                        IpAddress,
--		sispm10403166lExcludedIPRowStatus                        RowStatus
--    }
--
--sispm10403166lExcludedIPIndex OBJECT-TYPE
--   SYNTAX      Integer32 (1..16)
--   MAX-ACCESS  not-accessible
--   STATUS      current
--   DESCRIPTION
--       "Excluded IP table index, range: 1-16."
--   ::= {sispm10403166lExcludedIPEntry 1 }
--
--sispm10403166lExcludedIPRangeLow OBJECT-TYPE
--   SYNTAX      IpAddress
--   MAX-ACCESS  read-create
--   STATUS      current
--   DESCRIPTION
--       "ExcludedIP low range."
--   ::= {sispm10403166lExcludedIPEntry 2 }
--
--sispm10403166lExcludedIPRangeHigh OBJECT-TYPE
--   SYNTAX      IpAddress
--   MAX-ACCESS  read-create
--   STATUS      current
--   DESCRIPTION
--       "ExcludedIP high range."
--   ::= {sispm10403166lExcludedIPEntry 3 }
--
--sispm10403166lExcludedIPRowStatus OBJECT-TYPE
--   SYNTAX      RowStatus
--   MAX-ACCESS  read-create
--   STATUS      current
--   DESCRIPTION
--      "This object indicates the status of this entry, and is
--       used to create/delete entries.  Any object in an entry of
--       this table may be modified while the value of the
--       corresponding instance of this object is active(1).
--       createAndGo, notReady not supported."
--   ::= {sispm10403166lExcludedIPEntry 4 }
--
--
--
--sispm10403166lDHCPServerPoolConf                                 OBJECT IDENTIFIER ::= { sispm10403166lDHCPServer 3 }
--
--sispm10403166lDHCPServerPoolTable OBJECT-TYPE
--   SYNTAX      SEQUENCE OF SISPM10403166LDHCPServerPoolEntry
--   MAX-ACCESS  not-accessible
--   STATUS      current
--   DESCRIPTION
--       "This is the entry information for DHCP Pool."
--   ::= { sispm10403166lDHCPServerPoolConf 1 }
--
--sispm10403166lDHCPServerPoolEntry OBJECT-TYPE
--   SYNTAX      SISPM10403166LDHCPServerPoolEntry
--   MAX-ACCESS  not-accessible
--   STATUS      current
--   DESCRIPTION
--       " "
--   INDEX    { sispm10403166lDHCPServerConfIndex  }
--   ::= { sispm10403166lDHCPServerPoolTable 1 }
--
--SISPM10403166LDHCPServerPoolEntry ::= SEQUENCE {
--    sispm10403166lDHCPServerConfIndex               Integer32,
--    sispm10403166lDHCPServerPoolName                DisplayString,
--    sispm10403166lDHCPServerPoolType                Integer32,
--    sispm10403166lDHCPServerIP                      IpAddress,
--    sispm10403166lDHCPServerSubnetMask              IpAddress,
--    sispm10403166lDHCPServerLeaseTimeDays           Integer32,
--    sispm10403166lDHCPServerLeaseTimeHours          Integer32,
--    sispm10403166lDHCPServerLeaseTimeMinutes        Integer32,
--    sispm10403166lDHCPServerDomainName              DisplayString,
--    sispm10403166lDHCPServerBroadcastAddress        IpAddress,
--    sispm10403166lDHCPServerDefRouter1              IpAddress,
--    sispm10403166lDHCPServerDefRouter2              IpAddress,
--    sispm10403166lDHCPServerDefRouter3              IpAddress,
--    sispm10403166lDHCPServerDefRouter4              IpAddress,
--    sispm10403166lDHCPServerDNSServer1              IpAddress,
--    sispm10403166lDHCPServerDNSServer2              IpAddress,
--    sispm10403166lDHCPServerDNSServer3              IpAddress,
--    sispm10403166lDHCPServerDNSServer4              IpAddress,
--    sispm10403166lDHCPServerNTPServer1              IpAddress,
--    sispm10403166lDHCPServerNTPServer2              IpAddress,
--    sispm10403166lDHCPServerNTPServer3              IpAddress,
--    sispm10403166lDHCPServerNTPServer4              IpAddress,
--    sispm10403166lDHCPServerNetbiosType             Integer32,
--    sispm10403166lDHCPServerNetbiosScope            DisplayString,
--    sispm10403166lDHCPServerNetbiosNameServer1      IpAddress,
--    sispm10403166lDHCPServerNetbiosNameServer2      IpAddress,
--    sispm10403166lDHCPServerNetbiosNameServer3      IpAddress,
--    sispm10403166lDHCPServerNetbiosNameServer4      IpAddress,
--    sispm10403166lDHCPServerNisDomainName           DisplayString,
--    sispm10403166lDHCPServerNisServer1              IpAddress,
--    sispm10403166lDHCPServerNisServer2              IpAddress,
--    sispm10403166lDHCPServerNisServer3              IpAddress,
--    sispm10403166lDHCPServerNisServer4              IpAddress,
--    sispm10403166lDHCPServerClientIDType            Integer32,
--    sispm10403166lDHCPServerClientID                DisplayString,
--    sispm10403166lDHCPServerHWAddr                  DisplayString,
--    sispm10403166lDHCPServerClientName              DisplayString,
--    sispm10403166lDHCPServerVendorClassID1          DisplayString,
--    sispm10403166lDHCPServerVendorSpecificInfo1     DisplayString,
--    sispm10403166lDHCPServerVendorClassID2          DisplayString,
--    sispm10403166lDHCPServerVendorSpecificInfo2     DisplayString,
--    sispm10403166lDHCPServerVendorClassID3          DisplayString,
--    sispm10403166lDHCPServerVendorSpecificInfo3     DisplayString,
--    sispm10403166lDHCPServerVendorClassID4          DisplayString,
--    sispm10403166lDHCPServerVendorSpecificInfo4     DisplayString,
--    sispm10403166lDHCPServerVendorClassID5          DisplayString,
--    sispm10403166lDHCPServerVendorSpecificInfo5     DisplayString,
--    sispm10403166lDHCPServerVendorClassID6          DisplayString,
--    sispm10403166lDHCPServerVendorSpecificInfo6     DisplayString,
--    sispm10403166lDHCPServerVendorClassID7          DisplayString,
--    sispm10403166lDHCPServerVendorSpecificInfo7     DisplayString,
--    sispm10403166lDHCPServerVendorClassID8          DisplayString,
--    sispm10403166lDHCPServerVendorSpecificInfo8     DisplayString,
--    sispm10403166lDHCPServerRowStatus               RowStatus
--}
--
--sispm10403166lDHCPServerConfIndex OBJECT-TYPE
--   SYNTAX      Integer32 (1..64)
--   MAX-ACCESS  not-accessible
--   STATUS      current
--   DESCRIPTION
--       " pool, range : 1 - 64. "
--   ::= { sispm10403166lDHCPServerPoolEntry 1 }
--
--sispm10403166lDHCPServerPoolName OBJECT-TYPE
--   SYNTAX      DisplayString(SIZE (1..32))
--   MAX-ACCESS  read-create
--   STATUS      current
--   DESCRIPTION
--       " DHCP pool name. "
--   ::= { sispm10403166lDHCPServerPoolEntry 2 }
--
--sispm10403166lDHCPServerPoolType OBJECT-TYPE
--   SYNTAX      Integer32(0|1|2)
--   MAX-ACCESS  read-create
--   STATUS      current
--   DESCRIPTION
--       " DHCP Server Pool Type.
--	   0:None
--	   1:Network
--	   2:Host, please set DHCP Server IP first."
--   ::= { sispm10403166lDHCPServerPoolEntry 3 }
--
--sispm10403166lDHCPServerIP OBJECT-TYPE
--   SYNTAX      IpAddress
--   MAX-ACCESS  read-create
--   STATUS      current
--   DESCRIPTION
--       " DHCP Server IP. "
--   ::= { sispm10403166lDHCPServerPoolEntry 4 }
--
--sispm10403166lDHCPServerSubnetMask OBJECT-TYPE
--   SYNTAX      IpAddress
--   MAX-ACCESS  read-create
--   STATUS      current
--   DESCRIPTION
--       " DHCP Server IPv4 Subnet Mask. "
--   ::= { sispm10403166lDHCPServerPoolEntry 5}
--
--sispm10403166lDHCPServerLeaseTimeDays OBJECT-TYPE
--   SYNTAX      Integer32(0..365)
--   MAX-ACCESS  read-create
--   STATUS      current
--   DESCRIPTION
--       " DHCP Server IPv4 Lease Time:Days. "
--   ::= { sispm10403166lDHCPServerPoolEntry 6 }
--
--sispm10403166lDHCPServerLeaseTimeHours OBJECT-TYPE
--   SYNTAX      Integer32(0..23)
--   MAX-ACCESS  read-create
--   STATUS      current
--   DESCRIPTION
--       " DHCP Server IPv4 Lease Time:Hours. "
--   ::= { sispm10403166lDHCPServerPoolEntry 7 }
--
--sispm10403166lDHCPServerLeaseTimeMinutes OBJECT-TYPE
--   SYNTAX      Integer32(0..59)
--   MAX-ACCESS  read-create
--   STATUS      current
--   DESCRIPTION
--       " DHCP Server IPv4 Lease Time:Minutes. "
--   ::= { sispm10403166lDHCPServerPoolEntry 8 }
--
--sispm10403166lDHCPServerDomainName OBJECT-TYPE
--   SYNTAX      DisplayString(SIZE (0..128))
--   MAX-ACCESS  read-create
--   STATUS      current
--   DESCRIPTION
--       " DHCP Server Domain Name. "
--   ::= { sispm10403166lDHCPServerPoolEntry 9 }
--
--sispm10403166lDHCPServerBroadcastAddress OBJECT-TYPE
--   SYNTAX      IpAddress
--   MAX-ACCESS  read-create
--   STATUS      current
--   DESCRIPTION
--       " DHCP Server IPv4 Broadcast Address. "
--   ::= { sispm10403166lDHCPServerPoolEntry 10 }
--
--sispm10403166lDHCPServerDefRouter1 OBJECT-TYPE
--   SYNTAX      IpAddress
--   MAX-ACCESS  read-create
--   STATUS      current
--   DESCRIPTION
--       " DHCP Server IPv4 Default Router 1. "
--   ::= { sispm10403166lDHCPServerPoolEntry 11 }
--
--sispm10403166lDHCPServerDefRouter2 OBJECT-TYPE
--   SYNTAX      IpAddress
--   MAX-ACCESS  read-create
--   STATUS      current
--   DESCRIPTION
--       " DHCP Server IPv4 Default Router 2. "
--   ::= { sispm10403166lDHCPServerPoolEntry 12 }
--
--sispm10403166lDHCPServerDefRouter3 OBJECT-TYPE
--   SYNTAX      IpAddress
--   MAX-ACCESS  read-create
--   STATUS      current
--   DESCRIPTION
--       " DHCP Server IPv4 Default Router 3. "
--   ::= { sispm10403166lDHCPServerPoolEntry 13 }
--
--sispm10403166lDHCPServerDefRouter4 OBJECT-TYPE
--   SYNTAX      IpAddress
--   MAX-ACCESS  read-create
--   STATUS      current
--   DESCRIPTION
--       " DHCP Server IPv4 Default Router 4. "
--   ::= { sispm10403166lDHCPServerPoolEntry 14 }
--
--sispm10403166lDHCPServerDNSServer1 OBJECT-TYPE
--   SYNTAX      IpAddress
--   MAX-ACCESS  read-create
--   STATUS      current
--   DESCRIPTION
--       " DHCP Server DNS Server 1. "
--   ::= { sispm10403166lDHCPServerPoolEntry 15 }
--
--sispm10403166lDHCPServerDNSServer2 OBJECT-TYPE
--   SYNTAX      IpAddress
--   MAX-ACCESS  read-create
--   STATUS      current
--   DESCRIPTION
--       " DHCP Server DNS Server 2. "
--   ::= { sispm10403166lDHCPServerPoolEntry 16 }
--
--sispm10403166lDHCPServerDNSServer3 OBJECT-TYPE
--   SYNTAX      IpAddress
--   MAX-ACCESS  read-create
--   STATUS      current
--   DESCRIPTION
--       " DHCP Server DNS Server 3. "
--   ::= { sispm10403166lDHCPServerPoolEntry 17 }
--
--sispm10403166lDHCPServerDNSServer4 OBJECT-TYPE
--   SYNTAX      IpAddress
--   MAX-ACCESS  read-create
--   STATUS      current
--   DESCRIPTION
--       " DHCP Server DNS Server 4. "
--   ::= { sispm10403166lDHCPServerPoolEntry 18 }
--
--sispm10403166lDHCPServerNTPServer1 OBJECT-TYPE
--   SYNTAX      IpAddress
--   MAX-ACCESS  read-create
--   STATUS      current
--   DESCRIPTION
--       " DHCP Server NTP Server 1. "
--   ::= { sispm10403166lDHCPServerPoolEntry 19 }
--
--sispm10403166lDHCPServerNTPServer2 OBJECT-TYPE
--   SYNTAX      IpAddress
--   MAX-ACCESS  read-create
--   STATUS      current
--   DESCRIPTION
--       " DHCP Server NTP Server 2. "
--   ::= { sispm10403166lDHCPServerPoolEntry 20 }
--
--sispm10403166lDHCPServerNTPServer3 OBJECT-TYPE
--   SYNTAX      IpAddress
--   MAX-ACCESS  read-create
--   STATUS      current
--   DESCRIPTION
--       " DHCP Server NTP Server 3. "
--   ::= { sispm10403166lDHCPServerPoolEntry 21 }
--
--sispm10403166lDHCPServerNTPServer4 OBJECT-TYPE
--   SYNTAX      IpAddress
--   MAX-ACCESS  read-create
--   STATUS      current
--   DESCRIPTION
--       " DHCP Server NTP Server 4. "
--   ::= { sispm10403166lDHCPServerPoolEntry 22 }
--
--sispm10403166lDHCPServerNetbiosType OBJECT-TYPE
--   SYNTAX      Integer32(1..4)
--   MAX-ACCESS  read-create
--   STATUS      current
--   DESCRIPTION
--       " DHCP Server Netbios Node Type.
--	   0:None
--	   1:B-node
--	   2:P-node
--	   3:M-node
--	   4:H-node"
--   ::= { sispm10403166lDHCPServerPoolEntry 23 }
--
--sispm10403166lDHCPServerNetbiosScope OBJECT-TYPE
--   SYNTAX      DisplayString(SIZE (0..128))
--   MAX-ACCESS  read-create
--   STATUS      current
--   DESCRIPTION
--       " DHCP Server Netbios Scope. "
--   ::= { sispm10403166lDHCPServerPoolEntry 24 }
--
--sispm10403166lDHCPServerNetbiosNameServer1 OBJECT-TYPE
--   SYNTAX      IpAddress
--   MAX-ACCESS  read-create
--   STATUS      current
--   DESCRIPTION
--       " DHCP Server Netbios Name Server 1. "
--   ::= { sispm10403166lDHCPServerPoolEntry 25 }
--
--sispm10403166lDHCPServerNetbiosNameServer2 OBJECT-TYPE
--   SYNTAX      IpAddress
--   MAX-ACCESS  read-create
--   STATUS      current
--   DESCRIPTION
--       " DHCP Server Netbios Name Server 2. "
--   ::= { sispm10403166lDHCPServerPoolEntry 26 }
--
--sispm10403166lDHCPServerNetbiosNameServer3 OBJECT-TYPE
--   SYNTAX      IpAddress
--   MAX-ACCESS  read-create
--   STATUS      current
--   DESCRIPTION
--       " DHCP Server Netbios Name Server 3. "
--   ::= { sispm10403166lDHCPServerPoolEntry 27 }
--
--sispm10403166lDHCPServerNetbiosNameServer4 OBJECT-TYPE
--   SYNTAX      IpAddress
--   MAX-ACCESS  read-create
--   STATUS      current
--   DESCRIPTION
--       " DHCP Server Netbios Name Server 4. "
--   ::= { sispm10403166lDHCPServerPoolEntry 28 }
--
--sispm10403166lDHCPServerNisDomainName OBJECT-TYPE
--   SYNTAX      DisplayString(SIZE (0..128))
--   MAX-ACCESS  read-create
--   STATUS      current
--   DESCRIPTION
--       " DHCP Server Nis Domain Name. "
--   ::= { sispm10403166lDHCPServerPoolEntry 29 }
--
--sispm10403166lDHCPServerNisServer1 OBJECT-TYPE
--   SYNTAX      IpAddress
--   MAX-ACCESS  read-create
--   STATUS      current
--   DESCRIPTION
--       " DHCP Server Nis Server 1. "
--   ::= { sispm10403166lDHCPServerPoolEntry 30 }
--
--sispm10403166lDHCPServerNisServer2 OBJECT-TYPE
--   SYNTAX      IpAddress
--   MAX-ACCESS  read-create
--   STATUS      current
--   DESCRIPTION
--       " DHCP Server Nis Server 2. "
--   ::= { sispm10403166lDHCPServerPoolEntry 31 }
--
--sispm10403166lDHCPServerNisServer3 OBJECT-TYPE
--   SYNTAX      IpAddress
--   MAX-ACCESS  read-create
--   STATUS      current
--   DESCRIPTION
--       " DHCP Server Nis Server 3. "
--   ::= { sispm10403166lDHCPServerPoolEntry 32 }
--
--sispm10403166lDHCPServerNisServer4 OBJECT-TYPE
--   SYNTAX      IpAddress
--   MAX-ACCESS  read-create
--   STATUS      current
--   DESCRIPTION
--       " DHCP Server Nis Server 4. "
--   ::= { sispm10403166lDHCPServerPoolEntry 33 }
--
--sispm10403166lDHCPServerClientIDType OBJECT-TYPE
--   SYNTAX      Integer32(0..2)
--   MAX-ACCESS  read-create
--   STATUS      current
--   DESCRIPTION
--       " DHCP Server Client ID Type.
--	   0:None
--	   1:FQDN
--	   2:MAC"
--   ::= { sispm10403166lDHCPServerPoolEntry 34 }
--
--sispm10403166lDHCPServerClientID OBJECT-TYPE
--   SYNTAX      DisplayString(SIZE (0..128))
--   MAX-ACCESS  read-create
--   STATUS      current
--   DESCRIPTION
--       " DHCP Server Pool Client ID. "
--   ::= { sispm10403166lDHCPServerPoolEntry 35 }
--
--sispm10403166lDHCPServerHWAddr OBJECT-TYPE
--   SYNTAX      DisplayString(SIZE (0..17))
--   MAX-ACCESS  read-create
--   STATUS      current
--   DESCRIPTION
--       " DHCP Server Pool Hardware Address. "
--   ::= { sispm10403166lDHCPServerPoolEntry 36 }
--
--sispm10403166lDHCPServerClientName OBJECT-TYPE
--   SYNTAX      DisplayString(SIZE (0..32))
--   MAX-ACCESS  read-create
--   STATUS      current
--   DESCRIPTION
--       " DHCP Server Pool Client Name. "
--   ::= { sispm10403166lDHCPServerPoolEntry 37 }
--
--sispm10403166lDHCPServerVendorClassID1 OBJECT-TYPE
--   SYNTAX      DisplayString(SIZE (0..64))
--   MAX-ACCESS  read-create
--   STATUS      current
--   DESCRIPTION
--       " DHCP Server Vendor Class ID 1. Please also set VendorSpecificInfo1."
--   ::= { sispm10403166lDHCPServerPoolEntry 38 }
--
--sispm10403166lDHCPServerVendorSpecificInfo1 OBJECT-TYPE
--   SYNTAX      DisplayString(SIZE (0..32))
--   MAX-ACCESS  read-create
--   STATUS      current
--   DESCRIPTION
--       " DHCP Server Vendor Specific Info 1. Please also set VendorClassID1."
--   ::= { sispm10403166lDHCPServerPoolEntry 39 }
--
--sispm10403166lDHCPServerVendorClassID2 OBJECT-TYPE
--   SYNTAX      DisplayString(SIZE (0..64))
--   MAX-ACCESS  read-create
--   STATUS      current
--   DESCRIPTION
--       " DHCP Server Vendor Class ID 2. Please also set VendorSpecificInfo2."
--   ::= { sispm10403166lDHCPServerPoolEntry 40 }
--
--sispm10403166lDHCPServerVendorSpecificInfo2 OBJECT-TYPE
--   SYNTAX      DisplayString(SIZE (0..32))
--   MAX-ACCESS  read-create
--   STATUS      current
--   DESCRIPTION
--       " DHCP Server Vendor Specific Info 2. Please also set VendorClassID2."
--   ::= { sispm10403166lDHCPServerPoolEntry 41 }
--
--sispm10403166lDHCPServerVendorClassID3 OBJECT-TYPE
--   SYNTAX      DisplayString(SIZE (0..64))
--   MAX-ACCESS  read-create
--   STATUS      current
--   DESCRIPTION
--       " DHCP Server Vendor Class ID 3. Please also set VendorSpecificInfo3."
--   ::= { sispm10403166lDHCPServerPoolEntry 42 }
--
--sispm10403166lDHCPServerVendorSpecificInfo3 OBJECT-TYPE
--   SYNTAX      DisplayString(SIZE (0..32))
--   MAX-ACCESS  read-create
--   STATUS      current
--   DESCRIPTION
--       " DHCP Server Vendor Specific Info 3. Please also set VendorClassID3."
--   ::= { sispm10403166lDHCPServerPoolEntry 43 }
--
--sispm10403166lDHCPServerVendorClassID4 OBJECT-TYPE
--   SYNTAX      DisplayString(SIZE (0..64))
--   MAX-ACCESS  read-create
--   STATUS      current
--   DESCRIPTION
--       " DHCP Server Vendor Class ID 4. Please also set VendorSpecificInfo4."
--   ::= { sispm10403166lDHCPServerPoolEntry 44 }
--
--sispm10403166lDHCPServerVendorSpecificInfo4 OBJECT-TYPE
--   SYNTAX      DisplayString(SIZE (0..32))
--   MAX-ACCESS  read-create
--   STATUS      current
--   DESCRIPTION
--       " DHCP Server Vendor Specific Info 4. Please also set VendorClassID4."
--   ::= { sispm10403166lDHCPServerPoolEntry 45 }
--
--sispm10403166lDHCPServerVendorClassID5 OBJECT-TYPE
--   SYNTAX      DisplayString(SIZE (0..64))
--   MAX-ACCESS  read-create
--   STATUS      current
--   DESCRIPTION
--       " DHCP Server Vendor Class ID 5. Please also set VendorSpecificInfo5."
--   ::= { sispm10403166lDHCPServerPoolEntry 46 }
--
--sispm10403166lDHCPServerVendorSpecificInfo5 OBJECT-TYPE
--   SYNTAX      DisplayString(SIZE (0..32))
--   MAX-ACCESS  read-create
--   STATUS      current
--   DESCRIPTION
--       " DHCP Server Vendor Specific Info 5. Please also set VendorClassID5."
--   ::= { sispm10403166lDHCPServerPoolEntry 47 }
--
--sispm10403166lDHCPServerVendorClassID6 OBJECT-TYPE
--   SYNTAX      DisplayString(SIZE (0..64))
--   MAX-ACCESS  read-create
--   STATUS      current
--   DESCRIPTION
--       " DHCP Server Vendor Class ID 6. Please also set VendorSpecificInfo6."
--   ::= { sispm10403166lDHCPServerPoolEntry 48 }
--
--sispm10403166lDHCPServerVendorSpecificInfo6 OBJECT-TYPE
--   SYNTAX      DisplayString(SIZE (0..32))
--   MAX-ACCESS  read-create
--   STATUS      current
--   DESCRIPTION
--       " DHCP Server Vendor Specific Info 6. Please also set VendorClassID6."
--   ::= { sispm10403166lDHCPServerPoolEntry 49 }
--
--sispm10403166lDHCPServerVendorClassID7 OBJECT-TYPE
--   SYNTAX      DisplayString(SIZE (0..64))
--   MAX-ACCESS  read-create
--   STATUS      current
--   DESCRIPTION
--       " DHCP Server Vendor Class ID 7. Please also set VendorSpecificInfo7."
--   ::= { sispm10403166lDHCPServerPoolEntry 50 }
--
--sispm10403166lDHCPServerVendorSpecificInfo7 OBJECT-TYPE
--   SYNTAX      DisplayString(SIZE (0..32))
--   MAX-ACCESS  read-create
--   STATUS      current
--   DESCRIPTION
--       " DHCP Server Vendor Specific Info 7. Please also set VendorClassID7."
--   ::= { sispm10403166lDHCPServerPoolEntry 51 }
--
--sispm10403166lDHCPServerVendorClassID8 OBJECT-TYPE
--   SYNTAX      DisplayString(SIZE (0..64))
--   MAX-ACCESS  read-create
--   STATUS      current
--   DESCRIPTION
--       " DHCP Server Vendor Class ID 8. Please also set VendorSpecificInfo8."
--   ::= { sispm10403166lDHCPServerPoolEntry 52 }
--
--sispm10403166lDHCPServerVendorSpecificInfo8 OBJECT-TYPE
--   SYNTAX      DisplayString(SIZE (0..32))
--   MAX-ACCESS  read-create
--   STATUS      current
--   DESCRIPTION
--       " DHCP Server Vendor Specific Info 8. Please also set VendorClassID8."
--   ::= { sispm10403166lDHCPServerPoolEntry 53 }
--
--sispm10403166lDHCPServerRowStatus OBJECT-TYPE
--   SYNTAX      RowStatus
--   MAX-ACCESS  read-create
--   STATUS      current
--   DESCRIPTION
--      "This object indicates the status of this entry, and is
--       used to create/delete entries.  Any object in an entry of
--       this table may be modified while the value of the
--       corresponding instance of this object is active(1).
--       createAndGo, notReady not supported."
--   ::= {sispm10403166lDHCPServerPoolEntry 54 }
--
--sispm10403166lDHCPServerStatistics                         OBJECT IDENTIFIER ::= { sispm10403166lDHCPServer 4 }
--
--sispm10403166lDHCPServerStatisticsDatabaseCountersPool OBJECT-TYPE
--   SYNTAX      Integer32
--   MAX-ACCESS  read-only
--   STATUS      current
--   DESCRIPTION
--       "
--       "
--   ::= { sispm10403166lDHCPServerStatistics 1 }
--
--sispm10403166lDHCPServerStatisticsDatabaseCountersExcludedIPAddress OBJECT-TYPE
--   SYNTAX      Integer32
--   MAX-ACCESS  read-only
--   STATUS      current
--   DESCRIPTION
--       "
--       "
--   ::= { sispm10403166lDHCPServerStatistics 2 }
--
--sispm10403166lDHCPServerStatisticsDatabaseCountersDeclinedIPAddress OBJECT-TYPE
--   SYNTAX      Integer32
--   MAX-ACCESS  read-only
--   STATUS      current
--   DESCRIPTION
--       "
--       "
--   ::= { sispm10403166lDHCPServerStatistics 3 }
--
--sispm10403166lDHCPServerStatisticsBindingCountersAutomaticBinding OBJECT-TYPE
--   SYNTAX      Integer32
--   MAX-ACCESS  read-only
--   STATUS      current
--   DESCRIPTION
--       "
--       "
--   ::= { sispm10403166lDHCPServerStatistics 4 }
--
--sispm10403166lDHCPServerStatisticsBindingCountersManualBinding OBJECT-TYPE
--   SYNTAX      Integer32
--   MAX-ACCESS  read-only
--   STATUS      current
--   DESCRIPTION
--       "
--       "
--   ::= { sispm10403166lDHCPServerStatistics 5 }
--
--sispm10403166lDHCPServerStatisticsBindingCountersExpiredBinding OBJECT-TYPE
--   SYNTAX      Integer32
--   MAX-ACCESS  read-only
--   STATUS      current
--   DESCRIPTION
--       "
--       "
--   ::= { sispm10403166lDHCPServerStatistics 6 }
--
--sispm10403166lDHCPServerStatisticsDHCPMessageReceivedCountersDISCOVER OBJECT-TYPE
--   SYNTAX      Integer32
--   MAX-ACCESS  read-only
--   STATUS      current
--   DESCRIPTION
--       "
--       "
--   ::= { sispm10403166lDHCPServerStatistics 7 }
--
--sispm10403166lDHCPServerStatisticsDHCPMessageReceivedCountersREQUEST OBJECT-TYPE
--   SYNTAX      Integer32
--   MAX-ACCESS  read-only
--   STATUS      current
--   DESCRIPTION
--       "
--       "
--   ::= { sispm10403166lDHCPServerStatistics 8 }
--
--sispm10403166lDHCPServerStatisticsDHCPMessageReceivedCountersDECLINE OBJECT-TYPE
--   SYNTAX      Integer32
--   MAX-ACCESS  read-only
--   STATUS      current
--   DESCRIPTION
--       "
--       "
--   ::= { sispm10403166lDHCPServerStatistics 9 }
--
--sispm10403166lDHCPServerStatisticsDHCPMessageReceivedCountersRELEASE OBJECT-TYPE
--   SYNTAX      Integer32
--   MAX-ACCESS  read-only
--   STATUS      current
--   DESCRIPTION
--       "
--       "
--   ::= { sispm10403166lDHCPServerStatistics 10 }
--
--sispm10403166lDHCPServerStatisticsDHCPMessageReceivedCountersINFORM OBJECT-TYPE
--   SYNTAX      Integer32
--   MAX-ACCESS  read-only
--   STATUS      current
--   DESCRIPTION
--       "
--       "
--   ::= { sispm10403166lDHCPServerStatistics 11 }
--
--sispm10403166lDHCPServerStatisticsDHCPMessageSentCountersOFFER OBJECT-TYPE
--   SYNTAX      Integer32
--   MAX-ACCESS  read-only
--   STATUS      current
--   DESCRIPTION
--       "
--       "
--   ::= { sispm10403166lDHCPServerStatistics 12 }
--
--sispm10403166lDHCPServerStatisticsDHCPMessageSentCountersACK OBJECT-TYPE
--   SYNTAX      Integer32
--   MAX-ACCESS  read-only
--   STATUS      current
--   DESCRIPTION
--       "
--       "
--   ::= { sispm10403166lDHCPServerStatistics 13 }
--
--sispm10403166lDHCPServerStatisticsDHCPMessageSentCountersNAK OBJECT-TYPE
--   SYNTAX      Integer32
--   MAX-ACCESS  read-only
--   STATUS      current
--   DESCRIPTION
--       "
--       "
--   ::= { sispm10403166lDHCPServerStatistics 14 }
--
--sispm10403166lDHCPServerClear OBJECT-TYPE
--   SYNTAX      Integer32
--   MAX-ACCESS  read-write
--   STATUS      current
--   DESCRIPTION
--       "
--       "
--   ::= { sispm10403166lDHCPServerStatistics 15 }
--
--sispm10403166lDHCPServerBinding                         OBJECT IDENTIFIER ::= { sispm10403166lDHCPServer 5 }
--
--sispm10403166lDHCPServerBindingTable OBJECT-TYPE
--   SYNTAX      SEQUENCE OF SISPM10403166LDHCPServerBindingEntry
--   MAX-ACCESS  not-accessible
--   STATUS      current
--   DESCRIPTION
--       " "
--   ::= { sispm10403166lDHCPServerBinding 1 }
--
--sispm10403166lDHCPServerBindingEntry OBJECT-TYPE
--   SYNTAX      SISPM10403166LDHCPServerBindingEntry
--   MAX-ACCESS  not-accessible
--   STATUS      current
--   DESCRIPTION
--       " "
--   INDEX    { sispm10403166lDHCPServerBindingIndex  }
--   ::= { sispm10403166lDHCPServerBindingTable 1 }
--
--SISPM10403166LDHCPServerBindingEntry ::= SEQUENCE {
--   sispm10403166lDHCPServerBindingIndex                 Integer32,
--   sispm10403166lDHCPServerBindingIP                    DisplayString,
--   sispm10403166lDHCPServerBindingType                  DisplayString,
--   sispm10403166lDHCPServerBindingState                 DisplayString,
--   sispm10403166lDHCPServerBindingPoolName              DisplayString,
--   sispm10403166lDHCPServerBindingServerID              DisplayString,
--   sispm10403166lDHCPServerBindingVLAN                  Integer32,
--   sispm10403166lDHCPServerBindingSubnetMask            DisplayString,
--   sispm10403166lDHCPServerBindingClientIDType          DisplayString,
--   sispm10403166lDHCPServerBindingClientIDValue         DisplayString,
--   sispm10403166lDHCPServerBindingMACAddress            DisplayString,
--   sispm10403166lDHCPServerBindingLeaseTime             DisplayString,
--   sispm10403166lDHCPServerBindingWillExpiredIn         DisplayString,
--   sispm10403166lDHCPServerBindingDelete                Integer32
--}
--
--sispm10403166lDHCPServerBindingIndex OBJECT-TYPE
--   SYNTAX      Integer32
--   MAX-ACCESS  not-accessible
--   STATUS      current
--   DESCRIPTION
--       "Index"
--   ::= { sispm10403166lDHCPServerBindingEntry 1 }
--
--sispm10403166lDHCPServerBindingIP OBJECT-TYPE
--   SYNTAX      DisplayString
--   MAX-ACCESS  read-only
--   STATUS      current
--   DESCRIPTION
--       " "
--   ::= { sispm10403166lDHCPServerBindingEntry 2 }
--
--sispm10403166lDHCPServerBindingType OBJECT-TYPE
--   SYNTAX      DisplayString
--   MAX-ACCESS  read-only
--   STATUS      current
--   DESCRIPTION
--       " "
--   ::= { sispm10403166lDHCPServerBindingEntry 3 }
--
--sispm10403166lDHCPServerBindingState OBJECT-TYPE
--   SYNTAX      DisplayString
--   MAX-ACCESS  read-only
--   STATUS      current
--   DESCRIPTION
--       " "
--   ::= { sispm10403166lDHCPServerBindingEntry 4 }
--
--sispm10403166lDHCPServerBindingPoolName OBJECT-TYPE
--   SYNTAX      DisplayString
--   MAX-ACCESS  read-only
--   STATUS      current
--   DESCRIPTION
--       " "
--   ::= { sispm10403166lDHCPServerBindingEntry 5 }
--
--sispm10403166lDHCPServerBindingServerID OBJECT-TYPE
--   SYNTAX      DisplayString
--   MAX-ACCESS  read-only
--   STATUS      current
--   DESCRIPTION
--       " "
--   ::= { sispm10403166lDHCPServerBindingEntry 6 }
--
--sispm10403166lDHCPServerBindingVLAN OBJECT-TYPE
--   SYNTAX      Integer32
--   MAX-ACCESS  read-only
--   STATUS      current
--   DESCRIPTION
--       " "
--   ::= { sispm10403166lDHCPServerBindingEntry 7 }
--
--sispm10403166lDHCPServerBindingSubnetMask OBJECT-TYPE
--   SYNTAX      DisplayString
--   MAX-ACCESS  read-only
--   STATUS      current
--   DESCRIPTION
--       " "
--   ::= { sispm10403166lDHCPServerBindingEntry 8 }
--
--sispm10403166lDHCPServerBindingClientIDType OBJECT-TYPE
--   SYNTAX      DisplayString
--   MAX-ACCESS  read-only
--   STATUS      current
--   DESCRIPTION
--       " "
--   ::= { sispm10403166lDHCPServerBindingEntry 9 }
--
--sispm10403166lDHCPServerBindingClientIDValue OBJECT-TYPE
--   SYNTAX      DisplayString
--   MAX-ACCESS  read-only
--   STATUS      current
--   DESCRIPTION
--       " "
--   ::= { sispm10403166lDHCPServerBindingEntry 10 }
--
--sispm10403166lDHCPServerBindingMACAddress OBJECT-TYPE
--   SYNTAX      DisplayString
--   MAX-ACCESS  read-only
--   STATUS      current
--   DESCRIPTION
--       " "
--   ::= { sispm10403166lDHCPServerBindingEntry 11 }
--
--sispm10403166lDHCPServerBindingLeaseTime OBJECT-TYPE
--   SYNTAX      DisplayString
--   MAX-ACCESS  read-only
--   STATUS      current
--   DESCRIPTION
--       " "
--   ::= { sispm10403166lDHCPServerBindingEntry 12 }
--
--sispm10403166lDHCPServerBindingWillExpiredIn OBJECT-TYPE
--   SYNTAX      DisplayString
--   MAX-ACCESS  read-only
--   STATUS      current
--   DESCRIPTION
--       " "
--   ::= { sispm10403166lDHCPServerBindingEntry 13 }
--
--sispm10403166lDHCPServerBindingDelete OBJECT-TYPE
--   SYNTAX      Integer32
--   MAX-ACCESS  read-write
--   STATUS      current
--   DESCRIPTION
--       " "
--   ::= { sispm10403166lDHCPServerBindingEntry 14 }
--
--sispm10403166lDHCPServerBindingClearAutomatic   OBJECT-TYPE
--   SYNTAX      Integer32
--   MAX-ACCESS  read-write
--   STATUS      current
--   DESCRIPTION
--	   "1:clear"
--   ::= { sispm10403166lDHCPServerBinding 2 }
--
--sispm10403166lDHCPServerBindingClearManual   OBJECT-TYPE
--   SYNTAX      Integer32
--   MAX-ACCESS  read-write
--   STATUS      current
--   DESCRIPTION
--	   "1:clear"
--   ::= { sispm10403166lDHCPServerBinding 3 }
--
--sispm10403166lDHCPServerBindingClearExpired   OBJECT-TYPE
--   SYNTAX      Integer32
--   MAX-ACCESS  read-write
--   STATUS      current
--   DESCRIPTION
--	   "1:clear"
--   ::= { sispm10403166lDHCPServerBinding 4 }
--
--sispm10403166lDHCPServerDeclined                         OBJECT IDENTIFIER ::= { sispm10403166lDHCPServer 6 }
--
--sispm10403166lDHCPServerDeclinedTable OBJECT-TYPE
--   SYNTAX      SEQUENCE OF SISPM10403166LDHCPServerDeclinedEntry
--   MAX-ACCESS  not-accessible
--   STATUS      current
--   DESCRIPTION
--       " "
--   ::= { sispm10403166lDHCPServerDeclined 1 }
--
--sispm10403166lDHCPServerDeclinedEntry OBJECT-TYPE
--   SYNTAX      SISPM10403166LDHCPServerDeclinedEntry
--   MAX-ACCESS  not-accessible
--   STATUS      current
--   DESCRIPTION
--       " "
--   INDEX    { sispm10403166lDHCPServerDeclinedIndex  }
--   ::= { sispm10403166lDHCPServerDeclinedTable 1 }
--
--SISPM10403166LDHCPServerDeclinedEntry ::= SEQUENCE {
--   sispm10403166lDHCPServerDeclinedIndex                 Integer32,
--   sispm10403166lDHCPServerDeclinedIP                    DisplayString
--}
--
--sispm10403166lDHCPServerDeclinedIndex OBJECT-TYPE
--   SYNTAX      Integer32
--   MAX-ACCESS  not-accessible
--   STATUS      current
--   DESCRIPTION
--       "Index"
--   ::= { sispm10403166lDHCPServerDeclinedEntry 1 }
--
--sispm10403166lDHCPServerDeclinedIP OBJECT-TYPE
--   SYNTAX      DisplayString
--   MAX-ACCESS  read-only
--   STATUS      current
--   DESCRIPTION
--       " "
--   ::= { sispm10403166lDHCPServerDeclinedEntry 2 }

-- =======================================================================================================================
sispm10403166lVLANConf                                     OBJECT IDENTIFIER ::= { sispm10403166lSystem 10 }

sispm10403166lVLAN                                     OBJECT IDENTIFIER ::= { sispm10403166lVLANConf 2}

sispm10403166lVlanStatus              OBJECT IDENTIFIER   ::= { sispm10403166lVLAN 6 }

--
-- =======================================================================================================================
-- Start sispm10403166lVlan group
-- =======================================================================================================================
    sispm10403166lVlanExistingVLANs  OBJECT-TYPE
               SYNTAX      DisplayString
               MAX-ACCESS  read-write
               STATUS      current
               DESCRIPTION
                   "This field shows the VLANs that are created on the switch.
                    More VLANs may be created by using a
                    list syntax where the individual elements are separated by commas.
                    Ranges are specified with a
                    dash separating the lower and upper bound.
                    The following example will create VLANs 1, 10, 11, 12
                    , 13, 200, and 300: 1,10-13,200,300.
                    default: 1."
               ::= {     sispm10403166lVLAN 1 }

    sispm10403166lVlanEthertypeforCustomSPorts  OBJECT-TYPE
               SYNTAX      DisplayString
               MAX-ACCESS  read-write
               STATUS      current
               DESCRIPTION
                   "This field specifies the ethertype/TPID (specified in hexadecimal)
                    used for Custom S-ports. The
                    setting is in force for all ports whose Port Type
                    is set to S-Custom-Port.
                    range: 0600-ffff,
                    default: 88a8."
               ::= {     sispm10403166lVLAN 2 }

    sispm10403166lVlanTable OBJECT-TYPE
               SYNTAX      SEQUENCE OF     SISPM10403166LVlanEntry
               MAX-ACCESS  not-accessible
               STATUS      current
               DESCRIPTION
                   "Configure Vlan ports Configuration mode.
                    INDEX for this table is ifIndex which is
                    equivalent to the panel port number."
               ::= {     sispm10403166lVLAN 3 }

    sispm10403166lVlanEntry OBJECT-TYPE
               SYNTAX          SISPM10403166LVlanEntry
               MAX-ACCESS  not-accessible
               STATUS      current
               DESCRIPTION
                   "The Vlan entry."
               INDEX    {     ifIndex  }
               ::= {     sispm10403166lVlanTable 1 }

    SISPM10403166LVlanEntry             ::= SEQUENCE {
                sispm10403166lVlanMode              INTEGER,
                sispm10403166lVlanPortVLAN          Integer32,
                sispm10403166lVlanPortType          INTEGER,
                sispm10403166lVlanIngressFiltering  AdminMode,
--              sispm10403166lVlanVLANTrunking      AdminMode,
                sispm10403166lVlanIngressAcceptance INTEGER,
                sispm10403166lVlanEgressTagging     INTEGER,
                sispm10403166lVlanAllowedVLANs      DisplayString,
                sispm10403166lVlanForbiddenVLANs    DisplayString
                }

    sispm10403166lVlanMode OBJECT-TYPE
               SYNTAX      INTEGER{access(0), trunk(1), hybrid(2)}
               MAX-ACCESS  read-write
               STATUS      current
               DESCRIPTION
                   "The port mode determines the fundamental
                    behavior of the port in question.
                    A port can be in one of three modes as described below.
                    0: access,
                    1: trunk,
                    2: hybrid."
               DEFVAL  { access }
               ::= {     sispm10403166lVlanEntry 2 }

    sispm10403166lVlanPortVLAN OBJECT-TYPE
               SYNTAX      Integer32(1..4094)
               MAX-ACCESS  read-write
               STATUS      current
               DESCRIPTION
                   "Determines the port's VLAN ID (a.k.a. PVID).
                    range: 1-4095,
                    default: 1."
               ::= {     sispm10403166lVlanEntry 3 }

    sispm10403166lVlanPortType OBJECT-TYPE
               SYNTAX      INTEGER { unaware(0), cPort(1), sPort(2), sCustomPort(3) }
               MAX-ACCESS  read-write
               STATUS      current
               DESCRIPTION
                   "Ports in hybrid mode allow for changing the port type,
                    that is, whether a frame's VLAN tag is
                    used to classify the frame on ingress to a particular VLAN,
                    and if so, which TPID it reacts on.
                    Likewise, on egress, the Port Type determines the
                    TPID of the tag, if a tag is required.
                    0: unaware,
                    1: c-Port,
                    2: s-Port,
                    3: s-Custom-Port."
                DEFVAL  { cPort }
               ::= {     sispm10403166lVlanEntry 4 }

    sispm10403166lVlanIngressFiltering OBJECT-TYPE
               SYNTAX      AdminMode
               MAX-ACCESS  read-write
               STATUS      current
               DESCRIPTION
                   "Hybrid ports allow for changing ingress filtering.
                    Access and Trunk ports always have ingress
                    filtering enabled.If ingress filtering is enabled,
                    frames classified to
                    a VLAN that the port is not a member of get discarded."
               ::= {     sispm10403166lVlanEntry 5 }

--    sispm10403166lVlanVLANTrunking OBJECT-TYPE
--               SYNTAX      AdminMode
--               MAX-ACCESS  read-write
--               STATUS      current
--               DESCRIPTION
--                   "Trunk and Hybrid ports allow for enabling VLAN trunking.
--                    When VLAN trunking is enabled, frames
--                    classified to unknown VLANs are accepted on the port
--                    whether ingress filtering is enabled or not."
--               DEFVAL  { disable }
--               ::= {     sispm10403166lVlanEntry 6 }

    sispm10403166lVlanIngressAcceptance OBJECT-TYPE
               SYNTAX      INTEGER  { taggedAndUntagged  ( 0 ),
                                      taggedOnly ( 1 ),
                                      untaggedOnly ( 2 )
                                    }
               MAX-ACCESS  read-write
               STATUS      current
               DESCRIPTION
                   "Hybrid ports allow for changing the type of frames that are
                    accepted on ingress.
                    0: Tagged and Untagged,
                    1: Tagged Only,
                    2: Untagged Only."
               ::= {     sispm10403166lVlanEntry 7 }

    sispm10403166lVlanEgressTagging OBJECT-TYPE
               SYNTAX      INTEGER  { untagPortVlan  ( 0 ),
                                      tagAll ( 1 ),
                                      untagAll ( 2 )
                                    }
               MAX-ACCESS  read-write
               STATUS      current
               DESCRIPTION
                   "Ports in Trunk and Hybrid mode may control the
                    tagging of frames on egress.
                    0: Untag Port VLAN,
                    1: Tag All,
                    2: Untag All."
               ::= {     sispm10403166lVlanEntry 8 }

    sispm10403166lVlanAllowedVLANs OBJECT-TYPE
               SYNTAX      DisplayString
               MAX-ACCESS  read-write
               STATUS      current
               DESCRIPTION
                   "Ports in Trunk and Hybrid mode may control which
                    VLANs they are allowed to become members of.
                    Access ports can only be member of one VLAN, the Access VLAN.
                    range: 1~4095.
                    '-': Allowed VLANs is empty."
               ::= {     sispm10403166lVlanEntry 9 }

    sispm10403166lVlanForbiddenVLANs OBJECT-TYPE
               SYNTAX      DisplayString
               MAX-ACCESS  read-write
               STATUS      current
               DESCRIPTION
                   "A port may be configured to never be member of one or
                    more VLANs. This is particularly useful
                    when dynamic VLAN protocols like MVRP and GVRP
                    must be prevented from dynamically adding ports
                    to VLANs.
                    range: 1~4095.
                    '-': Forbidden VLANs is empty."
               ::= {     sispm10403166lVlanEntry 10 }

--sispm10403166lVLANMembershipStatusTable

    sispm10403166lVLANMembershipStatusTable OBJECT-TYPE
               SYNTAX      SEQUENCE OF     SISPM10403166LVLANMembershipStatusEntry
               MAX-ACCESS  not-accessible
               STATUS      current
               DESCRIPTION
                   "Vlan membership Status table.
                    INDEX for this table is ifIndex which is
                    equivalent to the panel port number."
               ::= {     sispm10403166lVlanStatus 1 }

    sispm10403166lVLANMembershipStatusEntry OBJECT-TYPE
               SYNTAX          SISPM10403166LVLANMembershipStatusEntry
               MAX-ACCESS  not-accessible
               STATUS      current
               DESCRIPTION
                   "Vlan membership Status entry."
               INDEX    {     ifIndex, sispm10403166lVLANMembershipVlanID    }
               ::= {     sispm10403166lVLANMembershipStatusTable 1 }

    SISPM10403166LVLANMembershipStatusEntry             ::= SEQUENCE {
                sispm10403166lVLANMembershipVlanID      Integer32,
                sispm10403166lVLANMembershipStatus      INTEGER
                }

    sispm10403166lVLANMembershipVlanID OBJECT-TYPE
               SYNTAX      Integer32(1..4095)
               MAX-ACCESS  not-accessible
               STATUS      current
               DESCRIPTION
                   "VLAN ID for which the Port members are displayed."
               ::= {     sispm10403166lVLANMembershipStatusEntry 2 }

    sispm10403166lVLANMembershipStatus OBJECT-TYPE
               SYNTAX      INTEGER  { portIsNotInVlan  ( 0 ),
                                      portIncludedInVlan ( 1 ),
                                      portInForbiddenPortList( 2 ),
                                      portInForbiddenPortListAndVlan( 3 )
                                    }
               MAX-ACCESS  read-only
               STATUS      current
               DESCRIPTION
                   "portIsNotInVlan(0): A port is nothing in a VLAN.
                    portIncludedInVlan(1): A port is included in a VLAN.
                    portInForbiddenPortList(2): A port is in the forbidden port list.
                    portInForbiddenPortListAndVlan(3):
                     A port is in the forbidden port list and at the same
                     time attempted included in the VLAN."
               ::= {     sispm10403166lVLANMembershipStatusEntry 3 }

--sispm10403166lVLANPortStatusTable
    sispm10403166lVLANPortStatusTable OBJECT-TYPE
               SYNTAX      SEQUENCE OF     SISPM10403166LVLANPortStatusEntry
               MAX-ACCESS  not-accessible
               STATUS      current
               DESCRIPTION
                   "The vlan port status table.
                    INDEX for this table is ifIndex which is
                    equivalent to the panel port number."
               ::= {     sispm10403166lVlanStatus 2 }

    sispm10403166lVLANPortStatusEntry OBJECT-TYPE
               SYNTAX          SISPM10403166LVLANPortStatusEntry
               MAX-ACCESS  not-accessible
               STATUS      current
               DESCRIPTION
                   "The vlan port status entry."
               INDEX    {     ifIndex }
               ::= {     sispm10403166lVLANPortStatusTable 1 }

    SISPM10403166LVLANPortStatusEntry             ::= SEQUENCE {
                sispm10403166lVLANPortStatusPortType          DisplayString,
                sispm10403166lVLANPortStatusIngressFiltering  AdminMode,
                sispm10403166lVLANPortStatusFrameType         DisplayString,
                sispm10403166lVLANPortStatusPortVLANID        Integer32,
                sispm10403166lVLANPortStatusTxTag             DisplayString,
                sispm10403166lVLANPortStatusUntaggedVLANID    Integer32,
                sispm10403166lVLANPortStatusConflicts         DisplayString
                }

    sispm10403166lVLANPortStatusPortType OBJECT-TYPE
               SYNTAX      DisplayString
               MAX-ACCESS  read-only
               STATUS      current
               DESCRIPTION
                   "Shows the port type (Unaware, C-Port, S-Port,
                    S-Custom-Port.) that a given user wants to configure on
                    the port.The field is empty if not overridden by the selected user."
               ::= {     sispm10403166lVLANPortStatusEntry 2 }

    sispm10403166lVLANPortStatusIngressFiltering OBJECT-TYPE
               SYNTAX      AdminMode
               MAX-ACCESS  read-only
               STATUS      current
               DESCRIPTION
                   "Shows whether a given user wants ingress filtering enabled or not."
               ::= {     sispm10403166lVLANPortStatusEntry 3 }

    sispm10403166lVLANPortStatusFrameType OBJECT-TYPE
               SYNTAX      DisplayString
               MAX-ACCESS  read-only
               STATUS      current
               DESCRIPTION
                   "Shows the acceptable frame types (All, Taged,
                    Untagged) that a given user wants to configure on the port.
                    The field is empty if not overridden by the selected user."
               ::= {     sispm10403166lVLANPortStatusEntry 4 }

    sispm10403166lVLANPortStatusPortVLANID OBJECT-TYPE
               SYNTAX      Integer32 (1..4095)
               MAX-ACCESS  read-only
               STATUS      current
               DESCRIPTION
                   "Shows the Port VLAN ID (PVID) that a given user
                    wants the port to have.
                    The field is 0 if not overridden by the selected user."
               ::= {     sispm10403166lVLANPortStatusEntry 5 }

    sispm10403166lVLANPortStatusTxTag OBJECT-TYPE
               SYNTAX      DisplayString
               MAX-ACCESS  read-only
               STATUS      current
               DESCRIPTION
                   "Shows the Tx Tag requirements (Tag All, Tag PVID,
                    Tag UVID, Untag All, Untag PVID, Untag UVID)
                    that a given user has on a port.The field is empty
                    if not overridden by the selected user."
               ::= {     sispm10403166lVLANPortStatusEntry 6 }

    sispm10403166lVLANPortStatusUntaggedVLANID OBJECT-TYPE
               SYNTAX      Integer32(1..4095)
               MAX-ACCESS  read-only
               STATUS      current
               DESCRIPTION
                   "If Tx Tag is overridden by the selected user and is
                    set to Tag or Untag UVID, then this field will show
                    the VLAN ID the user wants to tag or untag on egress.
                    The field is 0 if not overridden by the selected
                    user."
               ::= {     sispm10403166lVLANPortStatusEntry 7 }

    sispm10403166lVLANPortStatusConflicts OBJECT-TYPE
               SYNTAX      DisplayString
               MAX-ACCESS  read-only
               STATUS      current
               DESCRIPTION
                   "Two users may have conflicting requirements to a port's
                    configuration. For instance, one user may require
                    all frames to be tagged on egress while another requires
                    all frames to be untagged on egress.Since both
                    users cannot win, this gives rise to a conflict,
                    which is solved in a prioritized way. The Administrator
                    has the least priority. Other software modules are
                    prioritized according to their position in the drop-down
                    list: The higher in the list, the higher priority.
                    If conflicts exist, it will be displayed as 'Yes'."
               ::= {     sispm10403166lVLANPortStatusEntry 8 }

sispm10403166lMacBaesdVlanMembershipConfig     OBJECT IDENTIFIER   ::= { sispm10403166lVLAN 7 }

sispm10403166lMacBaesdVlanMembershipConfigTable  OBJECT-TYPE
   SYNTAX      SEQUENCE OF SISPM10403166LMacBaesdVlanMembershipConfigEntry
   MAX-ACCESS  not-accessible
   STATUS      current
   DESCRIPTION
       "Mac-Based VLAN Membership table"
 ::= { sispm10403166lMacBaesdVlanMembershipConfig 1 }

sispm10403166lMacBaesdVlanMembershipConfigEntry OBJECT-TYPE
    SYNTAX        SISPM10403166LMacBaesdVlanMembershipConfigEntry
    MAX-ACCESS    not-accessible
    STATUS        current
    DESCRIPTION
        "Mac-Based VLAN Membership table."
    INDEX        { sispm10403166lMacBaesdVlanMembershipConfigIndex }
    ::= { sispm10403166lMacBaesdVlanMembershipConfigTable 1 }

SISPM10403166LMacBaesdVlanMembershipConfigEntry ::=
    SEQUENCE {
        sispm10403166lMacBaesdVlanMembershipConfigIndex        Integer32,
        sispm10403166lMacBaesdVlanMembershipConfigMACAddress   DisplayString,
        sispm10403166lMacBaesdVlanMembershipConfigVLANID       Integer32,
        sispm10403166lMacBaesdVlanMembershipConfigPortMembers  DisplayString,
        sispm10403166lMacBaesdVlanMembershipConfigRowStatus    RowStatus
    }

sispm10403166lMacBaesdVlanMembershipConfigIndex OBJECT-TYPE
   SYNTAX      Integer32(1..65535)
   MAX-ACCESS  not-accessible
   STATUS      current
   DESCRIPTION
       "Mac-Based VLAN membership index."
   ::= {sispm10403166lMacBaesdVlanMembershipConfigEntry 1 }

sispm10403166lMacBaesdVlanMembershipConfigMACAddress OBJECT-TYPE
   SYNTAX      DisplayString
   MAX-ACCESS  read-create
   STATUS      current
   DESCRIPTION
       "MAC address: xx-xx-xx-xx-xx-xx."
   ::= {sispm10403166lMacBaesdVlanMembershipConfigEntry 2 }

sispm10403166lMacBaesdVlanMembershipConfigVLANID OBJECT-TYPE
   SYNTAX      Integer32
   MAX-ACCESS  read-create
   STATUS      current
   DESCRIPTION
       "VLAN ID"
   ::= {sispm10403166lMacBaesdVlanMembershipConfigEntry 3 }

sispm10403166lMacBaesdVlanMembershipConfigPortMembers OBJECT-TYPE
   SYNTAX      DisplayString
   MAX-ACCESS  read-create
   STATUS      current
   DESCRIPTION
       "0:remove or exclude the port from the mapping
        1:include a port in the mapping"
   ::= {sispm10403166lMacBaesdVlanMembershipConfigEntry 4 }

sispm10403166lMacBaesdVlanMembershipConfigRowStatus OBJECT-TYPE
   SYNTAX      RowStatus
   MAX-ACCESS  read-create
   STATUS      current
   DESCRIPTION
       "Row Status."
   ::= {sispm10403166lMacBaesdVlanMembershipConfigEntry 5 }

sispm10403166lMacBaesdVlanMembershipStatusUser   OBJECT-TYPE
       SYNTAX      Integer32
       MAX-ACCESS  read-write
       STATUS      current
       DESCRIPTION
           "MAC-based VLAN Membership Status User"
       ::= { sispm10403166lVLAN 8 }

sispm10403166lMacBaesdVlanMembershipStatus     OBJECT IDENTIFIER   ::= { sispm10403166lVLAN 9 }

sispm10403166lMacBaesdVlanMembershipStatusTable  OBJECT-TYPE
   SYNTAX      SEQUENCE OF SISPM10403166LMacBaesdVlanMembershipStatusEntry
   MAX-ACCESS  not-accessible
   STATUS      current
   DESCRIPTION
       "Mac-Based VLAN Membership table"
 ::= { sispm10403166lMacBaesdVlanMembershipStatus 1 }

sispm10403166lMacBaesdVlanMembershipStatusEntry OBJECT-TYPE
    SYNTAX        SISPM10403166LMacBaesdVlanMembershipStatusEntry
    MAX-ACCESS    not-accessible
    STATUS        current
    DESCRIPTION
        "Mac-Based VLAN Membership table."
    INDEX        { sispm10403166lMacBaesdVlanMembershipStatusIndex }
    ::= { sispm10403166lMacBaesdVlanMembershipStatusTable 1 }

SISPM10403166LMacBaesdVlanMembershipStatusEntry ::=
    SEQUENCE {
        sispm10403166lMacBaesdVlanMembershipStatusIndex        Integer32,
        sispm10403166lMacBaesdVlanMembershipStatusMACAddress   DisplayString,
        sispm10403166lMacBaesdVlanMembershipStatusVLANID       Integer32,
        sispm10403166lMacBaesdVlanMembershipStatusPortMembers  DisplayString
    }

sispm10403166lMacBaesdVlanMembershipStatusIndex OBJECT-TYPE
   SYNTAX      Integer32(1..65535)
   MAX-ACCESS  not-accessible
   STATUS      current
   DESCRIPTION
       "Mac-Based VLAN membership index."
   ::= {sispm10403166lMacBaesdVlanMembershipStatusEntry 1 }

sispm10403166lMacBaesdVlanMembershipStatusMACAddress OBJECT-TYPE
   SYNTAX      DisplayString
   MAX-ACCESS  read-only
   STATUS      current
   DESCRIPTION
       "MAC address: xx-xx-xx-xx-xx-xx."
   ::= {sispm10403166lMacBaesdVlanMembershipStatusEntry 2 }

sispm10403166lMacBaesdVlanMembershipStatusVLANID OBJECT-TYPE
   SYNTAX      Integer32
   MAX-ACCESS  read-only
   STATUS      current
   DESCRIPTION
       "VLAN ID"
   ::= {sispm10403166lMacBaesdVlanMembershipStatusEntry 3 }

sispm10403166lMacBaesdVlanMembershipStatusPortMembers OBJECT-TYPE
   SYNTAX      DisplayString
   MAX-ACCESS  read-only
   STATUS      current
   DESCRIPTION
       "0:remove or exclude the port from the mapping
        1:include a port in the mapping"
   ::= {sispm10403166lMacBaesdVlanMembershipStatusEntry 4 }

sispm10403166lProtocolbasedVLANConfig     OBJECT IDENTIFIER   ::= { sispm10403166lVLAN 10 }

sispm10403166lProtocolbasedVLANConfigTable  OBJECT-TYPE
   SYNTAX      SEQUENCE OF SISPM10403166LProtocolbasedVLANConfigEntry
   MAX-ACCESS  not-accessible
   STATUS      current
   DESCRIPTION
       "Protocol-based VLAN Config table"
 ::= { sispm10403166lProtocolbasedVLANConfig 1 }

sispm10403166lProtocolbasedVLANConfigEntry OBJECT-TYPE
    SYNTAX        SISPM10403166LProtocolbasedVLANConfigEntry
    MAX-ACCESS    not-accessible
    STATUS        current
    DESCRIPTION
        "Protocol-based VLAN Config table"
    INDEX        { sispm10403166lProtocolbasedVLANConfigIndex }
    ::= { sispm10403166lProtocolbasedVLANConfigTable 1 }

SISPM10403166LProtocolbasedVLANConfigEntry ::=
    SEQUENCE {
        sispm10403166lProtocolbasedVLANConfigIndex               Integer32,
        sispm10403166lProtocolbasedVLANConfigFrameType           Integer32,
        sispm10403166lProtocolbasedVLANConfigValueEthernetEtype  DisplayString,
        sispm10403166lProtocolbasedVLANConfigValueSNAPOUI        DisplayString,
        sispm10403166lProtocolbasedVLANConfigValueSNAPPID        DisplayString,
        sispm10403166lProtocolbasedVLANConfigValueLLCDSAP        DisplayString,
        sispm10403166lProtocolbasedVLANConfigValueLLCSSAP        DisplayString,
        sispm10403166lProtocolbasedVLANConfigGroupName           DisplayString,
        sispm10403166lProtocolbasedVLANConfigRowStatus           RowStatus
    }

sispm10403166lProtocolbasedVLANConfigIndex OBJECT-TYPE
   SYNTAX      Integer32(1..65535)
   MAX-ACCESS  not-accessible
   STATUS      current
   DESCRIPTION
       "Protocol-based VLAN Config index."
   ::= {sispm10403166lProtocolbasedVLANConfigEntry 1 }

sispm10403166lProtocolbasedVLANConfigFrameType OBJECT-TYPE
   SYNTAX      Integer32
   MAX-ACCESS  read-create
   STATUS      current
   DESCRIPTION
       "Frame Type.
       1:Ethernet
       2:LLC
       3:SNAP"
   ::= {sispm10403166lProtocolbasedVLANConfigEntry 2 }


sispm10403166lProtocolbasedVLANConfigValueEthernetEtype OBJECT-TYPE
   SYNTAX      DisplayString
   MAX-ACCESS  read-create
   STATUS      current
   DESCRIPTION
       "Ethernet Etype.
       Valid values for etype range between 0x0600 and 0xffff "
   ::= {sispm10403166lProtocolbasedVLANConfigEntry 3 }

sispm10403166lProtocolbasedVLANConfigValueSNAPOUI OBJECT-TYPE
   SYNTAX      DisplayString
   MAX-ACCESS  read-create
   STATUS      current
   DESCRIPTION
       "SNAP OUI.
       Format:xx-xx-xx"
   ::= {sispm10403166lProtocolbasedVLANConfigEntry 4 }

sispm10403166lProtocolbasedVLANConfigValueSNAPPID OBJECT-TYPE
   SYNTAX      DisplayString
   MAX-ACCESS  read-create
   STATUS      current
   DESCRIPTION
       "SNAP PID
       Ranging between 0x00 and 0xff."
   ::= {sispm10403166lProtocolbasedVLANConfigEntry 5 }

sispm10403166lProtocolbasedVLANConfigValueLLCDSAP OBJECT-TYPE
   SYNTAX      DisplayString
   MAX-ACCESS  read-create
   STATUS      current
   DESCRIPTION
       "LLC DSAP.
       Range: 0x00-0xff"
   ::= {sispm10403166lProtocolbasedVLANConfigEntry 6 }

sispm10403166lProtocolbasedVLANConfigValueLLCSSAP OBJECT-TYPE
   SYNTAX      DisplayString
   MAX-ACCESS  read-create
   STATUS      current
   DESCRIPTION
       "LLC SSAP.
       Range: 0x00-0xff"
   ::= {sispm10403166lProtocolbasedVLANConfigEntry 7 }

sispm10403166lProtocolbasedVLANConfigGroupName OBJECT-TYPE
   SYNTAX      DisplayString
   MAX-ACCESS  read-create
   STATUS      current
   DESCRIPTION
       "Group Name
        16-character long string, unique for every entry, which consists of a combination of alphabets (a-z or A-Z) and integers(0-9)."
   ::= {sispm10403166lProtocolbasedVLANConfigEntry 8 }

sispm10403166lProtocolbasedVLANConfigRowStatus OBJECT-TYPE
   SYNTAX      RowStatus
   MAX-ACCESS  read-create
   STATUS      current
   DESCRIPTION
       "Row Status."
   ::= {sispm10403166lProtocolbasedVLANConfigEntry 9 }



sispm10403166lGroupNameToVLANMappingConfigTable  OBJECT-TYPE
   SYNTAX      SEQUENCE OF SISPM10403166LGroupNameToVLANMappingConfigEntry
   MAX-ACCESS  not-accessible
   STATUS      current
   DESCRIPTION
       "Group Name To VLAN Mapping Config table"
 ::= { sispm10403166lProtocolbasedVLANConfig 2 }

sispm10403166lGroupNameToVLANMappingConfigEntry OBJECT-TYPE
    SYNTAX        SISPM10403166LGroupNameToVLANMappingConfigEntry
    MAX-ACCESS    not-accessible
    STATUS        current
    DESCRIPTION
        "Group Name To VLAN Mapping Config table."
    INDEX        { sispm10403166lGroupNameToVLANMappingConfigIndex }
    ::= { sispm10403166lGroupNameToVLANMappingConfigTable 1 }

SISPM10403166LGroupNameToVLANMappingConfigEntry ::=
    SEQUENCE {
        sispm10403166lGroupNameToVLANMappingConfigIndex        Integer32,
        sispm10403166lGroupNameToVLANMappingConfigGroupName    DisplayString,
        sispm10403166lGroupNameToVLANMappingConfigVLANID       Integer32,
        sispm10403166lGroupNameToVLANMappingConfigPortMembers  DisplayString,
        sispm10403166lGroupNameToVLANMappingConfigRowStatus    RowStatus
    }

sispm10403166lGroupNameToVLANMappingConfigIndex OBJECT-TYPE
   SYNTAX      Integer32(1..65535)
   MAX-ACCESS  not-accessible
   STATUS      current
   DESCRIPTION
       "Group Name To VLAN Mapping Config index."
   ::= {sispm10403166lGroupNameToVLANMappingConfigEntry 1 }

sispm10403166lGroupNameToVLANMappingConfigGroupName OBJECT-TYPE
   SYNTAX      DisplayString
   MAX-ACCESS  read-create
   STATUS      current
   DESCRIPTION
       "Group Name
        16-character long string, unique for every entry, which consists of a combination of alphabets (a-z or A-Z) and integers(0-9)."
   ::= {sispm10403166lGroupNameToVLANMappingConfigEntry 2 }

sispm10403166lGroupNameToVLANMappingConfigVLANID OBJECT-TYPE
   SYNTAX      Integer32
   MAX-ACCESS  read-create
   STATUS      current
   DESCRIPTION
       "VLAN ID"
   ::= {sispm10403166lGroupNameToVLANMappingConfigEntry 3 }

sispm10403166lGroupNameToVLANMappingConfigPortMembers OBJECT-TYPE
   SYNTAX      DisplayString
   MAX-ACCESS  read-create
   STATUS      current
   DESCRIPTION
       "0:remove or exclude the port from the mapping
        1:include a port in the mapping"
   ::= {sispm10403166lGroupNameToVLANMappingConfigEntry 4 }

sispm10403166lGroupNameToVLANMappingConfigRowStatus OBJECT-TYPE
   SYNTAX      RowStatus
   MAX-ACCESS  read-create
   STATUS      current
   DESCRIPTION
       "Row Status."
   ::= {sispm10403166lGroupNameToVLANMappingConfigEntry 5 }

sispm10403166lIPSubnetBasedVLANConfig     OBJECT IDENTIFIER   ::= { sispm10403166lVLAN 11 }

sispm10403166lIPSubnetBasedVLANConfigTable  OBJECT-TYPE
   SYNTAX      SEQUENCE OF SISPM10403166LIPSubnetBasedVLANConfigEntry
   MAX-ACCESS  not-accessible
   STATUS      current
   DESCRIPTION
       "IP Subnet Based VLAN Config table"
 ::= { sispm10403166lIPSubnetBasedVLANConfig 1 }

sispm10403166lIPSubnetBasedVLANConfigEntry OBJECT-TYPE
    SYNTAX        SISPM10403166LIPSubnetBasedVLANConfigEntry
    MAX-ACCESS    not-accessible
    STATUS        current
    DESCRIPTION
        "IP Subnet Based VLAN Config table."
    INDEX        { sispm10403166lIPSubnetBasedVLANConfigIndex }
    ::= { sispm10403166lIPSubnetBasedVLANConfigTable 1 }

SISPM10403166LIPSubnetBasedVLANConfigEntry ::=
    SEQUENCE {
        sispm10403166lIPSubnetBasedVLANConfigIndex        Integer32,
        sispm10403166lIPSubnetBasedVLANConfigIPAddress    IpAddress,
        sispm10403166lIPSubnetBasedVLANConfigMaskLength   Integer32,
        sispm10403166lIPSubnetBasedVLANConfigVLANID       Integer32,
        sispm10403166lIPSubnetBasedVLANConfigPortMembers  DisplayString,
        sispm10403166lIPSubnetBasedVLANConfigRowStatus    RowStatus
    }

sispm10403166lIPSubnetBasedVLANConfigIndex OBJECT-TYPE
   SYNTAX      Integer32(1..65535)
   MAX-ACCESS  not-accessible
   STATUS      current
   DESCRIPTION
       "IP Subnet Based VLAN Config index."
   ::= {sispm10403166lIPSubnetBasedVLANConfigEntry 1 }

sispm10403166lIPSubnetBasedVLANConfigIPAddress OBJECT-TYPE
   SYNTAX      IpAddress
   MAX-ACCESS  read-create
   STATUS      current
   DESCRIPTION
       "The subnet's IP address"
   ::= {sispm10403166lIPSubnetBasedVLANConfigEntry 2 }

sispm10403166lIPSubnetBasedVLANConfigMaskLength OBJECT-TYPE
   SYNTAX      Integer32
   MAX-ACCESS  read-create
   STATUS      current
   DESCRIPTION
       "The subnet's mask length. "
   ::= {sispm10403166lIPSubnetBasedVLANConfigEntry 3 }

sispm10403166lIPSubnetBasedVLANConfigVLANID OBJECT-TYPE
   SYNTAX      Integer32
   MAX-ACCESS  read-create
   STATUS      current
   DESCRIPTION
       "VLAN ID"
   ::= {sispm10403166lIPSubnetBasedVLANConfigEntry 4 }

sispm10403166lIPSubnetBasedVLANConfigPortMembers OBJECT-TYPE
   SYNTAX      DisplayString
   MAX-ACCESS  read-create
   STATUS      current
   DESCRIPTION
       "0:remove or exclude the port from the mapping
        1:include a port in the mapping"
   ::= {sispm10403166lIPSubnetBasedVLANConfigEntry 5 }

sispm10403166lIPSubnetBasedVLANConfigRowStatus OBJECT-TYPE
   SYNTAX      RowStatus
   MAX-ACCESS  read-create
   STATUS      current
   DESCRIPTION
       "Row Status."
   ::= {sispm10403166lIPSubnetBasedVLANConfigEntry 6 }

sispm10403166lVLANNameConfig     OBJECT IDENTIFIER   ::= { sispm10403166lVLAN 12 }

sispm10403166lVLANNameConfigTable  OBJECT-TYPE
   SYNTAX      SEQUENCE OF SISPM10403166LVLANNameConfigEntry
   MAX-ACCESS  not-accessible
   STATUS      current
   DESCRIPTION
       "VLAN Name Config table"
 ::= { sispm10403166lVLANNameConfig 1 }

sispm10403166lVLANNameConfigEntry OBJECT-TYPE
    SYNTAX        SISPM10403166LVLANNameConfigEntry
    MAX-ACCESS    not-accessible
    STATUS        current
    DESCRIPTION
        "VLAN Name Config table."
    INDEX        { sispm10403166lVLANNameConfigIndex }
    ::= { sispm10403166lVLANNameConfigTable 1 }

SISPM10403166LVLANNameConfigEntry ::=
    SEQUENCE {
        sispm10403166lVLANNameConfigIndex        Integer32,
        sispm10403166lVLANNameConfigVLANName     DisplayString
    }

sispm10403166lVLANNameConfigIndex OBJECT-TYPE
   SYNTAX      Integer32(1..65535)
   MAX-ACCESS  not-accessible
   STATUS      current
   DESCRIPTION
       "VLAN Name Config index."
   ::= {sispm10403166lVLANNameConfigEntry 1 }

sispm10403166lVLANNameConfigVLANName OBJECT-TYPE
   SYNTAX      DisplayString
   MAX-ACCESS  read-write
   STATUS      current
   DESCRIPTION
       "VLAN Name."
   ::= {sispm10403166lVLANNameConfigEntry 2 }


sispm10403166lSystemDIDO                                     OBJECT IDENTIFIER ::= { sispm10403166lSystem 11 }
    sispm10403166lSystemDIMode OBJECT-TYPE
               SYNTAX       Integer32 (0..1)
               MAX-ACCESS   read-write
               STATUS       current
               DESCRIPTION
                   "System digital in mode.
				   0:Low
				   1:High
				   "
               ::= {     sispm10403166lSystemDIDO 1 }

    sispm10403166lSystemDOMode OBJECT-TYPE
               SYNTAX       Integer32 (0..1)
               MAX-ACCESS   read-write
               STATUS       current
               DESCRIPTION
                   "System digital out mode.
				   0:Close
				   1:Open
				   "
               ::= {     sispm10403166lSystemDIDO 2 }

	sispm10403166lSystemDIEventDescNormal   OBJECT-TYPE
			   SYNTAX      DisplayString
			   MAX-ACCESS  read-write
			   STATUS      current
			   DESCRIPTION
				   "Customize event message. You can describe the event in detail. "
			   ::= {     sispm10403166lSystemDIDO 3 }

	sispm10403166lSystemDIEventDescAbnormal   OBJECT-TYPE
			   SYNTAX      DisplayString
			   MAX-ACCESS  read-write
			   STATUS      current
			   DESCRIPTION
				   "Customize event message. You can describe the event in detail. "
			   ::= {     sispm10403166lSystemDIDO 4 }

	sispm10403166lSystemDOAutoRecovery OBJECT-TYPE
			   SYNTAX       Integer32 (0..1)
			   MAX-ACCESS   read-write
			   STATUS       current
			   DESCRIPTION
				   "Enable the function of Auto Recovery.
				   0:Disable
				   1:Enable
				   "
			   ::= {    sispm10403166lSystemDIDO 5 }

    sispm10403166lSystemDIRebootSystem OBJECT-TYPE
               SYNTAX       Integer32 (0..1)
               MAX-ACCESS   read-write
               STATUS       current
               DESCRIPTION
                   "Enable the function of DI Reboot System.
				   0:Disable
				   1:When DI was changed to abnormal.
				   "
               ::= {     sispm10403166lSystemDIDO 6 }

sispm10403166lNTPConf   OBJECT IDENTIFIER ::= { sispm10403166lSystem 12 }

sispm10403166lNTPConfigMode OBJECT-TYPE
           SYNTAX       INTEGER {useLocal(0),useNTP(1)}
           MAX-ACCESS   read-write
           STATUS       current
           DESCRIPTION
               "The system NTP Mode.
                useLocal(0) : Use Local Settings,
                useNTP(1)   : Use NTP Server."
           DEFVAL  { useLocal }
           ::= {     sispm10403166lNTPConf 1 }

--sispm10403166lNTPConfigAutomatic   OBJECT-TYPE
--               SYNTAX      Integer32 (0|1)
--               MAX-ACCESS  read-write
--               STATUS      current
--               DESCRIPTION
--                   "Indicates the Automatic mode operation. Possible modes are:
--                   0:Disable, NTP servers available from the config.
--                   1:Enable, NTP servers available from the DHCP."
--               ::= { sispm10403166lNTPConf 2 }

sispm10403166lNTPConfigTimeSyncInterval   OBJECT-TYPE
               SYNTAX      Integer32 (5|10|15|30|60|120)
               MAX-ACCESS  read-write
               STATUS      current
               DESCRIPTION
                   "Time-Sync Interval.
                   Valid values are restricted to 5,10,15,30,60,120 minutes. "
               ::= { sispm10403166lNTPConf 3 }

sispm10403166lNTPConfigServerAddress1   OBJECT-TYPE
               SYNTAX      DisplayString
               MAX-ACCESS  read-write
               STATUS      current
               DESCRIPTION
                   "Provide the IPv4 or IPv6 address of a NTP server."
               ::= { sispm10403166lNTPConf 4 }

sispm10403166lNTPConfigServerAddress2   OBJECT-TYPE
               SYNTAX      DisplayString
               MAX-ACCESS  read-write
               STATUS      current
               DESCRIPTION
                   "Provide the IPv4 or IPv6 address of a NTP server."
               ::= { sispm10403166lNTPConf 5 }

sispm10403166lNTPConfigServerAddress3   OBJECT-TYPE
               SYNTAX      DisplayString
               MAX-ACCESS  read-write
               STATUS      current
               DESCRIPTION
                   "Provide the IPv4 or IPv6 address of a NTP server."
               ::= { sispm10403166lNTPConf 6 }

sispm10403166lNTPConfigServerAddress4   OBJECT-TYPE
               SYNTAX      DisplayString
               MAX-ACCESS  read-write
               STATUS      current
               DESCRIPTION
                   "Provide the IPv4 or IPv6 address of a NTP server."
               ::= { sispm10403166lNTPConf 7 }

sispm10403166lNTPConfigServerAddress5   OBJECT-TYPE
               SYNTAX      DisplayString
               MAX-ACCESS  read-write
               STATUS      current
               DESCRIPTION
                   "Provide the IPv4 or IPv6 address of a NTP server."
               ::= { sispm10403166lNTPConf 8 }


sispm10403166lTemperature   OBJECT IDENTIFIER ::= { sispm10403166lSystem 13 }

sispm10403166lTemperature1   OBJECT IDENTIFIER ::= { sispm10403166lTemperature 1 }

sispm10403166lTemperature1Celsius   OBJECT-TYPE
               SYNTAX      DisplayString
               MAX-ACCESS  read-only
               STATUS      current
               DESCRIPTION
                   "Value of Celsius"
               ::= { sispm10403166lTemperature1 1 }

sispm10403166lTemperature1Fahrenheit   OBJECT-TYPE
               SYNTAX      DisplayString
               MAX-ACCESS  read-only
               STATUS      current
               DESCRIPTION
                   "Value of Fahrenheit"
               ::= { sispm10403166lTemperature1 2 }

sispm10403166lTemperature2   OBJECT IDENTIFIER ::= { sispm10403166lTemperature 2 }

sispm10403166lTemperature2Celsius   OBJECT-TYPE
               SYNTAX      DisplayString
               MAX-ACCESS  read-only
               STATUS      current
               DESCRIPTION
                   "Value of Celsius"
               ::= { sispm10403166lTemperature2 1 }

sispm10403166lTemperature2Fahrenheit   OBJECT-TYPE
               SYNTAX      DisplayString
               MAX-ACCESS  read-only
               STATUS      current
               DESCRIPTION
                   "Value of Fahrenheit"
               ::= { sispm10403166lTemperature2 2 }

-- =======================================================================================================================
sispm10403166lConfiguration                                         OBJECT IDENTIFIER ::= { sispm10403166lProductId 2 }

sispm10403166lPort                                                  OBJECT IDENTIFIER ::= { sispm10403166lConfiguration 1 }

sispm10403166lPortConfigurationTable OBJECT-TYPE
   SYNTAX      SEQUENCE OF SISPM10403166LPortConfigurationEntry
   MAX-ACCESS  not-accessible
   STATUS      current
   DESCRIPTION
       " Show port configurations. "
   ::= { sispm10403166lPort 1 }

sispm10403166lPortConfigurationEntry OBJECT-TYPE
   SYNTAX      SISPM10403166LPortConfigurationEntry
   MAX-ACCESS  not-accessible
   STATUS      current
   DESCRIPTION
       " "
   INDEX    { sispm10403166lPortConfPort  }
   ::= { sispm10403166lPortConfigurationTable 1 }

SISPM10403166LPortConfigurationEntry ::= SEQUENCE {
   sispm10403166lPortConfPort                     Integer32,
   sispm10403166lPortConfDescription              DisplayString,
   sispm10403166lPortConfLink                     DisplayString,
   sispm10403166lPortConfSpeedStatus              DisplayString,
   sispm10403166lPortConfSpeedMode                Integer32,
   sispm10403166lPortConfFlowControlRxStatus      Integer32,
   sispm10403166lPortConfFlowControlTxStatus      Integer32,
   sispm10403166lPortConfFlowControlMode          Integer32,
   sispm10403166lPortConfMaximumFrameSize         Integer32
-- sispm10403166lPortConfExcessiveCollisionMode   Integer32,
-- sispm10403166lPortConfPowerControl             Integer32,
-- sispm10403166lPortConfPortMedia                DisplayString
}

sispm10403166lPortConfPort OBJECT-TYPE
   SYNTAX      Integer32 (1..4095)
   MAX-ACCESS  not-accessible
   STATUS      current
   DESCRIPTION
       " port, range : 1 - port number. "
   ::= { sispm10403166lPortConfigurationEntry 1 }

sispm10403166lPortConfDescription OBJECT-TYPE
   SYNTAX      DisplayString
   MAX-ACCESS  read-write
   STATUS      current
   DESCRIPTION
       " Interface specific description.
         Up to 16 characters describing this interface. "
   ::= { sispm10403166lPortConfigurationEntry 2 }

sispm10403166lPortConfLink OBJECT-TYPE
   SYNTAX      DisplayString(SIZE (2..4))
   MAX-ACCESS  read-only
   STATUS      current
   DESCRIPTION
       " The current link state. "
   ::= { sispm10403166lPortConfigurationEntry 3 }

sispm10403166lPortConfSpeedStatus OBJECT-TYPE
   SYNTAX      DisplayString(SIZE (6..12))
   MAX-ACCESS  read-only
   STATUS      current
   DESCRIPTION
       " The current link speed of the port. "
   ::= { sispm10403166lPortConfigurationEntry 4 }

sispm10403166lPortConfSpeedMode OBJECT-TYPE
   SYNTAX      Integer32 (0..9)
   MAX-ACCESS  read-write
   STATUS      current
   DESCRIPTION
       "default: 1,
        0: disable state,
        1: auto,
        2: 10 Half,
        3: 10 Full,
        4: 100 Half,
        5: 100 Full,
        6: 1G full,
        7: 10G Full,
        8: 100-FX,
        9: 1000-X. "
   ::= { sispm10403166lPortConfigurationEntry 5 }

sispm10403166lPortConfFlowControlRxStatus OBJECT-TYPE
   SYNTAX      Integer32 (0|1)
   MAX-ACCESS  read-only
   STATUS      current
   DESCRIPTION
       "0: disable
        1: enable
        2: not support.  "
   ::= { sispm10403166lPortConfigurationEntry 6 }

sispm10403166lPortConfFlowControlTxStatus OBJECT-TYPE
   SYNTAX      Integer32 (0|1)
   MAX-ACCESS  read-only
   STATUS      current
   DESCRIPTION
       "0: disable
        1: enable
        2: not support.  "
   ::= { sispm10403166lPortConfigurationEntry 7 }

sispm10403166lPortConfFlowControlMode OBJECT-TYPE
   SYNTAX      Integer32 (0|1)
   MAX-ACCESS  read-write
   STATUS      current
   DESCRIPTION
       "default: 0,
        0: disable
        1: enable
        2: not support. "
   ::= { sispm10403166lPortConfigurationEntry 8 }

sispm10403166lPortConfMaximumFrameSize OBJECT-TYPE
   SYNTAX      Integer32 (1518..10240)
   MAX-ACCESS  read-write
   STATUS      current
   DESCRIPTION
       "default: 10240 , range : 1518 - 10240 "
   ::= { sispm10403166lPortConfigurationEntry 9 }

--sispm10403166lPortConfExcessiveCollisionMode OBJECT-TYPE
--   SYNTAX      Integer32 (0|1)
--   MAX-ACCESS  read-write
--   STATUS      current
--   DESCRIPTION
--       "default: 0,
--        Excessive Collision Mode :
--        0: Discard,
--        1: Restart,
--        2: not support.
--       "
--   ::= { sispm10403166lPortConfigurationEntry 10 }

--sispm10403166lPortConfPowerControl OBJECT-TYPE
--   SYNTAX      Integer32 (0..3)
--   MAX-ACCESS  read-write
--   STATUS      current
--   DESCRIPTION
--       "default: 0,
--        PowerControl :
--        0: disable,
--        1: Actiphy,
--        2: Dynamic (perfectReach),
--        3: Enable,
--        4: not support.
--       "
--   ::= { sispm10403166lPortConfigurationEntry 11 }

--sispm10403166lPortConfPortMedia OBJECT-TYPE
--   SYNTAX      DisplayString(SIZE (1..4))
--   MAX-ACCESS  read-only
--   STATUS      current
--   DESCRIPTION
--       " Show port media. "
--   ::= { sispm10403166lPortConfigurationEntry 12 }


sispm10403166lPortTrafficStatisticsTable OBJECT-TYPE
   SYNTAX      SEQUENCE OF SISPM10403166LPortTrafficStatisticsEntry
   MAX-ACCESS  not-accessible
   STATUS      current
   DESCRIPTION
       " "
   ::= { sispm10403166lPort 2 }

sispm10403166lPortTrafficStatisticsEntry OBJECT-TYPE
   SYNTAX      SISPM10403166LPortTrafficStatisticsEntry
   MAX-ACCESS  not-accessible
   STATUS      current
   DESCRIPTION
       " "
   INDEX    { sispm10403166lPortTrafficStatisticsPort  }
   ::= { sispm10403166lPortTrafficStatisticsTable 1 }

SISPM10403166LPortTrafficStatisticsEntry ::= SEQUENCE {
   sispm10403166lPortTrafficStatisticsPort          Integer32,
   sispm10403166lPortTrafficStatisticsClear         Integer32,
   sispm10403166lPortTrafficRxPackets               Counter64,
   sispm10403166lPortTrafficRxOctets                Counter64,
   sispm10403166lPortTrafficRxUnicast               Counter64,
   sispm10403166lPortTrafficRxMulticast             Counter64,
   sispm10403166lPortTrafficRxBroadcast             Counter64,
   sispm10403166lPortTrafficRxPause                 Counter64,
   sispm10403166lPortTrafficRx64Bytes               Counter64,
   sispm10403166lPortTrafficRx65to127Bytes          Counter64,
   sispm10403166lPortTrafficRx128to255Bytes         Counter64,
   sispm10403166lPortTrafficRx256to511Bytes         Counter64,
   sispm10403166lPortTrafficRx512to1023Bytes        Counter64,
   sispm10403166lPortTrafficRx1024to1526Bytes       Counter64,
   sispm10403166lPortTrafficRxExceecd1527Bytes      Counter64,
   sispm10403166lPortTrafficRxQ0                    Counter64,
   sispm10403166lPortTrafficRxQ1                    Counter64,
   sispm10403166lPortTrafficRxQ2                    Counter64,
   sispm10403166lPortTrafficRxQ3                    Counter64,
   sispm10403166lPortTrafficRxQ4                    Counter64,
   sispm10403166lPortTrafficRxQ5                    Counter64,
   sispm10403166lPortTrafficRxQ6                    Counter64,
   sispm10403166lPortTrafficRxQ7                    Counter64,
   sispm10403166lPortTrafficRxDrops                 Counter64,
   sispm10403166lPortTrafficRxCRCorAlignment        Counter64,
   sispm10403166lPortTrafficRxUndersize             Counter64,
   sispm10403166lPortTrafficRxOversize              Counter64,
   sispm10403166lPortTrafficRxFragments             Counter64,
   sispm10403166lPortTrafficRxJabber                Counter64,
   sispm10403166lPortTrafficRxFiltered              Counter64,
   sispm10403166lPortTrafficTxPackets               Counter64,
   sispm10403166lPortTrafficTxOctets                Counter64,
   sispm10403166lPortTrafficTxUnicast               Counter64,
   sispm10403166lPortTrafficTxMulticast             Counter64,
   sispm10403166lPortTrafficTxBroadcast             Counter64,
   sispm10403166lPortTrafficTxPause                 Counter64,
   sispm10403166lPortTrafficTx64Bytes               Counter64,
   sispm10403166lPortTrafficTx65to127Bytes          Counter64,
   sispm10403166lPortTrafficTx128to255Bytes         Counter64,
   sispm10403166lPortTrafficTx256to511Bytes         Counter64,
   sispm10403166lPortTrafficTx512to1023Bytes        Counter64,
   sispm10403166lPortTrafficTx1024to1526Bytes       Counter64,
   sispm10403166lPortTrafficTxExceecd1527Bytes      Counter64,
   sispm10403166lPortTrafficTxQ0                    Counter64,
   sispm10403166lPortTrafficTxQ1                    Counter64,
   sispm10403166lPortTrafficTxQ2                    Counter64,
   sispm10403166lPortTrafficTxQ3                    Counter64,
   sispm10403166lPortTrafficTxQ4                    Counter64,
   sispm10403166lPortTrafficTxQ5                    Counter64,
   sispm10403166lPortTrafficTxQ6                    Counter64,
   sispm10403166lPortTrafficTxQ7                    Counter64,
   sispm10403166lPortTrafficTxDrops                 Counter64,
   sispm10403166lPortTrafficTxLateOrExcColl         Counter64
}

sispm10403166lPortTrafficStatisticsPort OBJECT-TYPE
   SYNTAX      Integer32 (1..4095)
   MAX-ACCESS  not-accessible
   STATUS      current
   DESCRIPTION
       " "
   ::= { sispm10403166lPortTrafficStatisticsEntry 1 }

sispm10403166lPortTrafficStatisticsClear OBJECT-TYPE
   SYNTAX      Integer32(0|1)
   MAX-ACCESS  read-write
   STATUS      current
   DESCRIPTION
       " "
   ::= { sispm10403166lPortTrafficStatisticsEntry 2 }

sispm10403166lPortTrafficRxPackets OBJECT-TYPE
   SYNTAX      Counter64
   MAX-ACCESS  read-only
   STATUS      current
   DESCRIPTION
       " "
   ::= { sispm10403166lPortTrafficStatisticsEntry 3 }

sispm10403166lPortTrafficRxOctets OBJECT-TYPE
   SYNTAX      Counter64
   MAX-ACCESS  read-only
   STATUS      current
   DESCRIPTION
       " "
   ::= { sispm10403166lPortTrafficStatisticsEntry 4 }

sispm10403166lPortTrafficRxUnicast OBJECT-TYPE
   SYNTAX      Counter64
   MAX-ACCESS  read-only
   STATUS      current
   DESCRIPTION
       " "
   ::= { sispm10403166lPortTrafficStatisticsEntry 5 }

sispm10403166lPortTrafficRxMulticast OBJECT-TYPE
   SYNTAX      Counter64
   MAX-ACCESS  read-only
   STATUS      current
   DESCRIPTION
       " "
   ::= { sispm10403166lPortTrafficStatisticsEntry 6 }

sispm10403166lPortTrafficRxBroadcast OBJECT-TYPE
   SYNTAX      Counter64
   MAX-ACCESS  read-only
   STATUS      current
   DESCRIPTION
       " "
   ::= { sispm10403166lPortTrafficStatisticsEntry 7 }

sispm10403166lPortTrafficRxPause OBJECT-TYPE
   SYNTAX      Counter64
   MAX-ACCESS  read-only
   STATUS      current
   DESCRIPTION
       " "
   ::= { sispm10403166lPortTrafficStatisticsEntry 8 }

sispm10403166lPortTrafficRx64Bytes OBJECT-TYPE
   SYNTAX      Counter64
   MAX-ACCESS  read-only
   STATUS      current
   DESCRIPTION
       " "
   ::= { sispm10403166lPortTrafficStatisticsEntry 9 }

sispm10403166lPortTrafficRx65to127Bytes OBJECT-TYPE
   SYNTAX      Counter64
   MAX-ACCESS  read-only
   STATUS      current
   DESCRIPTION
       " "
   ::= { sispm10403166lPortTrafficStatisticsEntry 10 }

sispm10403166lPortTrafficRx128to255Bytes OBJECT-TYPE
   SYNTAX      Counter64
   MAX-ACCESS  read-only
   STATUS      current
   DESCRIPTION
       " "
   ::= { sispm10403166lPortTrafficStatisticsEntry 11 }

sispm10403166lPortTrafficRx256to511Bytes OBJECT-TYPE
   SYNTAX      Counter64
   MAX-ACCESS  read-only
   STATUS      current
   DESCRIPTION
       " "
   ::= { sispm10403166lPortTrafficStatisticsEntry 12 }

sispm10403166lPortTrafficRx512to1023Bytes OBJECT-TYPE
   SYNTAX      Counter64
   MAX-ACCESS  read-only
   STATUS      current
   DESCRIPTION
       " "
   ::= { sispm10403166lPortTrafficStatisticsEntry 13 }

sispm10403166lPortTrafficRx1024to1526Bytes OBJECT-TYPE
   SYNTAX      Counter64
   MAX-ACCESS  read-only
   STATUS      current
   DESCRIPTION
       " "
   ::= { sispm10403166lPortTrafficStatisticsEntry 14 }

sispm10403166lPortTrafficRxExceecd1527Bytes OBJECT-TYPE
   SYNTAX      Counter64
   MAX-ACCESS  read-only
   STATUS      current
   DESCRIPTION
       " "
   ::= { sispm10403166lPortTrafficStatisticsEntry 15 }

sispm10403166lPortTrafficRxQ0 OBJECT-TYPE
   SYNTAX      Counter64
   MAX-ACCESS  read-only
   STATUS      current
   DESCRIPTION
       " "
   ::= { sispm10403166lPortTrafficStatisticsEntry 16 }

sispm10403166lPortTrafficRxQ1 OBJECT-TYPE
   SYNTAX      Counter64
   MAX-ACCESS  read-only
   STATUS      current
   DESCRIPTION
       " "
   ::= { sispm10403166lPortTrafficStatisticsEntry 17 }

sispm10403166lPortTrafficRxQ2 OBJECT-TYPE
   SYNTAX      Counter64
   MAX-ACCESS  read-only
   STATUS      current
   DESCRIPTION
       " "
   ::= { sispm10403166lPortTrafficStatisticsEntry 18 }

sispm10403166lPortTrafficRxQ3 OBJECT-TYPE
   SYNTAX      Counter64
   MAX-ACCESS  read-only
   STATUS      current
   DESCRIPTION
       " "
   ::= { sispm10403166lPortTrafficStatisticsEntry 19 }

sispm10403166lPortTrafficRxQ4 OBJECT-TYPE
   SYNTAX      Counter64
   MAX-ACCESS  read-only
   STATUS      current
   DESCRIPTION
       " "
   ::= { sispm10403166lPortTrafficStatisticsEntry 20 }

sispm10403166lPortTrafficRxQ5 OBJECT-TYPE
   SYNTAX      Counter64
   MAX-ACCESS  read-only
   STATUS      current
   DESCRIPTION
       " "
   ::= { sispm10403166lPortTrafficStatisticsEntry 21 }

sispm10403166lPortTrafficRxQ6 OBJECT-TYPE
   SYNTAX      Counter64
   MAX-ACCESS  read-only
   STATUS      current
   DESCRIPTION
       " "
   ::= { sispm10403166lPortTrafficStatisticsEntry 22 }

sispm10403166lPortTrafficRxQ7 OBJECT-TYPE
   SYNTAX      Counter64
   MAX-ACCESS  read-only
   STATUS      current
   DESCRIPTION
       " "
   ::= { sispm10403166lPortTrafficStatisticsEntry 23 }

sispm10403166lPortTrafficRxDrops OBJECT-TYPE
   SYNTAX      Counter64
   MAX-ACCESS  read-only
   STATUS      current
   DESCRIPTION
       " "
   ::= { sispm10403166lPortTrafficStatisticsEntry 24 }

sispm10403166lPortTrafficRxCRCorAlignment OBJECT-TYPE
   SYNTAX      Counter64
   MAX-ACCESS  read-only
   STATUS      current
   DESCRIPTION
       " "
   ::= { sispm10403166lPortTrafficStatisticsEntry 25 }

sispm10403166lPortTrafficRxUndersize OBJECT-TYPE
   SYNTAX      Counter64
   MAX-ACCESS  read-only
   STATUS      current
   DESCRIPTION
       " "
   ::= { sispm10403166lPortTrafficStatisticsEntry 26 }

sispm10403166lPortTrafficRxOversize OBJECT-TYPE
   SYNTAX      Counter64
   MAX-ACCESS  read-only
   STATUS      current
   DESCRIPTION
       " "
   ::= { sispm10403166lPortTrafficStatisticsEntry 27 }

sispm10403166lPortTrafficRxFragments OBJECT-TYPE
   SYNTAX      Counter64
   MAX-ACCESS  read-only
   STATUS      current
   DESCRIPTION
       " "
   ::= { sispm10403166lPortTrafficStatisticsEntry 28 }

sispm10403166lPortTrafficRxJabber OBJECT-TYPE
   SYNTAX      Counter64
   MAX-ACCESS  read-only
   STATUS      current
   DESCRIPTION
       " "
   ::= { sispm10403166lPortTrafficStatisticsEntry 29 }

sispm10403166lPortTrafficRxFiltered OBJECT-TYPE
   SYNTAX      Counter64
   MAX-ACCESS  read-only
   STATUS      current
   DESCRIPTION
       " "
   ::= { sispm10403166lPortTrafficStatisticsEntry 30 }

sispm10403166lPortTrafficTxPackets OBJECT-TYPE
   SYNTAX      Counter64
   MAX-ACCESS  read-only
   STATUS      current
   DESCRIPTION
       " "
   ::= { sispm10403166lPortTrafficStatisticsEntry 31 }

sispm10403166lPortTrafficTxOctets OBJECT-TYPE
   SYNTAX      Counter64
   MAX-ACCESS  read-only
   STATUS      current
   DESCRIPTION
       " "
   ::= { sispm10403166lPortTrafficStatisticsEntry 32 }

sispm10403166lPortTrafficTxUnicast OBJECT-TYPE
   SYNTAX      Counter64
   MAX-ACCESS  read-only
   STATUS      current
   DESCRIPTION
       " "
   ::= { sispm10403166lPortTrafficStatisticsEntry 33 }

sispm10403166lPortTrafficTxMulticast OBJECT-TYPE
   SYNTAX      Counter64
   MAX-ACCESS  read-only
   STATUS      current
   DESCRIPTION
       " "
   ::= { sispm10403166lPortTrafficStatisticsEntry 34 }

sispm10403166lPortTrafficTxBroadcast OBJECT-TYPE
   SYNTAX      Counter64
   MAX-ACCESS  read-only
   STATUS      current
   DESCRIPTION
       " "
   ::= { sispm10403166lPortTrafficStatisticsEntry 35 }

sispm10403166lPortTrafficTxPause OBJECT-TYPE
   SYNTAX      Counter64
   MAX-ACCESS  read-only
   STATUS      current
   DESCRIPTION
       " "
   ::= { sispm10403166lPortTrafficStatisticsEntry 36 }

sispm10403166lPortTrafficTx64Bytes OBJECT-TYPE
   SYNTAX      Counter64
   MAX-ACCESS  read-only
   STATUS      current
   DESCRIPTION
       " "
   ::= { sispm10403166lPortTrafficStatisticsEntry 37 }

sispm10403166lPortTrafficTx65to127Bytes OBJECT-TYPE
   SYNTAX      Counter64
   MAX-ACCESS  read-only
   STATUS      current
   DESCRIPTION
       " "
   ::= { sispm10403166lPortTrafficStatisticsEntry 38 }

sispm10403166lPortTrafficTx128to255Bytes OBJECT-TYPE
   SYNTAX      Counter64
   MAX-ACCESS  read-only
   STATUS      current
   DESCRIPTION
       " "
   ::= { sispm10403166lPortTrafficStatisticsEntry 39 }

sispm10403166lPortTrafficTx256to511Bytes OBJECT-TYPE
   SYNTAX      Counter64
   MAX-ACCESS  read-only
   STATUS      current
   DESCRIPTION
       " "
   ::= { sispm10403166lPortTrafficStatisticsEntry 40 }

sispm10403166lPortTrafficTx512to1023Bytes OBJECT-TYPE
   SYNTAX      Counter64
   MAX-ACCESS  read-only
   STATUS      current
   DESCRIPTION
       " "
   ::= { sispm10403166lPortTrafficStatisticsEntry 41 }

sispm10403166lPortTrafficTx1024to1526Bytes OBJECT-TYPE
   SYNTAX      Counter64
   MAX-ACCESS  read-only
   STATUS      current
   DESCRIPTION
       " "
   ::= { sispm10403166lPortTrafficStatisticsEntry 42 }

sispm10403166lPortTrafficTxExceecd1527Bytes OBJECT-TYPE
   SYNTAX      Counter64
   MAX-ACCESS  read-only
   STATUS      current
   DESCRIPTION
       " "
   ::= { sispm10403166lPortTrafficStatisticsEntry 43 }

sispm10403166lPortTrafficTxQ0 OBJECT-TYPE
   SYNTAX      Counter64
   MAX-ACCESS  read-only
   STATUS      current
   DESCRIPTION
       " "
   ::= { sispm10403166lPortTrafficStatisticsEntry 44 }

sispm10403166lPortTrafficTxQ1 OBJECT-TYPE
   SYNTAX      Counter64
   MAX-ACCESS  read-only
   STATUS      current
   DESCRIPTION
       " "
   ::= { sispm10403166lPortTrafficStatisticsEntry 45 }

sispm10403166lPortTrafficTxQ2 OBJECT-TYPE
   SYNTAX      Counter64
   MAX-ACCESS  read-only
   STATUS      current
   DESCRIPTION
       " "
   ::= { sispm10403166lPortTrafficStatisticsEntry 46 }

sispm10403166lPortTrafficTxQ3 OBJECT-TYPE
   SYNTAX      Counter64
   MAX-ACCESS  read-only
   STATUS      current
   DESCRIPTION
       " "
   ::= { sispm10403166lPortTrafficStatisticsEntry 47 }

sispm10403166lPortTrafficTxQ4 OBJECT-TYPE
   SYNTAX      Counter64
   MAX-ACCESS  read-only
   STATUS      current
   DESCRIPTION
       " "
   ::= { sispm10403166lPortTrafficStatisticsEntry 48 }

sispm10403166lPortTrafficTxQ5 OBJECT-TYPE
   SYNTAX      Counter64
   MAX-ACCESS  read-only
   STATUS      current
   DESCRIPTION
       " "
   ::= { sispm10403166lPortTrafficStatisticsEntry 49 }

sispm10403166lPortTrafficTxQ6 OBJECT-TYPE
   SYNTAX      Counter64
   MAX-ACCESS  read-only
   STATUS      current
   DESCRIPTION
       " "
   ::= { sispm10403166lPortTrafficStatisticsEntry 50 }


sispm10403166lPortTrafficTxQ7 OBJECT-TYPE
   SYNTAX      Counter64
   MAX-ACCESS  read-only
   STATUS      current
   DESCRIPTION
       " "
   ::= { sispm10403166lPortTrafficStatisticsEntry 51 }

sispm10403166lPortTrafficTxDrops OBJECT-TYPE
   SYNTAX      Counter64
   MAX-ACCESS  read-only
   STATUS      current
   DESCRIPTION
       " "
   ::= { sispm10403166lPortTrafficStatisticsEntry 52 }

sispm10403166lPortTrafficTxLateOrExcColl OBJECT-TYPE
   SYNTAX      Counter64
   MAX-ACCESS  read-only
   STATUS      current
   DESCRIPTION
       " "
   ::= { sispm10403166lPortTrafficStatisticsEntry 53 }


sispm10403166lPortQoSStatistics                                     OBJECT IDENTIFIER ::= { sispm10403166lPort 3 }

sispm10403166lPortQoSStatisticsClear OBJECT-TYPE
   SYNTAX      Integer32(0|1)
   MAX-ACCESS  read-only
   STATUS      current
   DESCRIPTION
       "default: 0
       0: none
       1: clear "
   ::= { sispm10403166lPortQoSStatistics 1 }

sispm10403166lPortQoSStatisticsTable OBJECT-TYPE
   SYNTAX      SEQUENCE OF SISPM10403166LPortQoSStatisticsEntry
   MAX-ACCESS  not-accessible
   STATUS      current
   DESCRIPTION
       " "
   ::= { sispm10403166lPortQoSStatistics 2 }

sispm10403166lPortQoSStatisticsEntry OBJECT-TYPE
   SYNTAX      SISPM10403166LPortQoSStatisticsEntry
   MAX-ACCESS  not-accessible
   STATUS      current
   DESCRIPTION
       " "
   INDEX    { sispm10403166lPortQoSStatisticsPort  }
   ::= { sispm10403166lPortQoSStatisticsTable 1 }

SISPM10403166LPortQoSStatisticsEntry ::= SEQUENCE {
   sispm10403166lPortQoSStatisticsPort      Integer32,
   sispm10403166lPortQoSQ0Rx                Counter64,
   sispm10403166lPortQoSQ0Tx                Counter64,
   sispm10403166lPortQoSQ1Rx                Counter64,
   sispm10403166lPortQoSQ1Tx                Counter64,
   sispm10403166lPortQoSQ2Rx                Counter64,
   sispm10403166lPortQoSQ2Tx                Counter64,
   sispm10403166lPortQoSQ3Rx                Counter64,
   sispm10403166lPortQoSQ3Tx                Counter64,
   sispm10403166lPortQoSQ4Rx                Counter64,
   sispm10403166lPortQoSQ4Tx                Counter64,
   sispm10403166lPortQoSQ5Rx                Counter64,
   sispm10403166lPortQoSQ5Tx                Counter64,
   sispm10403166lPortQoSQ6Rx                Counter64,
   sispm10403166lPortQoSQ6Tx                Counter64,
   sispm10403166lPortQoSQ7Rx                Counter64,
   sispm10403166lPortQoSQ7Tx                Counter64
}

sispm10403166lPortQoSStatisticsPort OBJECT-TYPE
   SYNTAX      Integer32 (1..4095)
   MAX-ACCESS  not-accessible
   STATUS      current
   DESCRIPTION
       " "
   ::= { sispm10403166lPortQoSStatisticsEntry 1 }

sispm10403166lPortQoSQ0Rx OBJECT-TYPE
   SYNTAX      Counter64
   MAX-ACCESS  read-only
   STATUS      current
   DESCRIPTION
       " "
   ::= { sispm10403166lPortQoSStatisticsEntry 2 }

sispm10403166lPortQoSQ0Tx OBJECT-TYPE
   SYNTAX      Counter64
   MAX-ACCESS  read-only
   STATUS      current
   DESCRIPTION
       " "
   ::= { sispm10403166lPortQoSStatisticsEntry 3 }

sispm10403166lPortQoSQ1Rx OBJECT-TYPE
   SYNTAX      Counter64
   MAX-ACCESS  read-only
   STATUS      current
   DESCRIPTION
       " "
   ::= { sispm10403166lPortQoSStatisticsEntry 4 }

sispm10403166lPortQoSQ1Tx OBJECT-TYPE
   SYNTAX      Counter64
   MAX-ACCESS  read-only
   STATUS      current
   DESCRIPTION
       " "
   ::= { sispm10403166lPortQoSStatisticsEntry 5 }

sispm10403166lPortQoSQ2Rx OBJECT-TYPE
   SYNTAX      Counter64
   MAX-ACCESS  read-only
   STATUS      current
   DESCRIPTION
       " "
   ::= { sispm10403166lPortQoSStatisticsEntry 6 }

sispm10403166lPortQoSQ2Tx OBJECT-TYPE
   SYNTAX      Counter64
   MAX-ACCESS  read-only
   STATUS      current
   DESCRIPTION
       " "
   ::= { sispm10403166lPortQoSStatisticsEntry 7 }

sispm10403166lPortQoSQ3Rx OBJECT-TYPE
   SYNTAX      Counter64
   MAX-ACCESS  read-only
   STATUS      current
   DESCRIPTION
       " "
   ::= { sispm10403166lPortQoSStatisticsEntry 8 }

sispm10403166lPortQoSQ3Tx OBJECT-TYPE
   SYNTAX      Counter64
   MAX-ACCESS  read-only
   STATUS      current
   DESCRIPTION
       " "
   ::= { sispm10403166lPortQoSStatisticsEntry 9 }

sispm10403166lPortQoSQ4Rx OBJECT-TYPE
   SYNTAX      Counter64
   MAX-ACCESS  read-only
   STATUS      current
   DESCRIPTION
       " "
   ::= { sispm10403166lPortQoSStatisticsEntry 10 }

sispm10403166lPortQoSQ4Tx OBJECT-TYPE
   SYNTAX      Counter64
   MAX-ACCESS  read-only
   STATUS      current
   DESCRIPTION
       " "
   ::= { sispm10403166lPortQoSStatisticsEntry 11 }

sispm10403166lPortQoSQ5Rx OBJECT-TYPE
   SYNTAX      Counter64
   MAX-ACCESS  read-only
   STATUS      current
   DESCRIPTION
       " "
   ::= { sispm10403166lPortQoSStatisticsEntry 12 }

sispm10403166lPortQoSQ5Tx OBJECT-TYPE
   SYNTAX      Counter64
   MAX-ACCESS  read-only
   STATUS      current
   DESCRIPTION
       " "
   ::= { sispm10403166lPortQoSStatisticsEntry 13 }

sispm10403166lPortQoSQ6Rx OBJECT-TYPE
   SYNTAX      Counter64
   MAX-ACCESS  read-only
   STATUS      current
   DESCRIPTION
       " "
   ::= { sispm10403166lPortQoSStatisticsEntry 14 }

sispm10403166lPortQoSQ6Tx OBJECT-TYPE
   SYNTAX      Counter64
   MAX-ACCESS  read-only
   STATUS      current
   DESCRIPTION
       " "
   ::= { sispm10403166lPortQoSStatisticsEntry 15 }

sispm10403166lPortQoSQ7Rx OBJECT-TYPE
   SYNTAX      Counter64
   MAX-ACCESS  read-only
   STATUS      current
   DESCRIPTION
       " "
   ::= { sispm10403166lPortQoSStatisticsEntry 16 }

sispm10403166lPortQoSQ7Tx OBJECT-TYPE
   SYNTAX      Counter64
   MAX-ACCESS  read-only
   STATUS      current
   DESCRIPTION
       " "
   ::= { sispm10403166lPortQoSStatisticsEntry 17 }

sispm10403166lSFPInfoTable OBJECT-TYPE
   SYNTAX      SEQUENCE OF SISPM10403166LSFPInfoEntry
   MAX-ACCESS  not-accessible
   STATUS      current
   DESCRIPTION
       " "
   ::= { sispm10403166lPort 4 }

sispm10403166lSFPInfoEntry OBJECT-TYPE
   SYNTAX      SISPM10403166LSFPInfoEntry
   MAX-ACCESS  not-accessible
   STATUS      current
   DESCRIPTION
       " "
   INDEX    { sispm10403166lSFPInfoIndex }
   ::= { sispm10403166lSFPInfoTable 1 }

SISPM10403166LSFPInfoEntry ::= SEQUENCE {
   sispm10403166lSFPInfoIndex               Integer32,
   sispm10403166lSFPInfoPort                DisplayString,
   sispm10403166lSFPConnectorType           DisplayString,
   sispm10403166lSFPFiberType               DisplayString,
   sispm10403166lSFPTxCentralWavelength     DisplayString,
   sispm10403166lSFPBaudRate                DisplayString,
   sispm10403166lSFPVendorOUI               DisplayString,
   sispm10403166lSFPVendorName              DisplayString,
   sispm10403166lSFPVendorPN                DisplayString,
   sispm10403166lSFPVendorRev               DisplayString,
   sispm10403166lSFPVendorSN                DisplayString,
   sispm10403166lSFPDateCode                DisplayString,
   sispm10403166lSFPTemperature             DisplayString,
   sispm10403166lSFPVcc                     DisplayString,
   sispm10403166lSFPMon1Bias                DisplayString,
   sispm10403166lSFPMon2TxPWR               DisplayString,
   sispm10403166lSFPMon3RxPWR               DisplayString
}

sispm10403166lSFPInfoIndex OBJECT-TYPE
   SYNTAX      Integer32 (1..4095)
   MAX-ACCESS  not-accessible
   STATUS      current
   DESCRIPTION
       " "
   ::= { sispm10403166lSFPInfoEntry 1 }

sispm10403166lSFPInfoPort OBJECT-TYPE
   SYNTAX      DisplayString
   MAX-ACCESS  read-only
   STATUS      current
   DESCRIPTION
       " "
   ::= { sispm10403166lSFPInfoEntry 2 }

sispm10403166lSFPConnectorType OBJECT-TYPE
   SYNTAX      DisplayString
   MAX-ACCESS  read-only
   STATUS      current
   DESCRIPTION
       " "
   ::= { sispm10403166lSFPInfoEntry 3 }

sispm10403166lSFPFiberType OBJECT-TYPE
   SYNTAX      DisplayString
   MAX-ACCESS  read-only
   STATUS      current
   DESCRIPTION
       " "
   ::= { sispm10403166lSFPInfoEntry 4 }

sispm10403166lSFPTxCentralWavelength OBJECT-TYPE
   SYNTAX      DisplayString
   MAX-ACCESS  read-only
   STATUS      current
   DESCRIPTION
       " "
   ::= { sispm10403166lSFPInfoEntry 5 }

sispm10403166lSFPBaudRate OBJECT-TYPE
   SYNTAX      DisplayString
   MAX-ACCESS  read-only
   STATUS      current
   DESCRIPTION
       " "
   ::= { sispm10403166lSFPInfoEntry 6 }

sispm10403166lSFPVendorOUI OBJECT-TYPE
   SYNTAX      DisplayString
   MAX-ACCESS  read-only
   STATUS      current
   DESCRIPTION
       " "
   ::= { sispm10403166lSFPInfoEntry 7 }

sispm10403166lSFPVendorName OBJECT-TYPE
   SYNTAX      DisplayString
   MAX-ACCESS  read-only
   STATUS      current
   DESCRIPTION
       " "
   ::= { sispm10403166lSFPInfoEntry 8 }

sispm10403166lSFPVendorPN OBJECT-TYPE
   SYNTAX      DisplayString
   MAX-ACCESS  read-only
   STATUS      current
   DESCRIPTION
       " "
   ::= { sispm10403166lSFPInfoEntry 9 }

sispm10403166lSFPVendorRev OBJECT-TYPE
   SYNTAX      DisplayString
   MAX-ACCESS  read-only
   STATUS      current
   DESCRIPTION
       " "
   ::= { sispm10403166lSFPInfoEntry 10 }

sispm10403166lSFPVendorSN OBJECT-TYPE
   SYNTAX      DisplayString
   MAX-ACCESS  read-only
   STATUS      current
   DESCRIPTION
       " "
   ::= { sispm10403166lSFPInfoEntry 11 }

sispm10403166lSFPDateCode OBJECT-TYPE
   SYNTAX      DisplayString
   MAX-ACCESS  read-only
   STATUS      current
   DESCRIPTION
       " "
   ::= { sispm10403166lSFPInfoEntry 12 }

sispm10403166lSFPTemperature OBJECT-TYPE
   SYNTAX      DisplayString
   MAX-ACCESS  read-only
   STATUS      current
   DESCRIPTION
       "Value of Celsius"
   ::= { sispm10403166lSFPInfoEntry 13 }

sispm10403166lSFPVcc OBJECT-TYPE
   SYNTAX      DisplayString
   MAX-ACCESS  read-only
   STATUS      current
   DESCRIPTION
       "Value of V"
   ::= { sispm10403166lSFPInfoEntry 14 }

sispm10403166lSFPMon1Bias OBJECT-TYPE
   SYNTAX      DisplayString
   MAX-ACCESS  read-only
   STATUS      current
   DESCRIPTION
       "Value of mA"
   ::= { sispm10403166lSFPInfoEntry 15 }

sispm10403166lSFPMon2TxPWR OBJECT-TYPE
   SYNTAX      DisplayString
   MAX-ACCESS  read-only
   STATUS      current
   DESCRIPTION
       "Value of dBm"
   ::= { sispm10403166lSFPInfoEntry 16 }

sispm10403166lSFPMon3RxPWR OBJECT-TYPE
   SYNTAX      DisplayString
   MAX-ACCESS  read-only
   STATUS      current
   DESCRIPTION
       "Value of dBm"
   ::= { sispm10403166lSFPInfoEntry 17 }


sispm10403166lVoiceVLAN                                             OBJECT IDENTIFIER ::= { sispm10403166lConfiguration 2 }

sispm10403166lVoiceVLANConf                                         OBJECT IDENTIFIER ::= { sispm10403166lVoiceVLAN 1 }

sispm10403166lVoiceVLANMode OBJECT-TYPE
   SYNTAX      Integer32 (0|1)
   MAX-ACCESS  read-write
   STATUS      current
   DESCRIPTION
       " Voice VLAN mode operation.
       default: 0,
       0: disable
       1: enable"
   ::= { sispm10403166lVoiceVLANConf 1 }

sispm10403166lVoiceVLANVLANId OBJECT-TYPE
   SYNTAX      Integer32 (1..4094)
   MAX-ACCESS  read-write
   STATUS      current
   DESCRIPTION
       "Voice VLAN ID.
        default: 1000,
        range : 1-4094. "
   ::= { sispm10403166lVoiceVLANConf 2 }

sispm10403166lVoiceVLANAgingTime OBJECT-TYPE
   SYNTAX      Integer32 (10..10000000)
   MAX-ACCESS  read-write
   STATUS      current
   DESCRIPTION
       " Voice VLAN secure learning aging time.
         default: 86400,
         range : 10 - 10000000. "
   ::= { sispm10403166lVoiceVLANConf 3 }

sispm10403166lVoiceVLANTrafficClass OBJECT-TYPE
   SYNTAX      Integer32 (0..7)
   MAX-ACCESS  read-write
   STATUS      current
   DESCRIPTION
       " Voice VLAN traffic class, all traffic on the Voice VLAN
         will apply this class, available value is from 0(Low)
         to 7(High).
         default: 7. "
   ::= { sispm10403166lVoiceVLANConf 4 }


sispm10403166lVoiceVLANPortTable OBJECT-TYPE
   SYNTAX      SEQUENCE OF SISPM10403166LVoiceVLANPortEntry
   MAX-ACCESS  not-accessible
   STATUS      current
   DESCRIPTION
       " Show Voice Vlan configuration. "
   ::= { sispm10403166lVoiceVLANConf 5 }

sispm10403166lVoiceVLANPortEntry OBJECT-TYPE
   SYNTAX      SISPM10403166LVoiceVLANPortEntry
   MAX-ACCESS  not-accessible
   STATUS      current
   DESCRIPTION
       " "
   INDEX    { sispm10403166lVoiceVLANPort  }
   ::= { sispm10403166lVoiceVLANPortTable 1 }

SISPM10403166LVoiceVLANPortEntry ::= SEQUENCE {
   sispm10403166lVoiceVLANPort                    Integer32,
   sispm10403166lVoiceVLANPortMode                Integer32,
   sispm10403166lVoiceVLANPortSecurity            Integer32,
   sispm10403166lVoiceVLANPortDiscoveryProtocol   Integer32
}

sispm10403166lVoiceVLANPort OBJECT-TYPE
   SYNTAX      Integer32 (1..4095)
   MAX-ACCESS  not-accessible
   STATUS      current
   DESCRIPTION
       " port, range : 1 - port number. "
   ::= { sispm10403166lVoiceVLANPortEntry 1 }

sispm10403166lVoiceVLANPortMode OBJECT-TYPE
   SYNTAX      Integer32 (0..2)
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { sispm10403166lVoiceVLANPortEntry 2 }

sispm10403166lVoiceVLANPortSecurity OBJECT-TYPE
   SYNTAX      Integer32 (0|1)
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { sispm10403166lVoiceVLANPortEntry 3 }

sispm10403166lVoiceVLANPortDiscoveryProtocol OBJECT-TYPE
   SYNTAX      Integer32 (0..2)
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { sispm10403166lVoiceVLANPortEntry 4 }


sispm10403166lVoiceVLANOUI                                          OBJECT IDENTIFIER ::= { sispm10403166lVoiceVLAN 2 }

sispm10403166lVoiceVLANOUICreate OBJECT-TYPE
   SYNTAX       Integer32(0|1)
   MAX-ACCESS   read-write
   STATUS       current
   DESCRIPTION
       "default: 0
        0 : None  (read only)
        1 : Create an OUI entry"
   ::= { sispm10403166lVoiceVLANOUI 1 }

sispm10403166lVoiceVLANOUITable OBJECT-TYPE
   SYNTAX      SEQUENCE OF SISPM10403166LVoiceVLANOUIEntry
   MAX-ACCESS  not-accessible
   STATUS      current
   DESCRIPTION
       " Create Voice VLAN OUI entry. Modify OUI table will
         restart auto detect OUI process. "
   ::= { sispm10403166lVoiceVLANOUI 2 }

sispm10403166lVoiceVLANOUIEntry OBJECT-TYPE
   SYNTAX      SISPM10403166LVoiceVLANOUIEntry
   MAX-ACCESS  not-accessible
   STATUS      current
   DESCRIPTION
       " "
   INDEX    { sispm10403166lVoiceVLANOUIIndex  }
   ::= { sispm10403166lVoiceVLANOUITable 1 }

SISPM10403166LVoiceVLANOUIEntry ::= SEQUENCE {
   sispm10403166lVoiceVLANOUIIndex         Integer32,
   sispm10403166lVoiceVLANTelephonyOUI     DisplayString,
   sispm10403166lVoiceVLANDescription      DisplayString,
   sispm10403166lVoiceVLANOUIRowStatus     RowStatus
}

sispm10403166lVoiceVLANOUIIndex OBJECT-TYPE
   SYNTAX      Integer32 (1..16)
   MAX-ACCESS  not-accessible
   STATUS      current
   DESCRIPTION
       " "
   ::= { sispm10403166lVoiceVLANOUIEntry 1 }

sispm10403166lVoiceVLANTelephonyOUI OBJECT-TYPE
   SYNTAX      DisplayString (SIZE (1..32))
   MAX-ACCESS  read-create
   STATUS      current
   DESCRIPTION
       "OUI address, format : 0a 1b 2c "
   ::= { sispm10403166lVoiceVLANOUIEntry 2 }

sispm10403166lVoiceVLANDescription OBJECT-TYPE
   SYNTAX      DisplayString (SIZE (1..32))
   MAX-ACCESS  read-create
   STATUS      current
   DESCRIPTION
       " Up to 32 characters describing OUI address. "
   ::= { sispm10403166lVoiceVLANOUIEntry 3 }

sispm10403166lVoiceVLANOUIRowStatus OBJECT-TYPE
   SYNTAX      RowStatus
   MAX-ACCESS  read-create
   STATUS      current
   DESCRIPTION
	   "This object indicates the status of this entry, and is used
	   to create/delete entries.  Any object in an entry of this table
	   may be modified while the value of the corresponding instance
	   of this object is active(1).
	   createAndGo, notReady not supported."
   ::= { sispm10403166lVoiceVLANOUIEntry 4 }

--sispm10403166lGARP                                                   OBJECT IDENTIFIER ::= { sispm10403166lConfiguration 3 }

--sispm10403166lGARPConfTable OBJECT-TYPE
--   SYNTAX      SEQUENCE OF SISPM10403166LGARPConfEntry
--   MAX-ACCESS  not-accessible
--   STATUS      current
--   DESCRIPTION
--       " "
--   ::= { sispm10403166lGARP 1 }

--sispm10403166lGARPConfEntry OBJECT-TYPE
--   SYNTAX      SISPM10403166LGARPConfEntry
--   MAX-ACCESS  not-accessible
--   STATUS      current
--   DESCRIPTION
--       " "
--   INDEX    { sispm10403166lGARPConfPort  }
--   ::= { sispm10403166lGARPConfTable 1 }

--SISPM10403166LGARPConfEntry ::= SEQUENCE {
--   sispm10403166lGARPConfPort           Integer32,
--   sispm10403166lGARPJoinTimer          Integer32,
--   sispm10403166lGARPLeaveTimer         Integer32,
--   sispm10403166lGARPLeaveAllTimer      Integer32,
--   sispm10403166lGARPApplicantion       Integer32,
--   sispm10403166lGARPAttributeType      Integer32,
--   sispm10403166lGARPApplicant          Integer32
--}

--sispm10403166lGARPConfPort OBJECT-TYPE
--   SYNTAX      Integer32 (1..4095)
--   MAX-ACCESS  not-accessible
--   STATUS      current
--   DESCRIPTION
--       " "
--   ::= { sispm10403166lGARPConfEntry 1 }

--sispm10403166lGARPJoinTimer OBJECT-TYPE
--   SYNTAX      Integer32 (200..1000)
--   MAX-ACCESS  read-write
--   STATUS      current
--   DESCRIPTION
--       "default: 200, range : 200 - 1000 "
--   ::= { sispm10403166lGARPConfEntry 2 }

--sispm10403166lGARPLeaveTimer OBJECT-TYPE
--   SYNTAX      Integer32 (600..3000)
--   MAX-ACCESS  read-write
--   STATUS      current
--   DESCRIPTION
--       "default: 600 , range : 600 - 3000"
--   ::= { sispm10403166lGARPConfEntry 3 }

--sispm10403166lGARPLeaveAllTimer OBJECT-TYPE
--   SYNTAX      Integer32 (10000..50000)
--   MAX-ACCESS  read-write
--   STATUS      current
--   DESCRIPTION
--       "default: 10000, range : 10000 - 50000 "
--   ::= { sispm10403166lGARPConfEntry 4 }

--sispm10403166lGARPApplicantion OBJECT-TYPE
--   SYNTAX      Integer32(1)
--   MAX-ACCESS  read-write
--   STATUS      current
--   DESCRIPTION
--       "default: 1
--       1: GVRP"
--   ::= { sispm10403166lGARPConfEntry 5 }

--sispm10403166lGARPAttributeType OBJECT-TYPE
--   SYNTAX      Integer32(1)
--   MAX-ACCESS  read-write
--   STATUS      current
--   DESCRIPTION
--       "default: 1
--       1: VLAN"
--   ::= { sispm10403166lGARPConfEntry 6 }

--sispm10403166lGARPApplicant OBJECT-TYPE
--   SYNTAX      Integer32(0|1)
--   MAX-ACCESS  read-write
--   STATUS      current
--   DESCRIPTION
--       "default: 0
--       0: normal-participant
--       1: non-participant"
--   ::= { sispm10403166lGARPConfEntry 7 }

--sispm10403166lGARPStatisticsTable OBJECT-TYPE
--   SYNTAX      SEQUENCE OF SISPM10403166LGARPStatisticsEntry
--   MAX-ACCESS  not-accessible
--   STATUS      current
--   DESCRIPTION
--       " Show the basic GARP port statistics. "
--   ::= { sispm10403166lGARP 2 }

--sispm10403166lGARPStatisticsEntry OBJECT-TYPE
--   SYNTAX      SISPM10403166LGARPStatisticsEntry
--   MAX-ACCESS  not-accessible
--   STATUS      current
--   DESCRIPTION
--       " "
--   INDEX    { sispm10403166lGARPStatisticsPort  }
--   ::= { sispm10403166lGARPStatisticsTable 1 }

--SISPM10403166LGARPStatisticsEntry ::= SEQUENCE {
--   sispm10403166lGARPStatisticsPort             Integer32,
--   sispm10403166lGARPStatisticsPeerMAC          DisplayString,
--   sispm10403166lGARPStatisticsFailedCount      Counter32
--}

--sispm10403166lGARPStatisticsPort OBJECT-TYPE
--   SYNTAX      Integer32 (1..4095)
--   MAX-ACCESS  not-accessible
--   STATUS      current
--   DESCRIPTION
--       " port, range : 1 - port number. "
--   ::= { sispm10403166lGARPStatisticsEntry 1 }

--sispm10403166lGARPStatisticsPeerMAC OBJECT-TYPE
--   SYNTAX      DisplayString
--   MAX-ACCESS  read-only
--   STATUS      current
--   DESCRIPTION
--       " Peer MAC is MAC address of the neighbour Switch from with GARP frame is received.  "
--   ::= { sispm10403166lGARPStatisticsEntry 2 }

--sispm10403166lGARPStatisticsFailedCount OBJECT-TYPE
--   SYNTAX      Counter32
--   MAX-ACCESS  read-only
--   STATUS      current
--   DESCRIPTION
--       " explain Failed count here. "
--   ::= { sispm10403166lGARPStatisticsEntry 3 }

sispm10403166lGVRP                                                   OBJECT IDENTIFIER ::= { sispm10403166lConfiguration 4 }

sispm10403166lGVRPConf                                                   OBJECT IDENTIFIER ::= { sispm10403166lGVRP 1 }

sispm10403166lGVRPMode OBJECT-TYPE
   SYNTAX      Integer32(0|1)
   MAX-ACCESS  read-write
   STATUS      current
   DESCRIPTION
       "default: 0,
        0: disable,
        1: enable. "
   ::= { sispm10403166lGVRPConf 1 }

sispm10403166lGVRPMaxVlan OBJECT-TYPE
   SYNTAX      Integer32(1..4095)
   MAX-ACCESS  read-write
   STATUS      current
   DESCRIPTION
       "Number of simultaniously VLANs that GVRP can control. "
   ::= { sispm10403166lGVRPConf 2 }

sispm10403166lGVRPJoinTime OBJECT-TYPE
   SYNTAX      Integer32(1..20)
   MAX-ACCESS  read-write
   STATUS      current
   DESCRIPTION
       "join-time in units of centi seconds. Range is 1-20. Default is 20. "
   ::= { sispm10403166lGVRPConf 3 }

sispm10403166lGVRPLeaveTime OBJECT-TYPE
   SYNTAX      Integer32(60..300)
   MAX-ACCESS  read-write
   STATUS      current
   DESCRIPTION
       "leave-time in units of centi seconds. Range is 60-300. Default is 60. "
   ::= { sispm10403166lGVRPConf 4 }

sispm10403166lGVRPLeaveAllTime OBJECT-TYPE
   SYNTAX      Integer32(1000..5000)
   MAX-ACCESS  read-write
   STATUS      current
   DESCRIPTION
       "leave-all-time in units of centi seconds Range is 1000-5000. Default is 1000"
   ::= { sispm10403166lGVRPConf 5 }

sispm10403166lGVRPConfTable OBJECT-TYPE
   SYNTAX      SEQUENCE OF SISPM10403166LGVRPConfEntry
   MAX-ACCESS  not-accessible
   STATUS      current
   DESCRIPTION
       " "
   ::= { sispm10403166lGVRPConf 6 }

sispm10403166lGVRPConfEntry OBJECT-TYPE
   SYNTAX      SISPM10403166LGVRPConfEntry
   MAX-ACCESS  not-accessible
   STATUS      current
   DESCRIPTION
       " "
   INDEX    { sispm10403166lGVRPConfPort  }
   ::= { sispm10403166lGVRPConfTable 1 }

SISPM10403166LGVRPConfEntry ::= SEQUENCE {
   sispm10403166lGVRPConfPort           Integer32,
   sispm10403166lGVRPConfPortMode       Integer32
-- sispm10403166lGVRPConfPortRRole      Integer32
}

sispm10403166lGVRPConfPort OBJECT-TYPE
   SYNTAX      Integer32 (1..4095)
   MAX-ACCESS  not-accessible
   STATUS      current
   DESCRIPTION
       " "
   ::= { sispm10403166lGVRPConfEntry 1 }

sispm10403166lGVRPConfPortMode OBJECT-TYPE
   SYNTAX      Integer32(0|1)
   MAX-ACCESS  read-write
   STATUS      current
   DESCRIPTION
       "default: 0
       1: enable
       0: disable"
   ::= { sispm10403166lGVRPConfEntry 2 }

--sispm10403166lGVRPConfPortRRole OBJECT-TYPE
--   SYNTAX      Integer32(0|1)
--   MAX-ACCESS  read-write
--   STATUS      current
--   DESCRIPTION
--       "default: 0
--       1: enable
--       0: disable"
--   ::= { sispm10403166lGVRPConfEntry 3 }

--sispm10403166lGVRPStatisticsTable OBJECT-TYPE
--   SYNTAX      SEQUENCE OF SISPM10403166LGVRPStatisticsEntry
--   MAX-ACCESS  not-accessible
--   STATUS      current
--   DESCRIPTION
--       " "
--   ::= { sispm10403166lGVRP 2 }

--sispm10403166lGVRPStatisticsEntry OBJECT-TYPE
--   SYNTAX      SISPM10403166LGVRPStatisticsEntry
--   MAX-ACCESS  not-accessible
--   STATUS      current
--   DESCRIPTION
--       " "
--   INDEX    { sispm10403166lGVRPStatisticsPort  }
--   ::= { sispm10403166lGVRPStatisticsTable 1 }

--SISPM10403166LGVRPStatisticsEntry ::= SEQUENCE {
--   sispm10403166lGVRPStatisticsPort         Integer32,
--   sispm10403166lGVRPStatisticsJoinTxCnt    Counter32,
--   sispm10403166lGVRPStatisticsLeaveTxCnt   Counter32
--}

--sispm10403166lGVRPStatisticsPort OBJECT-TYPE
--   SYNTAX      Integer32 (1..4095)
--   MAX-ACCESS  not-accessible
--   STATUS      current
--   DESCRIPTION
--       " "
--   ::= { sispm10403166lGVRPStatisticsEntry 1 }

--sispm10403166lGVRPStatisticsJoinTxCnt OBJECT-TYPE
--   SYNTAX      Counter32
--   MAX-ACCESS  read-only
--   STATUS      current
--   DESCRIPTION
--       " "
--   ::= { sispm10403166lGVRPStatisticsEntry 2 }

--sispm10403166lGVRPStatisticsLeaveTxCnt OBJECT-TYPE
--   SYNTAX      Counter32
--   MAX-ACCESS  read-only
--   STATUS      current
--   DESCRIPTION
--       " "
--   ::= { sispm10403166lGVRPStatisticsEntry 3 }


sispm10403166lMirroring                                             OBJECT IDENTIFIER ::= { sispm10403166lConfiguration 6 }

sispm10403166lMonitorSession OBJECT-TYPE
   SYNTAX      Integer32(1..5)
   MAX-ACCESS  read-write
   STATUS      current
   DESCRIPTION
       "Monitor session."
   ::= { sispm10403166lMirroring 1 }

sispm10403166lPortToMirrorOn OBJECT-TYPE
   SYNTAX      Integer32
   MAX-ACCESS  read-write
   STATUS      current
   DESCRIPTION
       "default: 0
        0: disable,
        range : 1 - port number. "
   ::= { sispm10403166lMirroring 2 }

sispm10403166lMirrorTable OBJECT-TYPE
   SYNTAX      SEQUENCE OF SISPM10403166LMirrorEntry
   MAX-ACCESS  not-accessible
   STATUS      current
   DESCRIPTION
       " "
   ::= { sispm10403166lMirroring 3 }

sispm10403166lMirrorEntry OBJECT-TYPE
   SYNTAX      SISPM10403166LMirrorEntry
   MAX-ACCESS  not-accessible
   STATUS      current
   DESCRIPTION
       " "
   INDEX    { sispm10403166lMirrorPort  }
   ::= { sispm10403166lMirrorTable 1 }

SISPM10403166LMirrorEntry ::= SEQUENCE {
   sispm10403166lMirrorPort		Integer32,
   sispm10403166lMirrorMode		Integer32
}

sispm10403166lMirrorPort OBJECT-TYPE
   SYNTAX      Integer32 (1..4095)
   MAX-ACCESS  not-accessible
   STATUS      current
   DESCRIPTION
       " "
   ::= { sispm10403166lMirrorEntry 1 }

sispm10403166lMirrorMode OBJECT-TYPE
   SYNTAX      Integer32(0..3)
   MAX-ACCESS  read-write
   STATUS      current
   DESCRIPTION
       "default: 0
       0: disable
       1: rx only
       2: tx only
       3: enable
       Setting Tx mirroring for analyzer port has no effect. Tx mirroring ignored"
   ::= { sispm10403166lMirrorEntry 2 }

sispm10403166lTrapEventSeverity                                             OBJECT IDENTIFIER ::= { sispm10403166lConfiguration 7 }

sispm10403166lTrapEventSeverityTable OBJECT-TYPE
   SYNTAX      SEQUENCE OF SISPM10403166LTrapEventSeverityEntry
   MAX-ACCESS  not-accessible
   STATUS      current
   DESCRIPTION
       " "
   ::= { sispm10403166lTrapEventSeverity 1 }

sispm10403166lTrapEventSeverityEntry OBJECT-TYPE
   SYNTAX      SISPM10403166LTrapEventSeverityEntry
   MAX-ACCESS  not-accessible
   STATUS      current
   DESCRIPTION
       " "
   INDEX    { sispm10403166lTrapEventSeverityIndex }
   ::= { sispm10403166lTrapEventSeverityTable 1 }

SISPM10403166LTrapEventSeverityEntry ::= SEQUENCE {
   sispm10403166lTrapEventSeverityIndex        Integer32,
   sispm10403166lTrapEventSeverityGroupName    DisplayString,
   sispm10403166lTrapEventSeverityLevel        Integer32,
   sispm10403166lTrapEventSeveritySyslog       Integer32,
   sispm10403166lTrapEventSeverityTrap         Integer32,
   sispm10403166lTrapEventSeveritySMTP         Integer32,
   sispm10403166lTrapEventSeverityDigitalOut   Integer32
}

sispm10403166lTrapEventSeverityIndex OBJECT-TYPE
   SYNTAX      Integer32(1..65535)
   MAX-ACCESS  not-accessible
   STATUS      current
   DESCRIPTION
       " "
   ::= { sispm10403166lTrapEventSeverityEntry 1 }

sispm10403166lTrapEventSeverityGroupName OBJECT-TYPE
   SYNTAX      DisplayString
   MAX-ACCESS  read-only
   STATUS      current
   DESCRIPTION
       "Group Name"
   ::= { sispm10403166lTrapEventSeverityEntry 2 }

sispm10403166lTrapEventSeverityLevel OBJECT-TYPE
   SYNTAX      Integer32
   MAX-ACCESS  not-accessible
   STATUS      current
   DESCRIPTION
       "0:Emergency
       1:Alert
       2:Critical
       3:Error
       4:Warning
       5:Notice
       6:Information
       7:Debug"
   ::= { sispm10403166lTrapEventSeverityEntry 3 }

sispm10403166lTrapEventSeveritySyslog OBJECT-TYPE
   SYNTAX      Integer32
   MAX-ACCESS  not-accessible
   STATUS      current
   DESCRIPTION
       "0:disable
       1:enable"
   ::= { sispm10403166lTrapEventSeverityEntry 4 }

sispm10403166lTrapEventSeverityTrap OBJECT-TYPE
   SYNTAX      Integer32
   MAX-ACCESS  not-accessible
   STATUS      current
   DESCRIPTION
       "0:disable
       1:enable"
   ::= { sispm10403166lTrapEventSeverityEntry 5 }

sispm10403166lTrapEventSeveritySMTP OBJECT-TYPE
   SYNTAX      Integer32
   MAX-ACCESS  not-accessible
   STATUS      current
   DESCRIPTION
       "0:disable
       1:enable"
   ::= { sispm10403166lTrapEventSeverityEntry 6 }

sispm10403166lTrapEventSeverityDigitalOut OBJECT-TYPE
   SYNTAX      Integer32
   MAX-ACCESS  not-accessible
   STATUS      current
   DESCRIPTION
       "0:disable
       1:enable
	   -1:not support"
   ::= { sispm10403166lTrapEventSeverityEntry 8 }

sispm10403166lPortEventSettingTable OBJECT-TYPE
   SYNTAX      SEQUENCE OF SISPM10403166LPortEventSettingEntry
   MAX-ACCESS  not-accessible
   STATUS      current
   DESCRIPTION
       " "
   ::= { sispm10403166lTrapEventSeverity 2 }

sispm10403166lPortEventSettingEntry OBJECT-TYPE
   SYNTAX      SISPM10403166LPortEventSettingEntry
   MAX-ACCESS  not-accessible
   STATUS      current
   DESCRIPTION
       " "
   INDEX    { sispm10403166lPortEventSettingIndex }
   ::= { sispm10403166lPortEventSettingTable 1 }

SISPM10403166LPortEventSettingEntry ::= SEQUENCE {
   sispm10403166lPortEventSettingIndex           Integer32,
   sispm10403166lPortEventSettingActive          Integer32,
   sispm10403166lPortEventSettingLinkOn          Integer32,
   sispm10403166lPortEventSettingLinkOff         Integer32,
   sispm10403166lPortEventSettingOverload        Integer32,
   sispm10403166lPortEventSettingThreshold       Integer32,
   sispm10403166lPortEventSettingTrafficDuration Integer32,
   sispm10403166lPortEventSettingSyslog          Integer32,
   sispm10403166lPortEventSettingTrap            Integer32,
   sispm10403166lPortEventSettingSmtp            Integer32,
   sispm10403166lPortEventSettingSwitch2go       Integer32,
   sispm10403166lPortEventSettingDigitialout     Integer32,
   sispm10403166lPortEventSettingSeverity        Integer32
}

sispm10403166lPortEventSettingIndex OBJECT-TYPE
   SYNTAX      Integer32 (1..65535)
   MAX-ACCESS  not-accessible
   STATUS      current
   DESCRIPTION
       " "
   ::= { sispm10403166lPortEventSettingEntry 1 }

sispm10403166lPortEventSettingActive OBJECT-TYPE
   SYNTAX      Integer32
   MAX-ACCESS  not-accessible
   STATUS      current
   DESCRIPTION
       "0:disable
       1:enable"
   ::= { sispm10403166lPortEventSettingEntry 2}

sispm10403166lPortEventSettingLinkOn OBJECT-TYPE
   SYNTAX      Integer32
   MAX-ACCESS  not-accessible
   STATUS      current
   DESCRIPTION
       "0:disable
       1:enable"
   ::= { sispm10403166lPortEventSettingEntry 3}

sispm10403166lPortEventSettingLinkOff OBJECT-TYPE
   SYNTAX      Integer32
   MAX-ACCESS  not-accessible
   STATUS      current
   DESCRIPTION
       "0:disable
       1:enable"
   ::= { sispm10403166lPortEventSettingEntry 4}

sispm10403166lPortEventSettingOverload OBJECT-TYPE
   SYNTAX      Integer32
   MAX-ACCESS  not-accessible
   STATUS      current
   DESCRIPTION
       "0:disable
       1:enable"
   ::= { sispm10403166lPortEventSettingEntry 5}

sispm10403166lPortEventSettingThreshold OBJECT-TYPE
   SYNTAX      Integer32
   MAX-ACCESS  not-accessible
   STATUS      current
   DESCRIPTION
       "Range:0-100"
   ::= { sispm10403166lPortEventSettingEntry 6}

sispm10403166lPortEventSettingTrafficDuration OBJECT-TYPE
   SYNTAX      Integer32
   MAX-ACCESS  not-accessible
   STATUS      current
   DESCRIPTION
       "Range:1-300"
   ::= { sispm10403166lPortEventSettingEntry 7}

sispm10403166lPortEventSettingSyslog OBJECT-TYPE
   SYNTAX      Integer32
   MAX-ACCESS  not-accessible
   STATUS      current
   DESCRIPTION
       "0:disable
       1:enable"
   ::= { sispm10403166lPortEventSettingEntry 8}

sispm10403166lPortEventSettingTrap OBJECT-TYPE
   SYNTAX      Integer32
   MAX-ACCESS  not-accessible
   STATUS      current
   DESCRIPTION
       "0:disable
       1:enable"
   ::= { sispm10403166lPortEventSettingEntry 9}

sispm10403166lPortEventSettingSmtp OBJECT-TYPE
   SYNTAX      Integer32
   MAX-ACCESS  not-accessible
   STATUS      current
   DESCRIPTION
       "0:disable
       1:enable"
   ::= { sispm10403166lPortEventSettingEntry 10}

sispm10403166lPortEventSettingSwitch2go OBJECT-TYPE
   SYNTAX      Integer32
   MAX-ACCESS  not-accessible
   STATUS      current
   DESCRIPTION
       "0:disable
       1:enable"
   ::= { sispm10403166lPortEventSettingEntry 11}

sispm10403166lPortEventSettingDigitialout OBJECT-TYPE
   SYNTAX      Integer32
   MAX-ACCESS  not-accessible
   STATUS      current
   DESCRIPTION
       "0:disable
       1:enable"
   ::= { sispm10403166lPortEventSettingEntry 12}

sispm10403166lPortEventSettingSeverity OBJECT-TYPE
   SYNTAX      Integer32
   MAX-ACCESS  not-accessible
   STATUS      current
   DESCRIPTION
       "0:Emergency
       1:Alert
       2:Critical
       3:Error
       4:Warning
       5:Notice
       6:Information
       7:Debug"
   ::= { sispm10403166lPortEventSettingEntry 13 }

-- =======================================================================================================================
sispm10403166lSMTP                                             OBJECT IDENTIFIER ::= { sispm10403166lConfiguration 8 }

sispm10403166lSMTPMailServer OBJECT-TYPE
   SYNTAX      DisplayString
   MAX-ACCESS  read-write
   STATUS      current
   DESCRIPTION
       " Up to 47 characters describing email server. "
   ::= { sispm10403166lSMTP 1 }

sispm10403166lSMTPUserName OBJECT-TYPE
   SYNTAX      DisplayString
   MAX-ACCESS  read-write
   STATUS      current
   DESCRIPTION
       " Up to 47 characters describing user name. "
   ::= { sispm10403166lSMTP 2 }

sispm10403166lSMTPPassword OBJECT-TYPE
   SYNTAX      DisplayString
   MAX-ACCESS  read-write
   STATUS      current
   DESCRIPTION
       " Up to 47 characters describing password. "
   ::= { sispm10403166lSMTP 3 }

sispm10403166lSMTPSender OBJECT-TYPE
   SYNTAX      DisplayString
   MAX-ACCESS  read-write
   STATUS      current
   DESCRIPTION
       " Up to 47 characters describing sender. "
   ::= { sispm10403166lSMTP 5 }

sispm10403166lSMTPReturnPath OBJECT-TYPE
   SYNTAX      DisplayString
   MAX-ACCESS  read-write
   STATUS      current
   DESCRIPTION
       " Up to 47 characters describing return path. "
   ::= { sispm10403166lSMTP 6 }

sispm10403166lSMTPEmailAddress1 OBJECT-TYPE
   SYNTAX      DisplayString
   MAX-ACCESS  read-write
   STATUS      current
   DESCRIPTION
       " Up to 47 characters describing mail address. "
   ::= { sispm10403166lSMTP 7 }

sispm10403166lSMTPEmailAddress2 OBJECT-TYPE
   SYNTAX      DisplayString
   MAX-ACCESS  read-write
   STATUS      current
   DESCRIPTION
       " Up to 47 characters describing mail address. "
   ::= { sispm10403166lSMTP 8 }

sispm10403166lSMTPEmailAddress3 OBJECT-TYPE
   SYNTAX      DisplayString
   MAX-ACCESS  read-write
   STATUS      current
   DESCRIPTION
       " Up to 47 characters describing mail address. "
   ::= { sispm10403166lSMTP 9 }

sispm10403166lSMTPEmailAddress4 OBJECT-TYPE
   SYNTAX      DisplayString
   MAX-ACCESS  read-write
   STATUS      current
   DESCRIPTION
       " Up to 47 characters describing mail address. "
   ::= { sispm10403166lSMTP 10 }

sispm10403166lSMTPEmailAddress5 OBJECT-TYPE
   SYNTAX      DisplayString
   MAX-ACCESS  read-write
   STATUS      current
   DESCRIPTION
       " Up to 47 characters describing mail address. "
   ::= { sispm10403166lSMTP 11 }

sispm10403166lSMTPEmailAddress6 OBJECT-TYPE
   SYNTAX      DisplayString
   MAX-ACCESS  read-write
   STATUS      current
   DESCRIPTION
       " Up to 47 characters describing mail address. "
   ::= { sispm10403166lSMTP 12 }

-- =======================================================================================================================
sispm10403166lACLConf                                              OBJECT IDENTIFIER ::= { sispm10403166lConfiguration 9 }

-- RowStatus Info:  createAndGo, notReady not supported.
-- =======================================================================================================================
-- Textual Conventions for the sispm10403166l Acl Mib
-- =======================================================================================================================
--
    sispm10403166lACL                     OBJECT IDENTIFIER  ::= { sispm10403166lACLConf 1 }
    sispm10403166lACLACE                  OBJECT IDENTIFIER  ::= { sispm10403166lACLConf 3 }

--
-- =======================================================================================================================
-- Start sispm10403166lACLPortConf group
-- =======================================================================================================================
--sispm10403166lACLPortConfTable

    sispm10403166lACLPortConfTable OBJECT-TYPE
               SYNTAX      SEQUENCE OF     SISPM10403166LACLPortConfEntry
               MAX-ACCESS  not-accessible
               STATUS      current
               DESCRIPTION
                   "The ACL Port Conf Table.
                    INDEX for this table is ifIndex which is
                    equivalent to the panel port number."
               ::= {     sispm10403166lACL 1 }

    sispm10403166lACLPortConfEntry OBJECT-TYPE
               SYNTAX          SISPM10403166LACLPortConfEntry
               MAX-ACCESS  not-accessible
               STATUS      current
               DESCRIPTION
                   "The ACL Port Conf Entry. "
               INDEX    {     ifIndex  }
               ::= {     sispm10403166lACLPortConfTable 1 }

    SISPM10403166LACLPortConfEntry             ::=
            SEQUENCE {
                 sispm10403166lACLPortConfPolicyID        Integer32,
                 sispm10403166lACLPortConfAction          INTEGER,
                 sispm10403166lACLPortConfRateLimiterID   Integer32,
                 sispm10403166lACLPortConfPortRedirect    Integer32,
                 sispm10403166lACLPortConfMirror          AdminMode,
                 sispm10403166lACLPortConfLogging         AdminMode,
                 sispm10403166lACLPortConfShutdown        AdminMode,
                 sispm10403166lACLPortConfState           AdminMode,
                 sispm10403166lACLPortConfCounter         Counter32
                 }

    sispm10403166lACLPortConfPolicyID OBJECT-TYPE
               SYNTAX       Integer32 (0..127)
               MAX-ACCESS   read-write
               STATUS       current
               DESCRIPTION
                   "The policy to apply to this port.
                    default: 0, range : 0 - 127. "
               ::= {     sispm10403166lACLPortConfEntry 2 }

    sispm10403166lACLPortConfAction OBJECT-TYPE
               SYNTAX      INTEGER { deny(0), permit(1) }
               MAX-ACCESS  read-write
               STATUS      current
               DESCRIPTION
                   "Whether forwarding is permitted ('Permit') or denied ('Deny').
                    default: 1,
                    0: Deny,
                    1: Permit."
               ::= {     sispm10403166lACLPortConfEntry 3 }

    sispm10403166lACLPortConfRateLimiterID OBJECT-TYPE
               SYNTAX      Integer32 (0..16)
               MAX-ACCESS  read-write
               STATUS      current
               DESCRIPTION
                   "The rate limiter to apply on this port.
                    0: Disable,
                    range : 0 - 16. "
               ::= {     sispm10403166lACLPortConfEntry 4 }

    sispm10403166lACLPortConfPortRedirect OBJECT-TYPE
               SYNTAX      Integer32 (0..4095)
               MAX-ACCESS  read-write
               STATUS      current
               DESCRIPTION
                   "Port frames are redirected on.
                    0: Disable,
                    range : 0 - end port number. "
               ::= {     sispm10403166lACLPortConfEntry 5 }

    sispm10403166lACLPortConfMirror OBJECT-TYPE
               SYNTAX      AdminMode
               MAX-ACCESS  read-write
               STATUS      current
               DESCRIPTION
                   "The mirror operation of this port."
               ::= {     sispm10403166lACLPortConfEntry 6 }

    sispm10403166lACLPortConfLogging OBJECT-TYPE
               SYNTAX      AdminMode
               MAX-ACCESS  read-write
               STATUS      current
               DESCRIPTION
                   "Specify the logging operation of this port."
               ::= {     sispm10403166lACLPortConfEntry 7 }

    sispm10403166lACLPortConfShutdown OBJECT-TYPE
               SYNTAX      AdminMode
               MAX-ACCESS  read-write
               STATUS      current
               DESCRIPTION
                   "Specify the port shut down operation of this port."
               DEFVAL  { disable }
               ::= {     sispm10403166lACLPortConfEntry 8 }

    sispm10403166lACLPortConfState OBJECT-TYPE
               SYNTAX      AdminMode
               MAX-ACCESS  read-write
               STATUS      current
               DESCRIPTION
                   "Specify the port state of this port."
               DEFVAL  { enable }
               ::= {     sispm10403166lACLPortConfEntry 9 }

    sispm10403166lACLPortConfCounter OBJECT-TYPE
               SYNTAX      Counter32
               MAX-ACCESS  read-only
               STATUS      current
               DESCRIPTION
                   "Counts the number of frames that match this ACE. "
               ::= {     sispm10403166lACLPortConfEntry 10 }

--
-- =======================================================================================================================
-- Start sispm10403166lACLRateLimiter group
-- =======================================================================================================================
--sispm10403166lACLRateLimiterTable

    sispm10403166lACLRateLimiterTable OBJECT-TYPE
               SYNTAX      SEQUENCE OF     SISPM10403166LACLRateLimiterEntry
               MAX-ACCESS  not-accessible
               STATUS      current
               DESCRIPTION
                   "The ACL Rate Limiter Table."
               ::= {     sispm10403166lACL 2 }

    sispm10403166lACLRateLimiterEntry OBJECT-TYPE
               SYNTAX          SISPM10403166LACLRateLimiterEntry
               MAX-ACCESS  not-accessible
               STATUS      current
               DESCRIPTION
                   "The ACL Rate Limiter Entry. "
               INDEX    {     sispm10403166lACLRateLimiterID  }
               ::= {     sispm10403166lACLRateLimiterTable 1 }

    SISPM10403166LACLRateLimiterEntry             ::= SEQUENCE {
                 sispm10403166lACLRateLimiterID       Integer32,
                 sispm10403166lACLRateLimiterRate     Integer32,
                 sispm10403166lACLRateLimiterUnit     Integer32
                 }

    sispm10403166lACLRateLimiterID OBJECT-TYPE
               SYNTAX      Integer32 (1..16)
               MAX-ACCESS  not-accessible
               STATUS      current
               DESCRIPTION
                   "Rate Limiter ID.
                    range : 1-16 "
               ::= {     sispm10403166lACLRateLimiterEntry 1 }

    sispm10403166lACLRateLimiterRate OBJECT-TYPE
               SYNTAX      Integer32(0..500000)
               MAX-ACCESS  read-write
               STATUS      current
               DESCRIPTION
                   "default: 1,
                    range :
                    <0-500000> 10pps,The valid rate is 0, 10, 20, 30,
                    ..., 5000000 in pps.
                    <0-400000> 25kbps,The valid rate is 0, 25, 50, 75,...,
                    10000000 in kbps."
               ::= {     sispm10403166lACLRateLimiterEntry 2 }

    sispm10403166lACLRateLimiterUnit OBJECT-TYPE
               SYNTAX      Integer32(0|1)
               MAX-ACCESS  read-write
               STATUS      current
               DESCRIPTION
                   "Specify the rate unit.
                    0: 10pps, 1: 25kbps.
                   "
               ::= {     sispm10403166lACLRateLimiterEntry 3 }

--
-- =======================================================================================================================
-- Start sispm10403166lACLACE group
-- =======================================================================================================================
--sispm10403166lACLACEClear

    sispm10403166lACLACEClear OBJECT-TYPE
               SYNTAX      ActivateCmd
               MAX-ACCESS  read-write
               STATUS      current
               DESCRIPTION
                   "Clear all ACE counters."
               ::= {     sispm10403166lACLACE 1 }

--sispm10403166lACLACETable

    sispm10403166lACLACETable OBJECT-TYPE
               SYNTAX      SEQUENCE OF     SISPM10403166LACLACEEntry
               MAX-ACCESS  not-accessible
               STATUS      current
               DESCRIPTION
                   "Create ACL ACE entry. "
               ::= {     sispm10403166lACLACE 2 }

    sispm10403166lACLACEEntry OBJECT-TYPE
               SYNTAX          SISPM10403166LACLACEEntry
               MAX-ACCESS  not-accessible
               STATUS      current
               DESCRIPTION
                   "The ACLACE Table."
               INDEX    {     sispm10403166lACLACEIndex  }
               ::= {     sispm10403166lACLACETable 1 }

    SISPM10403166LACLACEEntry             ::= SEQUENCE {
                 sispm10403166lACLACEIndex                Integer32,
                 sispm10403166lACLACEID                   Integer32,
                 sispm10403166lACLACENextID               Integer32,
--               sispm10403166lACLACELoopUp               AdminMode,
                 sispm10403166lACLACEIngressPort          DisplayString,
                 sispm10403166lACLACEPortPolicyNumber     Integer32,
                 sispm10403166lACLACEPortPolicyBitmask    Integer32,
                 sispm10403166lACLACEFrameType            INTEGER,
                 sispm10403166lACLACEAction               INTEGER,
                 sispm10403166lACLACEFilterPort           DisplayString,
                 sispm10403166lACLACEDenyPortRedirect     DisplayString,
                 sispm10403166lACLACERateLimiter          Integer32,
                 sispm10403166lACLACEMirror               AdminMode,
                 sispm10403166lACLACELogging              AdminMode,
                 sispm10403166lACLACEShutdown             AdminMode,
                 sispm10403166lACLACECounter              Counter32,
                 sispm10403166lACLACEVLAN8021QTagged      INTEGER,
                 sispm10403166lACLACEVLANVID              Integer32,
                 sispm10403166lACLACEVLANTagPriority      Integer32,
                 sispm10403166lACLACESMAC                 DisplayString,
                 sispm10403166lACLACEDMACType             INTEGER,
                 sispm10403166lACLACEDMAC                 DisplayString,
                 sispm10403166lACLACEEtherType            Integer32,
                 sispm10403166lACLACEArpOpCode            INTEGER,
                 sispm10403166lACLACEArpFlagsRequestReply INTEGER,
                 sispm10403166lACLACEArpFlagsArpSMac      INTEGER,
                 sispm10403166lACLACEArpFlagsRarpDmac     INTEGER,
                 sispm10403166lACLACEArpFlagsLength       INTEGER,
                 sispm10403166lACLACEArpFlagsIp           INTEGER,
                 sispm10403166lACLACEArpFlagsEthernet     INTEGER,
                 sispm10403166lACLACESIPType              INTEGER,
                 sispm10403166lACLACESIPIPAddress         IpAddress,
                 sispm10403166lACLACESIPIPMask            IpAddress,
                 sispm10403166lACLACEDIPType              INTEGER,
                 sispm10403166lACLACEDIPIPAddress         IpAddress,
                 sispm10403166lACLACEDIPIPMask            IpAddress,
                 sispm10403166lACLACEIPProtocol           INTEGER,
                 sispm10403166lACLACEIPProtocolValue      Integer32,
                 sispm10403166lACLACEIPFlagsTTL           INTEGER,
                 sispm10403166lACLACEIPFlagsFragment      INTEGER,
                 sispm10403166lACLACEIPFlagsOptions       INTEGER,
                 sispm10403166lACLACEICMPType             Integer32,
                 sispm10403166lACLACEICMPCode             Integer32,
                 sispm10403166lACLACESourcePort           DisplayString,
                 sispm10403166lACLACEDestPort             DisplayString,
                 sispm10403166lACLACETCPFlagsFin          INTEGER,
                 sispm10403166lACLACETCPFlagsSyn          INTEGER,
                 sispm10403166lACLACETCPFlagsRst          INTEGER,
                 sispm10403166lACLACETCPFlagsPsh          INTEGER,
                 sispm10403166lACLACETCPFlagsAck          INTEGER,
                 sispm10403166lACLACETCPFlagsUrg          INTEGER,
                 sispm10403166lACLACEIPv6SIPAddress       DisplayString,
                 sispm10403166lACLACEIPv6SIPBitmask       DisplayString,
                 sispm10403166lACLACEIPv6HopLimit         INTEGER,
                 sispm10403166lACLACERowStatus            RowStatus
                 }

    sispm10403166lACLACEIndex OBJECT-TYPE
               SYNTAX      Integer32(1..256)
               MAX-ACCESS  not-accessible
               STATUS      current
               DESCRIPTION
                   "The index. "
               ::= {     sispm10403166lACLACEEntry 1 }

    sispm10403166lACLACEID OBJECT-TYPE
               SYNTAX      Integer32(1..256)
               MAX-ACCESS  read-create
               STATUS      current
               DESCRIPTION
                   "If the ACE ID is specified and an entry with this ACE ID
                    already exists, the ACE will be modified. Otherwise, a
                    new ACE will be added.
                    range : 1 - 256. "
               ::= {     sispm10403166lACLACEEntry 2 }

    sispm10403166lACLACENextID OBJECT-TYPE
               SYNTAX      Integer32 (0..256)
               MAX-ACCESS  read-create
               STATUS      current
               DESCRIPTION
                   "If the next ACE ID is non zero, the ACE will be placed
                    before this ACE in the list. If the next ACE ID is zero,
                    the ACE will be placed last in the list.
                    range : 0 - 256. "
               ::= {     sispm10403166lACLACEEntry 3 }

--    sispm10403166lACLACELoopUp OBJECT-TYPE
--               SYNTAX      AdminMode
--               MAX-ACCESS  read-create
--               STATUS      current
--               DESCRIPTION
--                   "Specify the second lookup operation of the ACE."
--               ::= {     sispm10403166lACLACEEntry 4 }
--
    sispm10403166lACLACEIngressPort OBJECT-TYPE
               SYNTAX      DisplayString
               MAX-ACCESS  read-create
               STATUS      current
               DESCRIPTION
                   "Indicates the ingress port of the ACE. Possible values are:
                    0: All,The ACE will match all ingress port.
                    Port n: The ACE will match a specific ingress port."
               ::= {     sispm10403166lACLACEEntry 5 }

    sispm10403166lACLACEPortPolicyNumber OBJECT-TYPE
               SYNTAX      Integer32(0..127)
               MAX-ACCESS  read-create
               STATUS      current
               DESCRIPTION
                   "policy value.
                    range : 0 - 127.
                    0: Any."
               ::= {     sispm10403166lACLACEEntry 6 }

    sispm10403166lACLACEPortPolicyBitmask OBJECT-TYPE
               SYNTAX      Integer32(0..127)
               MAX-ACCESS  read-create
               STATUS      current
               DESCRIPTION
                   "When 'Specific' is selected for the policy filter,
                    you can enter a specific policy bitmask.
                    range : 0 - 127, 0: no data."
               ::= {     sispm10403166lACLACEEntry 7 }

    sispm10403166lACLACEFrameType OBJECT-TYPE
               SYNTAX      INTEGER {   any(0), etype(1), arp(2),
                                       ipv4(3), ipv6(4) }
               MAX-ACCESS  read-create
               STATUS      current
               DESCRIPTION
                   "Select the frame type for this ACE.
                    When change the type Related oid will set default.
                    0: any,
                    1: etype,
                    2: arp,
                    3: ipv4,
                    4: ipv6."
               ::= {     sispm10403166lACLACEEntry 8 }

    sispm10403166lACLACEAction OBJECT-TYPE
               SYNTAX      INTEGER { deny(0), permit(1), filter(2) }
               MAX-ACCESS  read-create
               STATUS      current
               DESCRIPTION
                   "0: Deny
				    1: Permit
					2: Filter"
               ::= {     sispm10403166lACLACEEntry 9 }

    sispm10403166lACLACEFilterPort OBJECT-TYPE
               SYNTAX      DisplayString
               MAX-ACCESS  read-create
               STATUS      current
               DESCRIPTION
                   "When 'Action' is 'Filter' can set.
                    0: Disable,
                    Port n: The ACE applies to this port number, where n is
                    the number of the switch port.
                    range: 0 - Port number.
                   "
               ::= {     sispm10403166lACLACEEntry 10 }

    sispm10403166lACLACEDenyPortRedirect OBJECT-TYPE
               SYNTAX      DisplayString
               MAX-ACCESS  read-create
               STATUS      current
               DESCRIPTION
                   "Frames that hit the ACE are redirected to the port
                    number specified here.Disabled,indicates that the port
                    redirect operation is disabled.
                    When 'Action' is 'Deny' can set.
                    0: disabled,
                    Port no: The ACE applies to this port number, where n is
                    the number of the switch port."
               ::= {     sispm10403166lACLACEEntry 11 }

    sispm10403166lACLACERateLimiter OBJECT-TYPE
               SYNTAX      Integer32(0..16)
               MAX-ACCESS  read-create
               STATUS      current
               DESCRIPTION
                   "default: 0,
                    0: Disable
                    range : 0 - 16 "
               ::= {     sispm10403166lACLACEEntry 12 }

    sispm10403166lACLACEMirror OBJECT-TYPE
               SYNTAX      AdminMode
               MAX-ACCESS  read-create
               STATUS      current
               DESCRIPTION
                   "default: 0,
                    0: disable - Frames matching the ACE are not mirrored.
                    1: enable - Frames matching the ACE are mirrored.
                   "
               ::= {     sispm10403166lACLACEEntry 13 }

    sispm10403166lACLACELogging OBJECT-TYPE
               SYNTAX      AdminMode
               MAX-ACCESS  read-create
               STATUS      current
               DESCRIPTION
                   "default: 0,
                    0: disable - Frames matching the ACE are not logged.
                    1: enable - Frames matching the ACE are stored in the
                   system log."
               ::= {     sispm10403166lACLACEEntry 14 }

    sispm10403166lACLACEShutdown OBJECT-TYPE
               SYNTAX      AdminMode
               MAX-ACCESS  read-create
               STATUS      current
               DESCRIPTION
                   "default: 0,
                    0: disable - Port shut down is disabled for the AC.
                    1: enable - If a frame matches the ACE, the ingress port
                    will be disabled."
               ::= {     sispm10403166lACLACEEntry 15 }

    sispm10403166lACLACECounter OBJECT-TYPE
               SYNTAX      Counter32
               MAX-ACCESS  read-only
               STATUS      current
               DESCRIPTION
                   "The counter indicates the number of times the ACE was
                    hit by a frame. "
               ::= {     sispm10403166lACLACEEntry 16 }

    sispm10403166lACLACEVLAN8021QTagged OBJECT-TYPE
               SYNTAX      INTEGER { disable(0), enable(1), any(2) }
               MAX-ACCESS  read-create
               STATUS      current
               DESCRIPTION
                   "Specify whether frames can hit the action according to
                    the 802.1Q tagged.
                    default: 2,
                    0: disable - Untagged frame only.
                    1: enable - Tagged frame only.
                    2: Any - Any value is allowed.
                    "
               ::= {     sispm10403166lACLACEEntry 17 }

    sispm10403166lACLACEVLANVID OBJECT-TYPE
               SYNTAX      Integer32(0..4095)
               MAX-ACCESS  read-create
               STATUS      current
               DESCRIPTION
                   "Specify the VLAN ID filter for this ACE.
                    The vid can't be set when 802.1Q Tagged is disabled.
                    default: 0,
                    0: Any - No VLAN ID filter is specified.
                    range : 0 - 4095 "
               ::= {     sispm10403166lACLACEEntry 18 }

    sispm10403166lACLACEVLANTagPriority OBJECT-TYPE
               SYNTAX      Integer32(0..14)
               MAX-ACCESS  read-create
               STATUS      current
               DESCRIPTION
                   "Specify the tag priority for this ACE.
                    The tag priority can't be set when 802.1Q Tagged is disabled.
                    range: 0-14
					0:0
					1:1
					2:2
					3:3
					4:4
					5:5
					6:6
					7:7
					8:0-1
					9:2-3
					10:4-5
					11:6-7
					12:0-3
					13:4-7
					14:Any
					"
               ::= {     sispm10403166lACLACEEntry 19 }

    sispm10403166lACLACESMAC OBJECT-TYPE
               SYNTAX      DisplayString
               MAX-ACCESS  read-create
               STATUS      current
               DESCRIPTION
                   "Configure source MAC address for this ACE.
                    <mac-address>: A frame that hits this ACE matches this
                    source MAC address value. xx-xx-xx-xx-xx-xx.
                    Any: Don't care."
               ::= {    sispm10403166lACLACEEntry 20 }

    sispm10403166lACLACEDMACType OBJECT-TYPE
               SYNTAX      INTEGER { any(0), mc(1), bc(2), uc(3) ,
                                     macAddress(4) , noData(5) }
               MAX-ACCESS  read-create
               STATUS      current
               DESCRIPTION
                   "DMAC Type.
                    default: 0,
                    0: Any - Don't care.
                    1: Multicast - Frame must be multicast.
                    2: Broadcast - Frame must be broadcast.
                    3: Unicast - Frame must be unicast.
                    4: mac address.
                    5: no data."
               DEFVAL  { any }
               ::= {    sispm10403166lACLACEEntry 21 }

    sispm10403166lACLACEDMAC OBJECT-TYPE
               SYNTAX      DisplayString
               MAX-ACCESS  read-create
               STATUS      current
               DESCRIPTION
                   "Configure destination MAC address for this ACE.
                    <mac-address>: A frame that hits this ACE matches this
                    destination MAC address value. xx-xx-xx-xx-xx-xx."
               ::= {     sispm10403166lACLACEEntry 22 }

    sispm10403166lACLACEEtherType OBJECT-TYPE
               SYNTAX      Integer32(-1..65535)
               MAX-ACCESS  read-create
               STATUS      current
               DESCRIPTION
                   "0: Any
				   range : 0, or 1536(0x0600) - 65535(0xffff) but excluding 0x0800(IPv4) 0x0806(ARP) and
                    0x86DD(IPv6).
                    -1: No data. "
               ::= {     sispm10403166lACLACEEntry 23 }

    sispm10403166lACLACEArpOpCode OBJECT-TYPE
               SYNTAX      INTEGER { any(0), arp(1), rarp(2),
                                     other(3), noData(4) }
               MAX-ACCESS  read-create
               STATUS      current
               DESCRIPTION
                   "Configure ARP opcode for this ACE.
                    default: 0,
                    0: Any - Don't care.
                    1: arp.
                    2: rarp.
                    3: other.
                    4: No data."
               DEFVAL  { any }
               ::= {     sispm10403166lACLACEEntry 24 }

    sispm10403166lACLACEArpFlagsRequestReply OBJECT-TYPE
               SYNTAX      INTEGER { reply(0), request(1), any(2), noData(3)}
               MAX-ACCESS  read-create
               STATUS      current
               DESCRIPTION
                   "Specify the available ARP/RARP opcode (OP) flag for this ACE.
                    default: 2,
                    0: Frame must have ARP Reply or RARP Reply OP flag.
                    1: Frame must have ARP Request or RARP Request OP flag set.
                    2: Any - Don't care.
                    3: No data."
               DEFVAL  { any }
               ::= {     sispm10403166lACLACEEntry 25 }

    sispm10403166lACLACEArpFlagsArpSMac OBJECT-TYPE
               SYNTAX      INTEGER { notEqualSMAC(0), equalSMAC(1),
                                     any(2), noData(3)}
               MAX-ACCESS  read-create
               STATUS      current
               DESCRIPTION
                   "Specify whether frames can hit the action according to their
                    sender hardware address field (SHA) settings.
                    default: 2,
                    0: ARP frames where SHA is not equal to the SMAC address.
                    1: ARP frames where SHA is equal to the SMAC address.
                    2: Any - Don't care.
                    3: No data."
               DEFVAL  { any }
               ::= {     sispm10403166lACLACEEntry 26 }

    sispm10403166lACLACEArpFlagsRarpDmac OBJECT-TYPE
               SYNTAX      INTEGER { notEqualDMAC(0), equalDMAC(1),
                                     any(2), noData(3)}
               MAX-ACCESS  read-create
               STATUS      current
               DESCRIPTION
                   "Specify whether frames can hit the action according to
                    their target hardware address field (THA) settings.
                    default: 2,
                    0: RARP frames where THA is not equal to the DMAC address.
                    1: RARP frames where THA is equal to the DMAC address.
                    2: Any - Don't care.
                    3: No data."
               DEFVAL  { any }
               ::= {     sispm10403166lACLACEEntry 27 }

    sispm10403166lACLACEArpFlagsLength OBJECT-TYPE
               SYNTAX      INTEGER { notEqualEthIpV4 (0), equalEthIpV4(1),
                                     any(2), noData(3)}
               MAX-ACCESS  read-create
               STATUS      current
               DESCRIPTION
                   "Specify whether frames can hit the action according to
                    their ARP/RARP hardware address length (HLN) and protocol
                    address length (PLN) settings.
                    default: 2,
                    0: ARP/RARP frames where the HLN is not equal to
                    Ethernet(0x06) or the (PLN) is not equal to IPv4(0x04).
                    1: ARP/RARP frames where the HLN is equal to Ethernet (0x06)
                    and the (PLN) is equal to IPv4(0x04).
                    2: Any - Don't care.
                    3: No data."
                DEFVAL  { any }
                ::= {     sispm10403166lACLACEEntry 28 }

    sispm10403166lACLACEArpFlagsIp OBJECT-TYPE
               SYNTAX      INTEGER { notEqualEth(0), equalEth(1),
                                     any(2), noData(3)}
               MAX-ACCESS  read-create
               STATUS      current
               DESCRIPTION
                   "Specify whether frames can hit the action according to
                    their ARP/RARP hardware address space (HRD) settings.
                    default: 2,
                    0: ARP/RARP frames where the HLD is not equal to Ethernet(1).
                    1: ARP/RARP frames where the HLD is equal to Ethernet(1).
                    2: Any - Don't care.
                    3: No data."
               DEFVAL  { any }
               ::= {     sispm10403166lACLACEEntry 29 }

    sispm10403166lACLACEArpFlagsEthernet OBJECT-TYPE
               SYNTAX      INTEGER { notEqualIp(0), equalIp(1),
                                     any(2), noData(3)}
               MAX-ACCESS  read-create
               STATUS      current
               DESCRIPTION
                   "Specify whether frames can hit the action
                    according to their ARP/RARP protocol address space (PRO) settings.
                    default: 2,
                    0: ARP/RARP frames where the PRO is not equal to IP\n(0x800).
                    1: ARP/RARP frames where the PRO is equal to IP(0x800).
                    2: Any - Don't care.
                    3: No data."
               DEFVAL  { any }
               ::= {     sispm10403166lACLACEEntry 30 }

    sispm10403166lACLACESIPType OBJECT-TYPE
               SYNTAX      INTEGER { any(0), ip(1), network(2), noData(3) }
               MAX-ACCESS  read-create
               STATUS      current
               DESCRIPTION
                   "Configure source IP address for this ACE.
                    default: 0,
                    0: Any - Don't care.
                    1: IP Address.
                    2: Network.
                    3: No data."
               DEFVAL  { any }
               ::= {     sispm10403166lACLACEEntry 31 }

    sispm10403166lACLACESIPIPAddress OBJECT-TYPE
               SYNTAX      IpAddress
               MAX-ACCESS  read-create
               STATUS      current
               DESCRIPTION
                   "A frame that hits this ACE matches this source IP address
                    value."
               ::= {     sispm10403166lACLACEEntry 32 }

    sispm10403166lACLACESIPIPMask OBJECT-TYPE
               SYNTAX      IpAddress
               MAX-ACCESS  read-create
               STATUS      current
               DESCRIPTION
                   "Specific sender IP mask in dotted decimal notation."
               ::= {     sispm10403166lACLACEEntry 33 }

    sispm10403166lACLACEDIPType OBJECT-TYPE
               SYNTAX      INTEGER { any(0), ip(1), network(2), noData(3) }
               MAX-ACCESS  read-create
               STATUS      current
               DESCRIPTION
                   "Configure destination IP address for this ACE.
                    default: 0,
                    0: Any - Don't care.
                    1: IP Address.
                    2: Network.
                    3: No data."
               DEFVAL  { any }
               ::= {     sispm10403166lACLACEEntry 34 }

    sispm10403166lACLACEDIPIPAddress OBJECT-TYPE
               SYNTAX      IpAddress
               MAX-ACCESS  read-create
               STATUS      current
               DESCRIPTION
                   "A frame that hits this ACE matches this destination IP
                    address value."
               ::= {     sispm10403166lACLACEEntry 35 }

    sispm10403166lACLACEDIPIPMask OBJECT-TYPE
               SYNTAX      IpAddress
               MAX-ACCESS  read-create
               STATUS      current
               DESCRIPTION
                   "Specific sender IP mask in dotted decimal notation."
               ::= {     sispm10403166lACLACEEntry 36 }

    sispm10403166lACLACEIPProtocol OBJECT-TYPE
               SYNTAX      INTEGER{ any(0), icmp(1), udp(2), tcp(3),
                                    other(4), noData(5)}
               MAX-ACCESS  read-create
               STATUS      current
               DESCRIPTION
                   "Specify the IP protocol filter for this ACE.
                    default: 0,
                    0: Any,
                    1: ICMP,
                    2: UDP,
                    3: TCP,
                    4: Other,
                    5: no data."
               DEFVAL  { any }
               ::= {     sispm10403166lACLACEEntry 37 }

    sispm10403166lACLACEIPProtocolValue OBJECT-TYPE
               SYNTAX      Integer32(0..256)
               MAX-ACCESS  read-create
               STATUS      current
               DESCRIPTION
                   "Configure IP protocol value for this ACE when IP Protocol
                    is 'other'.
                    default: 256,
                    256: No data.
                    range : 0 - 256"
               ::= {     sispm10403166lACLACEEntry 38 }

    sispm10403166lACLACEIPFlagsTTL OBJECT-TYPE
               SYNTAX      INTEGER { nonZero(0), zero(1), any(2), noData(3) }
               MAX-ACCESS  read-create
               STATUS      current
               DESCRIPTION
                   "Specify the Time-to-Live settings for this ACE.
                    default: 0,
                    0: zero,
                    1: Non-Zero
                    2: Any,,
                    3: No data."
               DEFVAL  { nonZero }
               ::= {     sispm10403166lACLACEEntry 39 }

    sispm10403166lACLACEIPFlagsFragment OBJECT-TYPE
               SYNTAX      INTEGER{yes(0), no(1), any(2), noData(3)}
               MAX-ACCESS  read-create
               STATUS      current
               DESCRIPTION
                   "Specify the fragment offset settings for this ACE.
                    default: 2,
                    0: No,
                    1: Yes,
                    2: Any,
                    3: No data."
               DEFVAL  { any }
               ::= {     sispm10403166lACLACEEntry 40 }

    sispm10403166lACLACEIPFlagsOptions OBJECT-TYPE
               SYNTAX      INTEGER{yes(0), no(1), any(2),  noData(3)}
               MAX-ACCESS  read-create
               STATUS      current
               DESCRIPTION
                   "Specify the options flag setting for this ACE.
                    default: 2,
                    0: No,
                    1: Yes,
                    2: Any,
                    3: No data."
               DEFVAL  { any }
               ::= {     sispm10403166lACLACEEntry 41 }

    sispm10403166lACLACEICMPType OBJECT-TYPE
               SYNTAX      Integer32(0..257)
               MAX-ACCESS  read-create
               STATUS      current
               DESCRIPTION
                   "Configure ICMP type for this ACE.
                    default: 256,
                    256: Any - Don't care.
                    257: No data.
                    range : 0 - 257."
               ::= { sispm10403166lACLACEEntry 42 }

    sispm10403166lACLACEICMPCode OBJECT-TYPE
               SYNTAX      Integer32(0..257)
               MAX-ACCESS  read-create
               STATUS      current
               DESCRIPTION
                   "Configure ICMP code for this ACE.
                    default: 256,
                    256: Any - Don't care.
                    257: No data.
                    range : 0 - 257."
               ::= {     sispm10403166lACLACEEntry 43 }

    sispm10403166lACLACESourcePort OBJECT-TYPE
               SYNTAX      DisplayString
               MAX-ACCESS  read-create
               STATUS      current
               DESCRIPTION
                   "Configure Source UDP/TCP port range for this ACE.
                    default: any,
                    specific: 0~65535,
                    range : 0 - 65535."
               ::= {     sispm10403166lACLACEEntry 44 }

    sispm10403166lACLACEDestPort OBJECT-TYPE
               SYNTAX      DisplayString
               MAX-ACCESS  read-create
               STATUS      current
               DESCRIPTION
                   "Configure Destination UDP/TCP port range for this ACE.
                    default: any,
                    specific: 0~65535,
                    range : 0 - 65535."
               ::= {     sispm10403166lACLACEEntry 45 }

    sispm10403166lACLACETCPFlagsFin OBJECT-TYPE
               SYNTAX      INTEGER { unset(0), set(1), any(2), noData(3) }
               MAX-ACCESS  read-create
               STATUS      current
               DESCRIPTION
                   "Configure TCP (FIN) flags for this ACE.
                    default: 2,
                    0: TCP frames where the FIN field is unset.
                    1: TCP frames where the FIN field is set.
                    2: Any - Don't care.
                    3: No data."
               DEFVAL  { any }
               ::= {     sispm10403166lACLACEEntry 46 }

    sispm10403166lACLACETCPFlagsSyn OBJECT-TYPE
               SYNTAX      INTEGER { unset(0), set(1), any(2), noData(3) }
               MAX-ACCESS  read-create
               STATUS      current
               DESCRIPTION
                   "Configure TCP (SYN) flags for this ACE.
                    default: 2,
                    0: TCP frames where the SYN field is unset.
                    1: TCP frames where the SYN field is set.
                    2: Any - Don't care.
                    3: No data."
               DEFVAL  { any }
               ::= {     sispm10403166lACLACEEntry 47 }

    sispm10403166lACLACETCPFlagsRst OBJECT-TYPE
               SYNTAX      INTEGER { unset(0), set(1), any(2), noData(3) }
               MAX-ACCESS  read-create
               STATUS      current
               DESCRIPTION
                   "Configure TCP (RST) flags for this ACE.
                    default: 2,
                    0: TCP frames where the RST field is unset.
                    1: TCP frames where the RST field is set.
                    2: Any - Don't care.
                    3: No data."
               DEFVAL  { any }
               ::= {     sispm10403166lACLACEEntry 48 }

    sispm10403166lACLACETCPFlagsPsh OBJECT-TYPE
               SYNTAX      INTEGER { unset(0), set(1), any(2), noData(3) }
               MAX-ACCESS  read-create
               STATUS      current
               DESCRIPTION
                   "Configure TCP (PSH) flags for this ACE.
                    default: 2,
                    0: TCP frames where the PSH field is unset.
                    1: TCP frames where the PSH field is set.
                    2: Any - Don't care.
                    3: No data."
               DEFVAL  { any }
               ::= {     sispm10403166lACLACEEntry 49 }

    sispm10403166lACLACETCPFlagsAck OBJECT-TYPE
               SYNTAX      INTEGER { unset(0), set(1), any(2), noData(3) }
               MAX-ACCESS  read-create
               STATUS      current
               DESCRIPTION
                   "Configure TCP (ACK) flags for this ACE.
                    default: 2,
                    0: TCP frames where the ACK field is unset.
                    1: TCP frames where the ACK field is set.
                    2: Any - Don't care.
                    3: No data."
               DEFVAL  { any }
               ::= {     sispm10403166lACLACEEntry 50 }

    sispm10403166lACLACETCPFlagsUrg OBJECT-TYPE
               SYNTAX      INTEGER { unset(0), set(1), any(2), noData(3) }
               MAX-ACCESS  read-create
               STATUS      current
               DESCRIPTION
                   "Configure TCP (URG) flags for this ACE.
                    default: 2,
                    0: TCP frames where the URG field is unset.
                    1: TCP frames where the URG field is set.
                    2: Any - Don't care.
                    3: No data."
               DEFVAL  { any }
               ::= {     sispm10403166lACLACEEntry 51 }

    sispm10403166lACLACEIPv6SIPAddress OBJECT-TYPE
               SYNTAX      DisplayString
               MAX-ACCESS  read-create
               STATUS      current
               DESCRIPTION
                   "When 'Specific' is selected for the source IPv6 filter,
                    you can enter a specific SIPv6 address.
                    The field only supported last 32 bits for IPv6 address. "
               ::= {     sispm10403166lACLACEEntry 52 }

    sispm10403166lACLACEIPv6SIPBitmask OBJECT-TYPE
               SYNTAX      DisplayString
               MAX-ACCESS  read-create
               STATUS      current
               DESCRIPTION
                   "When 'Specific' is selected for the source IPv6 filter,
                    you can enter a specific SIPv6 mask.
                    The field only supported last 32 bits for IPv6 address. "
               ::= {     sispm10403166lACLACEEntry 53 }

    sispm10403166lACLACEIPv6HopLimit OBJECT-TYPE
               SYNTAX      INTEGER { unset(0), set(1), any(2), noData(3) }
               MAX-ACCESS  read-create
               STATUS      current
               DESCRIPTION
                   "Specify the hop limit settings for this ACE.
                    default: 2,
                    0: Where the Hop Limit field is unset.
                    1: Where the Hop Limit field is set.
                    2: Any - Don't care,
                    3: No data."
               DEFVAL  { any }
               ::= {     sispm10403166lACLACEEntry 54 }

    sispm10403166lACLACERowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sispm10403166lACLACEEntry 56 }

--
-- =======================================================================================================================
-- Start sispm10403166lACLStatus group
-- =======================================================================================================================
--sispm10403166lACLStatusTable

    sispm10403166lACLStatusTable OBJECT-TYPE
               SYNTAX      SEQUENCE OF     SISPM10403166LACLStatusEntry
               MAX-ACCESS  not-accessible
               STATUS      current
               DESCRIPTION
                   " ACL ACE Status entry. "
               ::= {     sispm10403166lACL 4 }

    sispm10403166lACLStatusEntry OBJECT-TYPE
               SYNTAX          SISPM10403166LACLStatusEntry
               MAX-ACCESS  not-accessible
               STATUS      current
               DESCRIPTION
                   "The ACL Status Entry."
               INDEX    {    sispm10403166lACLStatusIndex  }
               ::= {     sispm10403166lACLStatusTable 1 }

    SISPM10403166LACLStatusEntry             ::= SEQUENCE {
                 sispm10403166lACLStatusIndex          Integer32,
                 sispm10403166lACLStatusUser           DisplayString,
                 sispm10403166lACLStatusID             Integer32,
                 sispm10403166lACLStatusIngressPort    DisplayString,
                 sispm10403166lACLStatusFrameType      DisplayString,
                 sispm10403166lACLStatusAction         DisplayString,
                 sispm10403166lACLStatusRateLimiter    DisplayString,
                 sispm10403166lACLStatusPortRedirect   DisplayString,
                 sispm10403166lACLStatusMirror         DisplayString,
                 sispm10403166lACLStatusCPU            DisplayString,
                 sispm10403166lACLStatusCPUOnce        DisplayString,
                 sispm10403166lACLStatusCounter        Counter32,
                 sispm10403166lACLStatusConflict       DisplayString
                 }

    sispm10403166lACLStatusIndex OBJECT-TYPE
               SYNTAX      Integer32(1..256)
               MAX-ACCESS  not-accessible
               STATUS      current
               DESCRIPTION
                   "The ACL status index. "
               ::= {     sispm10403166lACLStatusEntry 1 }

    sispm10403166lACLStatusUser OBJECT-TYPE
               SYNTAX      DisplayString
               MAX-ACCESS  read-only
               STATUS      current
               DESCRIPTION
                   "Indicates the ACL user.
                    S : Static,
                    IPMG : IP Management,
                    IPSG : IP Source Guard,
                    IPMC : IPMC,
                    ARPI : Arp Inspection,
                    UPnP : UPnP,
                    DHCP : DHCP. "
               ::= {     sispm10403166lACLStatusEntry 2 }

    sispm10403166lACLStatusID OBJECT-TYPE
               SYNTAX      Integer32(1..256)
               MAX-ACCESS  read-only
               STATUS      current
               DESCRIPTION
                   "ACE ID.
                    range : 1 - 256. "
               ::= {     sispm10403166lACLStatusEntry 3 }

    sispm10403166lACLStatusIngressPort OBJECT-TYPE
               SYNTAX      DisplayString
               MAX-ACCESS  read-only
               STATUS      current
               DESCRIPTION
                   "Indicates the ingress port of the ACE. Possible values are:
                    All: The ACE will match all ingress port.
                    Port: The ACE will match a specific ingress port. "
               ::= {     sispm10403166lACLStatusEntry 4 }

    sispm10403166lACLStatusFrameType OBJECT-TYPE
               SYNTAX      DisplayString
               MAX-ACCESS  read-only
               STATUS      current
               DESCRIPTION
                   "Indicates the frame type of the ACE.
                    Any: The ACE will match any frame type.
                    EType: The ACE will match Ethernet Type frames.
                    Note that an Ethernet Type based ACE will not get matched
                    by IP and ARP frames.
                    ARP: The ACE will match ARP/RARP frames.
                    IPv4: The ACE will match all IPv4 frames.
                    IPv4/ICMP: The ACE will match IPv4 frames with ICMP protocol.
                    IPv4/UDP: The ACE will match IPv4 frames with UDP protocol.
                    IPv4/TCP: The ACE will match IPv4 frames with TCP protocol.
                    IPv4/Other: The ACE will match IPv4 frames, which are not
                    ICMP/UDP/TCP.
                    IPv6: The ACE will match all IPv6 standard frames. "
               ::= {     sispm10403166lACLStatusEntry 5 }

    sispm10403166lACLStatusAction OBJECT-TYPE
               SYNTAX      DisplayString
               MAX-ACCESS  read-only
               STATUS      current
               DESCRIPTION
                   "Indicates the forwarding action of the ACE. "
               ::= {     sispm10403166lACLStatusEntry 6 }

    sispm10403166lACLStatusRateLimiter OBJECT-TYPE
               SYNTAX      DisplayString
               MAX-ACCESS  read-only
               STATUS      current
               DESCRIPTION
                   "Indicates the rate limiter number of the ACE. "
               ::= {     sispm10403166lACLStatusEntry 7 }

    sispm10403166lACLStatusPortRedirect OBJECT-TYPE
               SYNTAX      DisplayString
               MAX-ACCESS  read-only
               STATUS      current
               DESCRIPTION
                   "Indicates the port redirect operation of the ACE.
                    Frames matching the ACE are redirected to the port number. "
               ::= {     sispm10403166lACLStatusEntry 8 }

    sispm10403166lACLStatusMirror OBJECT-TYPE
               SYNTAX      DisplayString
               MAX-ACCESS  read-only
               STATUS      current
               DESCRIPTION
                   "Specify the mirror operation of this port."
               ::= {     sispm10403166lACLStatusEntry 9 }

    sispm10403166lACLStatusCPU OBJECT-TYPE
               SYNTAX      DisplayString
               MAX-ACCESS  read-only
               STATUS      current
               DESCRIPTION
                   "Forward packet that matched the specific ACE to CPU. "
               ::= {     sispm10403166lACLStatusEntry 10 }

    sispm10403166lACLStatusCPUOnce OBJECT-TYPE
               SYNTAX      DisplayString
               MAX-ACCESS  read-only
               STATUS      current
               DESCRIPTION
                   "Forward first packet that matched the specific ACE to CPU. "
               ::= {     sispm10403166lACLStatusEntry 11 }

    sispm10403166lACLStatusCounter OBJECT-TYPE
               SYNTAX      Counter32
               MAX-ACCESS  read-only
               STATUS      current
               DESCRIPTION
                   "The counter indicates the number of times the ACE was hit
                    by a frame. "
               ::= {     sispm10403166lACLStatusEntry 12 }

    sispm10403166lACLStatusConflict OBJECT-TYPE
               SYNTAX      DisplayString
               MAX-ACCESS  read-only
               STATUS      current
               DESCRIPTION
                   "Indicates the hardware status of the specific ACE.
                    The specific ACE is not applied to the hardware due to
                    hardware limitations. "
               ::= {     sispm10403166lACLStatusEntry 13 }


-- =======================================================================================================================
-- sispm10403166lAclConformance
-- =======================================================================================================================
sispm10403166lAclConformance OBJECT IDENTIFIER ::= { sispm10403166lACL 200 }

sispm10403166lAclCompliances OBJECT IDENTIFIER ::= { sispm10403166lAclConformance 1 }

sispm10403166lAclGroups    OBJECT IDENTIFIER ::= { sispm10403166lAclConformance 2 }

sispm10403166lACLPortConfGroup OBJECT-GROUP
    OBJECTS {
                -- sispm10403166lACLPortConfTable
                 sispm10403166lACLPortConfPolicyID,
                 sispm10403166lACLPortConfAction,
                 sispm10403166lACLPortConfRateLimiterID,
                 sispm10403166lACLPortConfPortRedirect,
                 sispm10403166lACLPortConfMirror,
                 sispm10403166lACLPortConfLogging,
                 sispm10403166lACLPortConfShutdown,
                 sispm10403166lACLPortConfState,
                 sispm10403166lACLPortConfCounter
            }
     STATUS  current
     DESCRIPTION
            "The collection of objects which are used to indicate
            sispm10403166l ACL information."
    ::= { sispm10403166lAclGroups 1 }

sispm10403166lACLRateLimiterGroup OBJECT-GROUP
    OBJECTS {
                -- sispm10403166lACLRateLimiterTable
                 sispm10403166lACLRateLimiterRate,
                 sispm10403166lACLRateLimiterUnit
            }
     STATUS  current
     DESCRIPTION
            "The collection of objects which are used to indicate
            sispm10403166l ACL information."
    ::= { sispm10403166lAclGroups 2 }

sispm10403166lACLACEGroup OBJECT-GROUP
    OBJECTS {
                -- sispm10403166lACLACEClear
                 sispm10403166lACLACEClear,

                -- sispm10403166lACLACETable
                 sispm10403166lACLACEID,
                 sispm10403166lACLACENextID,
--               sispm10403166lACLACELoopUp,
                 sispm10403166lACLACEIngressPort,
                 sispm10403166lACLACEPortPolicyNumber,
                 sispm10403166lACLACEPortPolicyBitmask,
                 sispm10403166lACLACEFrameType,
                 sispm10403166lACLACEAction,
                 sispm10403166lACLACEFilterPort,
                 sispm10403166lACLACEDenyPortRedirect,
                 sispm10403166lACLACERateLimiter,
                 sispm10403166lACLACEMirror,
                 sispm10403166lACLACELogging,
                 sispm10403166lACLACEShutdown,
                 sispm10403166lACLACECounter,
                 sispm10403166lACLACEVLAN8021QTagged,
                 sispm10403166lACLACEVLANVID,
                 sispm10403166lACLACEVLANTagPriority,
                 sispm10403166lACLACESMAC,
                 sispm10403166lACLACEDMACType,
                 sispm10403166lACLACEDMAC,
                 sispm10403166lACLACEEtherType,
                 sispm10403166lACLACEArpOpCode,
                 sispm10403166lACLACEArpFlagsRequestReply,
                 sispm10403166lACLACEArpFlagsArpSMac,
                 sispm10403166lACLACEArpFlagsRarpDmac,
                 sispm10403166lACLACEArpFlagsLength,
                 sispm10403166lACLACEArpFlagsIp,
                 sispm10403166lACLACEArpFlagsEthernet,
                 sispm10403166lACLACESIPType,
                 sispm10403166lACLACESIPIPAddress,
                 sispm10403166lACLACESIPIPMask,
                 sispm10403166lACLACEDIPType,
                 sispm10403166lACLACEDIPIPAddress,
                 sispm10403166lACLACEDIPIPMask,
                 sispm10403166lACLACEIPProtocol,
                 sispm10403166lACLACEIPProtocolValue,
                 sispm10403166lACLACEIPFlagsTTL,
                 sispm10403166lACLACEIPFlagsFragment,
                 sispm10403166lACLACEIPFlagsOptions,
                 sispm10403166lACLACEICMPType,
                 sispm10403166lACLACEICMPCode,
                 sispm10403166lACLACESourcePort,
                 sispm10403166lACLACEDestPort,
                 sispm10403166lACLACETCPFlagsFin,
                 sispm10403166lACLACETCPFlagsSyn,
                 sispm10403166lACLACETCPFlagsRst,
                 sispm10403166lACLACETCPFlagsPsh,
                 sispm10403166lACLACETCPFlagsAck,
                 sispm10403166lACLACETCPFlagsUrg,
                 sispm10403166lACLACEIPv6SIPAddress,
                 sispm10403166lACLACEIPv6SIPBitmask,
                 sispm10403166lACLACEIPv6HopLimit,
                 sispm10403166lACLACERowStatus
            }
     STATUS  current
     DESCRIPTION
            "The collection of objects which are used to indicate
            sispm10403166l ACL information."
    ::= { sispm10403166lAclGroups 3 }

sispm10403166lACLStatusGroup OBJECT-GROUP
    OBJECTS {
                -- sispm10403166lACLStatusTable
                 sispm10403166lACLStatusUser,
                 sispm10403166lACLStatusID,
                 sispm10403166lACLStatusIngressPort,
                 sispm10403166lACLStatusFrameType,
                 sispm10403166lACLStatusAction,
                 sispm10403166lACLStatusRateLimiter,
                 sispm10403166lACLStatusPortRedirect,
                 sispm10403166lACLStatusMirror,
                 sispm10403166lACLStatusCPU,
                 sispm10403166lACLStatusCPUOnce,
                 sispm10403166lACLStatusCounter,
                 sispm10403166lACLStatusConflict
            }
     STATUS  current
     DESCRIPTION
            "The collection of objects which are used to indicate
            sispm10403166l ACL information."
    ::= { sispm10403166lAclGroups 4 }


-- =======================================================================================================================
-- =======================================================================================================================
 -- RowStatus Info:  createAndGo, notReady not supported.
-- =======================================================================================================================
-- Textual Conventions for the sispm10403166l Qos Mib
-- =======================================================================================================================
--
sispm10403166lQosConf                    OBJECT IDENTIFIER ::= { sispm10403166lConfiguration 10 }
    sispm10403166lQos                        OBJECT IDENTIFIER   ::= { sispm10403166lQosConf  1  }
    sispm10403166lQosPortClassification      OBJECT IDENTIFIER   ::= { sispm10403166lQos 1 }
    sispm10403166lQosPortPolicing            OBJECT IDENTIFIER   ::= { sispm10403166lQos 2 }
--  sispm10403166lQosQueuePolicing           OBJECT IDENTIFIER   ::= { sispm10403166lQos 3 }
--  sispm10403166lQosPortScheduler           OBJECT IDENTIFIER   ::= { sispm10403166lQos 4 }
    sispm10403166lQosEgressPortPCPRemarking  OBJECT IDENTIFIER   ::= { sispm10403166lQos 6 }
    sispm10403166lQosPortDSCP                OBJECT IDENTIFIER   ::= { sispm10403166lQos 7 }
    sispm10403166lQosDSCPBasedQoS            OBJECT IDENTIFIER   ::= { sispm10403166lQos 8 }
    sispm10403166lQosDSCPTranslation         OBJECT IDENTIFIER   ::= { sispm10403166lQos 9 }
    sispm10403166lQosDSCPClassification      OBJECT IDENTIFIER   ::= { sispm10403166lQos 10 }
    sispm10403166lQosControlList             OBJECT IDENTIFIER   ::= { sispm10403166lQos 11 }
    sispm10403166lQosStormControl            OBJECT IDENTIFIER   ::= { sispm10403166lQos 12 }
    sispm10403166lQosPortStormControl        OBJECT IDENTIFIER   ::= { sispm10403166lQos 13 }
    sispm10403166lQosWRED                    OBJECT IDENTIFIER   ::= { sispm10403166lQos 14 }
    sispm10403166lQosQCLStatus               OBJECT IDENTIFIER   ::= { sispm10403166lQos 15 }
    sispm10403166lQosPortShapers             OBJECT IDENTIFIER   ::= { sispm10403166lQos 16 }
    sispm10403166lQosPortSchedulers          OBJECT IDENTIFIER   ::= { sispm10403166lQos 17 }
--
-- =======================================================================================================================
-- Start sispm10403166lQosPortClassification group
-- =======================================================================================================================
--sispm10403166lQosPortClassificationTable

     sispm10403166lQosPortClassificationTable OBJECT-TYPE
               SYNTAX      SEQUENCE OF     SISPM10403166LQosPortClassificationEntry
               MAX-ACCESS  not-accessible
               STATUS      current
               DESCRIPTION
                   "QoS Ingress Port Classification.
                    INDEX for this table is ifIndex which is
                    equivalent to the panel port number."
               ::= {     sispm10403166lQosPortClassification  1 }

    sispm10403166lQosPortClassificationEntry OBJECT-TYPE
               SYNTAX          SISPM10403166LQosPortClassificationEntry
               MAX-ACCESS  not-accessible
               STATUS      current
               DESCRIPTION
                   "The Qos Port Classification Table."
               INDEX    {     ifIndex  }
               ::= {     sispm10403166lQosPortClassificationTable 1 }

    SISPM10403166LQosPortClassificationEntry             ::= SEQUENCE {
                sispm10403166lQosPortClassificationQoSClass        Integer32,
                sispm10403166lQosPortClassificationDPlevel         Integer32,
                sispm10403166lQosPortClassificationPCP             Integer32,
                sispm10403166lQosPortClassificationDEI             Integer32,
                sispm10403166lQosPortClassificationPCPClassification AdminMode,
                sispm10403166lQosPortClassificationDSCPBased       AdminMode,
--              sispm10403166lQosPortClassificationQCLAddr         INTEGER,
--              sispm10403166lQosPortClassificationKeyType         KeyType,
                sispm10403166lQosPortClassificationWredGroup       Integer32
                }

    sispm10403166lQosPortClassificationQoSClass OBJECT-TYPE
               SYNTAX      Integer32(0..7)
               MAX-ACCESS  read-write
               STATUS      current
               DESCRIPTION
                  "Controls the default QoS class, i.e., the QoS class for
                   frames not classified
                   in any way. There is a one to one mapping between
                   QoS class, queue and
                   priority. A QoS class of 0 (zero) has the lowest priority.
                   NOTe: If the QoS class has been dynamically changed, then
                   the actual QoS class
                   is shown in parentheses after the configured QoS class.
                   range: 0~7,
                   default: 0."
               ::= {     sispm10403166lQosPortClassificationEntry 2 }

    sispm10403166lQosPortClassificationDPlevel OBJECT-TYPE
               SYNTAX      Integer32(0..3)
               MAX-ACCESS  read-write
               STATUS      current
               DESCRIPTION
                   "DP level for frames not classified in any way.
                    range: 0~3,
                    default: 0."
               ::= {     sispm10403166lQosPortClassificationEntry 3 }

    sispm10403166lQosPortClassificationPCP OBJECT-TYPE
               SYNTAX      Integer32(0..7)
               MAX-ACCESS  read-write
               STATUS      current
               DESCRIPTION
                  "Priority Code Point. It is a 3-bit field storing
                   the priority level for the 802.1Q frame.
                   range: 0~7,
                   default: 0.
                   "
               ::= {     sispm10403166lQosPortClassificationEntry 4 }

    sispm10403166lQosPortClassificationDEI OBJECT-TYPE
               SYNTAX      Integer32(0|1)
               MAX-ACCESS  read-write
               STATUS      current
               DESCRIPTION
                  "Drop Eligible Indicator. It is a 1-bit field in the VLAN.
                   range 0~1,
                   default: 0.
                  "
               ::= {     sispm10403166lQosPortClassificationEntry 5 }

    sispm10403166lQosPortClassificationPCPClassification OBJECT-TYPE
               SYNTAX      AdminMode
               MAX-ACCESS  read-write
               STATUS      current
               DESCRIPTION
                  "Configure the classification mode for tagged frames.
                  "
               DEFVAL  { disable }
               ::= {     sispm10403166lQosPortClassificationEntry 6 }

    sispm10403166lQosPortClassificationDSCPBased OBJECT-TYPE
               SYNTAX      AdminMode
               MAX-ACCESS  read-write
               STATUS      current
               DESCRIPTION
                  "Click to Enable DSCP Based QoS Ingress Port Classification."
               DEFVAL  { disable }
               ::= {     sispm10403166lQosPortClassificationEntry 7 }

--    sispm10403166lQosPortClassificationQCLAddr OBJECT-TYPE
--               SYNTAX      INTEGER { sMacSip(0), dMacDip (1) }
--               MAX-ACCESS  read-write
--               STATUS      current
--               DESCRIPTION
--                  "Controls the QCL address matching mode.
--                   0: SMAC/SIP,
--                   1: DMAC/DIP,
--                  default: SMAC/SIP.
--                  Only support SPARX_III."
--               DEFVAL  { sMacSip }
--               ::= {     sispm10403166lQosPortClassificationEntry 8 }

--    sispm10403166lQosPortClassificationKeyType OBJECT-TYPE
--               SYNTAX      KeyType
--               MAX-ACCESS  read-write
--               STATUS      current
--               DESCRIPTION
--                  "The key type specifying the key generated for frames received
--                   on the port.
--                   0: Normal, Half key, match outer tag, SIP/DIP and SMAC/DMAC.
--                   1: Double Tag: Quarter key, match inner and outer tag.
--                   2: IP Address: Half key, match inner and outer tag, SIP and
--                      DIP. For non-IP frames, match outer tag only.
--                   3: MAC and IP Address: Full key, match inner and outer tag,
--                      SMAC, DMAC, SIP and DIP.
--                   Only support on SERVAL version."
--               DEFVAL  { normal }
--               ::= {     sispm10403166lQosPortClassificationEntry 9 }

    sispm10403166lQosPortClassificationWredGroup OBJECT-TYPE
               SYNTAX      Integer32
               MAX-ACCESS  read-write
               STATUS      current
               DESCRIPTION
                  "Controls the WRED group membership. Range:1-3."
               ::= {     sispm10403166lQosPortClassificationEntry 10 }

--sispm10403166lQoSIngressPortTagClassificationTable
    sispm10403166lQoSIngressPortTagClassificationTable OBJECT-TYPE
               SYNTAX      SEQUENCE OF     SISPM10403166LQoSIngressPortTagClassificationEntry
               MAX-ACCESS  not-accessible
               STATUS      current
               DESCRIPTION
                   "Show QoS Ingress Port Tag Classification.
                    INDEX for this table is ifIndex which is
                    equivalent to the panel port number."
               ::= {     sispm10403166lQosPortClassification 2 }

    sispm10403166lQoSIngressPortTagClassificationEntry OBJECT-TYPE
               SYNTAX          SISPM10403166LQoSIngressPortTagClassificationEntry
               MAX-ACCESS  not-accessible
               STATUS      current
               DESCRIPTION
                   "QoS Ingress Port Tag Classification entry."
               INDEX    {     ifIndex,
                              sispm10403166lQoSIngressPortTagPCP,
                              sispm10403166lQoSIngressPortTagDEI  }
               ::= {     sispm10403166lQoSIngressPortTagClassificationTable 1 }

    SISPM10403166LQoSIngressPortTagClassificationEntry             ::= SEQUENCE {
                sispm10403166lQoSIngressPortTagPCP                   INTEGER,
                sispm10403166lQoSIngressPortTagDEI                   INTEGER,
                sispm10403166lQoSIngressPortTagQosClass              Integer32,
                sispm10403166lQoSIngressPortTagDPLevel               Integer32
                }

    sispm10403166lQoSIngressPortTagPCP OBJECT-TYPE
               SYNTAX      INTEGER { pcp0(1),
                                     pcp1(2),
                                     pcp2(3),
                                     pcp3(4),
                                     pcp4(5),
                                     pcp5(6),
                                     pcp6(7),
                                     pcp7(8) }
               MAX-ACCESS  not-accessible
               STATUS      current
               DESCRIPTION
                   "range: 1-8,
                    PCP0:1, PCP1:2..."
               ::= {     sispm10403166lQoSIngressPortTagClassificationEntry 2 }

    sispm10403166lQoSIngressPortTagDEI OBJECT-TYPE
               SYNTAX      INTEGER { dei0(1), dei1(2) }
               MAX-ACCESS  not-accessible
               STATUS      current
               DESCRIPTION
                   "Ingress Port Tag dei,
                    DEI0:1, DEI1:2."
               ::= {     sispm10403166lQoSIngressPortTagClassificationEntry 3 }

    sispm10403166lQoSIngressPortTagQosClass OBJECT-TYPE
               SYNTAX      Integer32(0..7)
               MAX-ACCESS  read-write
               STATUS      current
               DESCRIPTION
                   "range: 0-7."
               ::= {     sispm10403166lQoSIngressPortTagClassificationEntry 4 }

    sispm10403166lQoSIngressPortTagDPLevel OBJECT-TYPE
               SYNTAX      Integer32(0..3)
               MAX-ACCESS  read-write
               STATUS      current
               DESCRIPTION
                   "range: 0-3."
               ::= {     sispm10403166lQoSIngressPortTagClassificationEntry 5 }


--
-- =======================================================================================================================
-- Start sispm10403166lQosPortPolicing group
-- =======================================================================================================================
--sispm10403166lQosPortPolicingTable
   sispm10403166lQosPortPolicingTable OBJECT-TYPE
               SYNTAX      SEQUENCE OF     SISPM10403166LQosPortPolicingEntry
               MAX-ACCESS  not-accessible
               STATUS      current
               DESCRIPTION
                   "The Policer settings.
                    INDEX for this table is ifIndex which is
                    equivalent to the panel port number."
               ::= {     sispm10403166lQosPortPolicing 1 }

    sispm10403166lQosPortPolicingEntry OBJECT-TYPE
               SYNTAX          SISPM10403166LQosPortPolicingEntry
               MAX-ACCESS  not-accessible
               STATUS      current
               DESCRIPTION
                   "The Policer setting entry."
               INDEX    {     ifIndex  }
               ::= {     sispm10403166lQosPortPolicingTable 1 }

    SISPM10403166LQosPortPolicingEntry             ::= SEQUENCE {
                sispm10403166lQosPortPolicingEnabled         AdminMode,
                sispm10403166lQosPortPolicingRate            Integer32,
                sispm10403166lQosPortPolicingUnit            Integer32,
                sispm10403166lQosPortPolicingFlowControl     AdminMode
                }

    sispm10403166lQosPortPolicingEnabled OBJECT-TYPE
               SYNTAX      AdminMode
               MAX-ACCESS  read-write
               STATUS      current
               DESCRIPTION
                  "Controls whether the policer is enabled on this switch port."
               DEFVAL  { disable }
               ::= {     sispm10403166lQosPortPolicingEntry 2 }

    sispm10403166lQosPortPolicingRate OBJECT-TYPE
               SYNTAX      Integer32
               MAX-ACCESS  read-write
               STATUS      current
               DESCRIPTION
                   "Controls the rate for the policer.
                    default: 500(kbps)."
               ::= {     sispm10403166lQosPortPolicingEntry 3 }

    sispm10403166lQosPortPolicingUnit OBJECT-TYPE
               SYNTAX      Integer32
               MAX-ACCESS  read-write
               STATUS      current
               DESCRIPTION
                   "Controls the unit of measure for the policer rate.
                    0: kbps
                    1: Mbps
		    2: fps
		    3: kfps
		    "
               ::= {     sispm10403166lQosPortPolicingEntry 4 }

    sispm10403166lQosPortPolicingFlowControl OBJECT-TYPE
               SYNTAX      AdminMode
               MAX-ACCESS  read-write
               STATUS      current
               DESCRIPTION
                   "If flow control is enabled and the port is in flow control mode,
                    then pause frames are sent instead of discarding frames."
               DEFVAL  { disable }
               ::= {     sispm10403166lQosPortPolicingEntry 5 }

--
-- =======================================================================================================================
-- Start sispm10403166lQosQueuePolicing group
-- =======================================================================================================================
--sispm10403166lQosQueuePolicingTable
--    sispm10403166lQosQueuePolicingTable OBJECT-TYPE
--               SYNTAX      SEQUENCE OF     SISPM10403166LQosQueuePolicingEntry
--               MAX-ACCESS  not-accessible
--               STATUS      current
--               DESCRIPTION
--                   "The Queue Policer settings.
--                    INDEX for this table is ifIndex which is
--                    equivalent to the panel port number."
--               ::= {     sispm10403166lQosQueuePolicing 1 }
--
--    sispm10403166lQosQueuePolicingEntry OBJECT-TYPE
--               SYNTAX          SISPM10403166LQosQueuePolicingEntry
--               MAX-ACCESS  not-accessible
--               STATUS      current
--               DESCRIPTION
--                   "The Qos Queue Policing Entry."
--               INDEX    {     ifIndex  }
--               ::= {     sispm10403166lQosQueuePolicingTable 1 }
--
--    SISPM10403166LQosQueuePolicingEntry             ::= SEQUENCE {
--                sispm10403166lQosQueuePolicingQueue0Enable   AdminMode,
--                sispm10403166lQosQueuePolicingQueue0Rate     Integer32,
--		sispm10403166lQosQueuePolicingQueue0Unit     Integer32,
--                sispm10403166lQosQueuePolicingQueue1Enable   AdminMode,
--                sispm10403166lQosQueuePolicingQueue1Rate     Integer32,
--		sispm10403166lQosQueuePolicingQueue1Unit     Integer32,
--                sispm10403166lQosQueuePolicingQueue2Enable   AdminMode,
--                sispm10403166lQosQueuePolicingQueue2Rate     Integer32,
--                sispm10403166lQosQueuePolicingQueue2Unit     Integer32,
--                sispm10403166lQosQueuePolicingQueue3Enable   AdminMode,
--                sispm10403166lQosQueuePolicingQueue3Rate     Integer32,
--                sispm10403166lQosQueuePolicingQueue3Unit     Integer32,
--                sispm10403166lQosQueuePolicingQueue4Enable   AdminMode,
--                sispm10403166lQosQueuePolicingQueue4Rate     Integer32,
--		sispm10403166lQosQueuePolicingQueue4Unit     Integer32,
--                sispm10403166lQosQueuePolicingQueue5Enable   AdminMode,
--                sispm10403166lQosQueuePolicingQueue5Rate     Integer32,
--		sispm10403166lQosQueuePolicingQueue5Unit     Integer32,
--                sispm10403166lQosQueuePolicingQueue6Enable   AdminMode,
--                sispm10403166lQosQueuePolicingQueue6Rate     Integer32,
--		sispm10403166lQosQueuePolicingQueue6Unit     Integer32,
--                sispm10403166lQosQueuePolicingQueue7Enable   AdminMode,
--                sispm10403166lQosQueuePolicingQueue7Rate     Integer32,
--		sispm10403166lQosQueuePolicingQueue7Unit     Integer32
--                }
--
--    sispm10403166lQosQueuePolicingQueue0Enable OBJECT-TYPE
--               SYNTAX      AdminMode
--               MAX-ACCESS  read-write
--               STATUS      current
--               DESCRIPTION
--                   "Controls whether the queue 0 policer is enabled on this switch port."
--               DEFVAL  { disable }
--               ::= {     sispm10403166lQosQueuePolicingEntry 3 }
--
--    sispm10403166lQosQueuePolicingQueue0Rate OBJECT-TYPE
--               SYNTAX      Integer32
--               MAX-ACCESS  read-write
--               STATUS      current
--               DESCRIPTION
--                   "Controls whether the queue 0 policer is enabled on this switch port.
--                    default: 500(Kbps)"
--               ::= {     sispm10403166lQosQueuePolicingEntry 4 }
--
--    sispm10403166lQosQueuePolicingQueue0Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sispm10403166lQosQueuePolicingEntry 5 }
--
--    sispm10403166lQosQueuePolicingQueue1Enable OBJECT-TYPE
--               SYNTAX      AdminMode
--               MAX-ACCESS  read-write
--               STATUS      current
--               DESCRIPTION
--                   "Controls whether the queue 1 policer is enabled on this switch port."
--               DEFVAL  { disable }
--               ::= {     sispm10403166lQosQueuePolicingEntry 6 }
--
--    sispm10403166lQosQueuePolicingQueue1Rate OBJECT-TYPE
--               SYNTAX      Integer32
--               MAX-ACCESS  read-write
--               STATUS      current
--               DESCRIPTION
--                   "Controls whether the queue 1 policer is enabled on this switch port.,
--                    default: 500(Kbps)"
--               ::= {     sispm10403166lQosQueuePolicingEntry 7 }
--
--    sispm10403166lQosQueuePolicingQueue1Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sispm10403166lQosQueuePolicingEntry 8 }
--
--    sispm10403166lQosQueuePolicingQueue2Enable OBJECT-TYPE
--               SYNTAX      AdminMode
--               MAX-ACCESS  read-write
--               STATUS      current
--               DESCRIPTION
--                   "Controls whether the queue 2 policer is enabled on this switch port."
--               DEFVAL  { disable }
--               ::= {     sispm10403166lQosQueuePolicingEntry 9 }
--
--    sispm10403166lQosQueuePolicingQueue2Rate OBJECT-TYPE
--               SYNTAX      Integer32
--               MAX-ACCESS  read-write
--               STATUS      current
--               DESCRIPTION
--                   "Controls whether the queue 2 policer is enabled on this switch port.
--                    default: 500(Kbps)"
--               ::= {     sispm10403166lQosQueuePolicingEntry 10 }
--
--    sispm10403166lQosQueuePolicingQueue2Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sispm10403166lQosQueuePolicingEntry 11 }
--
--    sispm10403166lQosQueuePolicingQueue3Enable OBJECT-TYPE
--               SYNTAX      AdminMode
--               MAX-ACCESS  read-write
--               STATUS      current
--               DESCRIPTION
--                   "Controls whether the queue 3 policer is enabled on this switch port."
--               DEFVAL  { disable }
--               ::= {     sispm10403166lQosQueuePolicingEntry 12 }
--
--    sispm10403166lQosQueuePolicingQueue3Rate OBJECT-TYPE
--               SYNTAX      Integer32
--               MAX-ACCESS  read-write
--               STATUS      current
--               DESCRIPTION
--                   "Controls whether the queue 3 policer is enabled on this switch port.
--                    default: 500(Kbps)"
--               ::= {     sispm10403166lQosQueuePolicingEntry 13 }
--
--    sispm10403166lQosQueuePolicingQueue3Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sispm10403166lQosQueuePolicingEntry 14 }
--
--    sispm10403166lQosQueuePolicingQueue4Enable OBJECT-TYPE
--               SYNTAX      AdminMode
--               MAX-ACCESS  read-write
--               STATUS      current
--               DESCRIPTION
--                   "Controls whether the queue 4 policer is enabled on this switch port."
--               DEFVAL  { disable }
--               ::= {     sispm10403166lQosQueuePolicingEntry 15 }
--
--    sispm10403166lQosQueuePolicingQueue4Rate OBJECT-TYPE
--               SYNTAX      Integer32
--               MAX-ACCESS  read-write
--               STATUS      current
--               DESCRIPTION
--                   "Controls whether the queue 4 policer is enabled on this switch port.
--                    default: 500(Kbps)"
--               ::= {     sispm10403166lQosQueuePolicingEntry 16 }
--
--    sispm10403166lQosQueuePolicingQueue4Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sispm10403166lQosQueuePolicingEntry 17 }
--
--    sispm10403166lQosQueuePolicingQueue5Enable OBJECT-TYPE
--               SYNTAX      AdminMode
--               MAX-ACCESS  read-write
--               STATUS      current
--               DESCRIPTION
--                   "Controls whether the queue 5 policer is enabled on this switch port."
--               DEFVAL  { disable }
--               ::= {     sispm10403166lQosQueuePolicingEntry 18 }
--
--    sispm10403166lQosQueuePolicingQueue5Rate OBJECT-TYPE
--               SYNTAX      Integer32
--               MAX-ACCESS  read-write
--               STATUS      current
--               DESCRIPTION
--                   "Controls whether the queue 5 policer is enabled on this switch port.
--                    default: 500(Kbps)"
--               ::= {     sispm10403166lQosQueuePolicingEntry 19 }
--
--    sispm10403166lQosQueuePolicingQueue5Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sispm10403166lQosQueuePolicingEntry 20 }
--
--    sispm10403166lQosQueuePolicingQueue6Enable OBJECT-TYPE
--               SYNTAX      AdminMode
--               MAX-ACCESS  read-write
--               STATUS      current
--               DESCRIPTION
--                   "Controls whether the queue 6 policer is enabled on this switch port."
--               DEFVAL  { disable }
--               ::= {     sispm10403166lQosQueuePolicingEntry 21 }
--
--    sispm10403166lQosQueuePolicingQueue6Rate OBJECT-TYPE
--               SYNTAX      Integer32
--               MAX-ACCESS  read-write
--               STATUS      current
--               DESCRIPTION
--                   "Controls whether the queue 6 policer is enabled on this switch port.
--                    default: 500(Kbps)"
--               ::= {     sispm10403166lQosQueuePolicingEntry 22 }
--
--    sispm10403166lQosQueuePolicingQueue6Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sispm10403166lQosQueuePolicingEntry 23 }
--
--    sispm10403166lQosQueuePolicingQueue7Enable OBJECT-TYPE
--               SYNTAX      AdminMode
--               MAX-ACCESS  read-write
--               STATUS      current
--               DESCRIPTION
--                   "Controls whether the queue 7 policer is enabled on this switch port."
--               DEFVAL  { disable }
--               ::= {     sispm10403166lQosQueuePolicingEntry 24 }
--
--    sispm10403166lQosQueuePolicingQueue7Rate OBJECT-TYPE
--               SYNTAX      Integer32
--               MAX-ACCESS  read-write
--               STATUS      current
--               DESCRIPTION
--                   "Controls whether the queue 7 policer is enabled on this switch port.
--                    default: 500(Kbps)"
--               ::= {     sispm10403166lQosQueuePolicingEntry 25 }
--
--    sispm10403166lQosQueuePolicingQueue7Unit OBJECT-TYPE
--               SYNTAX      Integer32(0|1)
--               MAX-ACCESS  read-write
--               STATUS      current
--               DESCRIPTION
--                   "Controls the unit of measure for the queue policer rate as kbps or Mbps.
--                    range:
--		    0:kbs
--		    1:Mbps
--                    default: 0(kbps)"
--               ::= {     sispm10403166lQosQueuePolicingEntry 26 }
--
--
-- =======================================================================================================================
-- Start sispm10403166lQosPortScheduler group
-- =======================================================================================================================
--sispm10403166lQosPortSchedulerModeTable

--     sispm10403166lQosPortSchedulerModeTable OBJECT-TYPE
--               SYNTAX      SEQUENCE OF     SISPM10403166LQosPortSchedulerModeEntry
--               MAX-ACCESS  not-accessible
--               STATUS      current
--               DESCRIPTION
--                   "The basic QoS Port Scheduler Mode settings.
--                    INDEX for this table is ifIndex which is
--                    equivalent to the panel port number."
--               ::= {     sispm10403166lQosPortScheduler  1 }
--
--    sispm10403166lQosPortSchedulerModeEntry OBJECT-TYPE
--               SYNTAX          SISPM10403166LQosPortSchedulerModeEntry
--               MAX-ACCESS  not-accessible
--               STATUS      current
--               DESCRIPTION
--                   "The Qos Port Scheduler Mode entry."
--               INDEX    {     ifIndex  }
--               ::= {     sispm10403166lQosPortSchedulerModeTable 1 }
--
--    SISPM10403166LQosPortSchedulerModeEntry             ::= SEQUENCE {
--                sispm10403166lQosSchedulerMode            Integer32,
--                sispm10403166lQosSchedulerShaper          AdminMode,
--                sispm10403166lQosSchedulerShaperRate      Integer32
--                }
--
--    sispm10403166lQosSchedulerMode OBJECT-TYPE
--               SYNTAX      Integer32
--               MAX-ACCESS  read-write
--               STATUS      current
--               DESCRIPTION
--                   "Controls whether the scheduler mode is Strict Priority or Weighted
--                    on this switch port.
--                    0:Strict Priority,
--		    2: 2 Queues Weighted
--		    3: 3 Queues Weighted: only Jaguar2 support
--		    4: 4 Queues Weighted: only Jaguar2 support
--		    5: 5 Queues Weighted: only Jaguar2 support
--                    6: 6 Queues Weighted
--		    7: 7 Queues Weighted: only Jaguar2 support
--		    8: 8 Queues Weighted: only Jaguar2 support"
--               ::= {     sispm10403166lQosPortSchedulerModeEntry 2 }
--
--    sispm10403166lQosSchedulerShaper OBJECT-TYPE
--               SYNTAX      AdminMode
--               MAX-ACCESS  read-write
--               STATUS      current
--               DESCRIPTION
--                   "Controls whether the port shaper is enabled."
--               DEFVAL  { disable }
--               ::= {     sispm10403166lQosPortSchedulerModeEntry 3 }
--
--    sispm10403166lQosSchedulerShaperRate OBJECT-TYPE
--               SYNTAX      Integer32
--               MAX-ACCESS  read-write
--               STATUS      current
--               DESCRIPTION
--                   "Controls the rate for the port shaper.
--                    default: 500 kbps."
--               ::= {     sispm10403166lQosPortSchedulerModeEntry 4 }
--
--sispm10403166lQosPortSchedulerTable
--    sispm10403166lQosPortSchedulerTable OBJECT-TYPE
--               SYNTAX      SEQUENCE OF     SISPM10403166LQosPortSchedulerEntry
--               MAX-ACCESS  not-accessible
--               STATUS      current
--               DESCRIPTION
--                   "Show Qos Port Scheduler.
--                    INDEX for this table is ifIndex which is
--                    equivalent to the panel port number."
--               ::= {     sispm10403166lQosPortScheduler 2 }
--
--    sispm10403166lQosPortSchedulerEntry OBJECT-TYPE
--               SYNTAX          SISPM10403166LQosPortSchedulerEntry
--               MAX-ACCESS  not-accessible
--               STATUS      current
--               DESCRIPTION
--                   "The Qos Port Scheduler Entry."
--               INDEX    {     ifIndex,
--                              sispm10403166lQosSchedulerPortQueue}
--               ::= {     sispm10403166lQosPortSchedulerTable 1 }
--
--    SISPM10403166LQosPortSchedulerEntry             ::= SEQUENCE {
--                sispm10403166lQosSchedulerPortQueue                  INTEGER,
--                sispm10403166lQosSchedulerPortQueueShaper            AdminMode,
--                sispm10403166lQosSchedulerPortQueueShaperRate        Integer32,
--                sispm10403166lQosSchedulerPortQueueShaperExcess      AdminMode,
--                sispm10403166lQosSchedulerPortQueueSchedulerWeight   Integer32,
--                sispm10403166lQosSchedulerPortQueueSchedulerPercent  DisplayString
--                }
--
--    sispm10403166lQosSchedulerPortQueue OBJECT-TYPE
--               SYNTAX      INTEGER { q0(1),
--                                     q1(2),
--                                     q2(3),
--                                     q3(4),
--                                     q4(5),
--                                     q5(6),
--                                     q6(7),
--                                     q7(8) }
--               MAX-ACCESS  not-accessible
--               STATUS      current
--               DESCRIPTION
--                   "range: 1-8.
--                    Q0: 1, Q1: 2, ..."
--               ::= {     sispm10403166lQosPortSchedulerEntry 2 }
--
--    sispm10403166lQosSchedulerPortQueueShaper OBJECT-TYPE
--               SYNTAX     AdminMode
--               MAX-ACCESS  read-write
--               STATUS      current
--               DESCRIPTION
--                   "Qos scheduler admin state."
--               DEFVAL  { disable }
--               ::= {     sispm10403166lQosPortSchedulerEntry 3 }
--
--    sispm10403166lQosSchedulerPortQueueShaperRate OBJECT-TYPE
--               SYNTAX      Integer32(100..1000000)
--               MAX-ACCESS  read-write
--               STATUS      current
--               DESCRIPTION
--                   "range: 100..1000000 kbps. "
--               ::= {     sispm10403166lQosPortSchedulerEntry 4 }
--
--    sispm10403166lQosSchedulerPortQueueShaperExcess OBJECT-TYPE
--               SYNTAX      AdminMode
--               MAX-ACCESS  read-write
--               STATUS      current
--               DESCRIPTION
--                   "admin state sispm10403166lQosSchedulerPortQueueShaperExcess"
--               DEFVAL  { disable }
--               ::= {     sispm10403166lQosPortSchedulerEntry 5 }
--
--    sispm10403166lQosSchedulerPortQueueSchedulerWeight OBJECT-TYPE
--               SYNTAX      Integer32(0..100)
--               MAX-ACCESS  read-write
--               STATUS      current
--               DESCRIPTION
--                   "range: 1-100,
--                    default: 17.
--                    Only use in Q0 - Q5.  Q6 & Q7 show 0"
--               ::= {     sispm10403166lQosPortSchedulerEntry 6 }
--
--    sispm10403166lQosSchedulerPortQueueSchedulerPercent OBJECT-TYPE
--               SYNTAX      DisplayString
--               MAX-ACCESS  read-only
--               STATUS      current
--               DESCRIPTION
--                   "Only use in Q0 - Q5. Q6 & Q7 show empty"
--               ::= {     sispm10403166lQosPortSchedulerEntry 7 }
--
-- =======================================================================================================================
-- Start sispm10403166lQosEgressPortPCPRemarking group
-- =======================================================================================================================
--sispm10403166lQosEgressPortPCPRemarkingTable
    sispm10403166lQosEgressPortPCPRemarkingTable OBJECT-TYPE
               SYNTAX      SEQUENCE OF     SISPM10403166LQosEgressPortPCPRemarkingEntry
               MAX-ACCESS  not-accessible
               STATUS      current
               DESCRIPTION
                   "The basic Qos Egress Port PCP Remarking
                    Configuration settings.
                    INDEX for this table is ifIndex which is
                    equivalent to the panel port number."
               ::= {     sispm10403166lQosEgressPortPCPRemarking  1 }

    sispm10403166lQosEgressPortPCPRemarkingEntry OBJECT-TYPE
               SYNTAX          SISPM10403166LQosEgressPortPCPRemarkingEntry
               MAX-ACCESS  not-accessible
               STATUS      current
               DESCRIPTION
                   "The Qos Egress Port PCP Remarking Entry."
               INDEX    {     ifIndex  }
               ::= {     sispm10403166lQosEgressPortPCPRemarkingTable 1 }

    SISPM10403166LQosEgressPortPCPRemarkingEntry             ::= SEQUENCE {
                sispm10403166lQosEgressPortPCPRemarkingMode                    INTEGER
                }

    sispm10403166lQosEgressPortPCPRemarkingMode OBJECT-TYPE
               SYNTAX      INTEGER { keep(0), specific(1), mapped(2) }
               MAX-ACCESS  read-write
               STATUS      current
               DESCRIPTION
                   "the tag remarking mode for this port.
                    0:Keep, Use classified PCP/DEI values.
                    1:Specific, Use default PCP/DEI values.
                    2:Mapped, Use mapped versions of QoS class and DP level."
               ::= {     sispm10403166lQosEgressPortPCPRemarkingEntry 2 }

--sispm10403166lQosEgressPortPCPRemarkingSpecificTable
    sispm10403166lQosEgressPortPCPRemarkingSpecificTable OBJECT-TYPE
               SYNTAX      SEQUENCE OF     SISPM10403166LQosEgressPortPCPRemarkingSpecificEntry
               MAX-ACCESS  not-accessible
               STATUS      current
               DESCRIPTION
                   "The basic Qos Egress Port PCP Remarking Specific
                    Configuration settings.
                    INDEX for this table is ifIndex which is
                    equivalent to the panel port number."
               ::= {     sispm10403166lQosEgressPortPCPRemarking  2 }

    sispm10403166lQosEgressPortPCPRemarkingSpecificEntry OBJECT-TYPE
               SYNTAX          SISPM10403166LQosEgressPortPCPRemarkingSpecificEntry
               MAX-ACCESS  not-accessible
               STATUS      current
               DESCRIPTION
                   "The Qos Egress Port PCP Remarking Specific Entry."
               INDEX    {     ifIndex  }
               ::= {     sispm10403166lQosEgressPortPCPRemarkingSpecificTable 1 }

    SISPM10403166LQosEgressPortPCPRemarkingSpecificEntry             ::= SEQUENCE {
                sispm10403166lQosEgressPortPCPRemarkingSpecificPCP                Integer32,
                sispm10403166lQosEgressPortPCPRemarkingSpecificDEI                AdminMode
                }

    sispm10403166lQosEgressPortPCPRemarkingSpecificPCP OBJECT-TYPE
               SYNTAX      Integer32(0..7)
               MAX-ACCESS  read-write
               STATUS      current
               DESCRIPTION
                   "Controls the specific PCP
                    Range : 0-7"
               ::= {     sispm10403166lQosEgressPortPCPRemarkingSpecificEntry 2 }

    sispm10403166lQosEgressPortPCPRemarkingSpecificDEI OBJECT-TYPE
               SYNTAX      AdminMode
               MAX-ACCESS  read-write
               STATUS      current
               DESCRIPTION
                   "controls the admin state of DEI"
               ::= {     sispm10403166lQosEgressPortPCPRemarkingSpecificEntry 3 }

--sispm10403166lQosPortEgressTagRemarkingMapDPTable
--    sispm10403166lQosPortEgressTagRemarkingMapDPTable OBJECT-TYPE
--               SYNTAX      SEQUENCE OF     SISPM10403166LQosPortEgressTagRemarkingMapDPEntry
--               MAX-ACCESS  not-accessible
--               STATUS      current
--               DESCRIPTION
--                   "Show Qos Port Egress Tag Remarking Map DP.
--                    INDEX for this table is ifIndex which is
--                    equivalent to the panel port number."
--               ::= {     sispm10403166lQosPortEgressTagRemarking 3 }

--    sispm10403166lQosPortEgressTagRemarkingMapDPEntry OBJECT-TYPE
--               SYNTAX          SISPM10403166LQosPortEgressTagRemarkingMapDPEntry
--               MAX-ACCESS  not-accessible
--               STATUS      current
--               DESCRIPTION
--                   "The Qos Port Egress Tag Remarking Map DP Entry."
--               INDEX    {     ifIndex,
--                              sispm10403166lQosPortEgressTagRemarkingClassifiedDPLevel}
--               ::= {     sispm10403166lQosPortEgressTagRemarkingMapDPTable 1 }

--    SISPM10403166LQosPortEgressTagRemarkingMapDPEntry             ::= SEQUENCE {
--                sispm10403166lQosPortEgressTagRemarkingClassifiedDPLevel      Integer32,
--                sispm10403166lQosPortEgressTagRemarkingDPLevel                AdminMode
--                }

--    sispm10403166lQosPortEgressTagRemarkingClassifiedDPLevel OBJECT-TYPE
--               SYNTAX      Integer32(1..4)
--               MAX-ACCESS  not-accessible
--               STATUS      current
--               DESCRIPTION
--                   "range: 1-4."
--               ::= {     sispm10403166lQosPortEgressTagRemarkingMapDPEntry 2 }

--    sispm10403166lQosPortEgressTagRemarkingDPLevel OBJECT-TYPE
--               SYNTAX      AdminMode
--               MAX-ACCESS  read-write
--               STATUS      current
--               DESCRIPTION
--                   "admin state of Tag remark"
--               ::= {     sispm10403166lQosPortEgressTagRemarkingMapDPEntry 3 }

--sispm10403166lQosEgressPortPCPRemarkingMappedTable
    sispm10403166lQosEgressPortPCPRemarkingMappedTable OBJECT-TYPE
               SYNTAX      SEQUENCE OF     SISPM10403166LQosEgressPortPCPRemarkingMappedEntry
               MAX-ACCESS  not-accessible
               STATUS      current
               DESCRIPTION
                   "Show Qos Egress Port PCP Remarking Mapped.
                    INDEX for this table is ifIndex which is
                    equivalent to the panel port number."
               ::= {     sispm10403166lQosEgressPortPCPRemarking 4 }

    sispm10403166lQosEgressPortPCPRemarkingMappedEntry OBJECT-TYPE
               SYNTAX          SISPM10403166LQosEgressPortPCPRemarkingMappedEntry
               MAX-ACCESS  not-accessible
               STATUS      current
               DESCRIPTION
                   "The Qos Egress Port PCP Remarking Mapped Entry."
               INDEX    {     ifIndex,
                              sispm10403166lQosEgressPortPCPRemarkingMappedQueuePriority,
                              sispm10403166lQosEgressPortPCPRemarkingMappedDPLevel  }
               ::= {     sispm10403166lQosEgressPortPCPRemarkingMappedTable 1 }

    SISPM10403166LQosEgressPortPCPRemarkingMappedEntry             ::= SEQUENCE {
                sispm10403166lQosEgressPortPCPRemarkingMappedQueuePriority          INTEGER,
                sispm10403166lQosEgressPortPCPRemarkingMappedDPLevel                INTEGER,
                sispm10403166lQosEgressPortPCPRemarkingMappedPCP                    Integer32,
                sispm10403166lQosEgressPortPCPRemarkingMappedDEI                    Integer32
                }

    sispm10403166lQosEgressPortPCPRemarkingMappedQueuePriority OBJECT-TYPE
               SYNTAX      INTEGER {
                        class0(1),
                        class1(2),
                        class2(3),
                        class3(4),
                        class4(5),
                        class5(6),
                        class6(7),
                        class7(8)
                        }
               MAX-ACCESS  not-accessible
               STATUS      current
               DESCRIPTION
                   "range: 1-8,
                    QoS Class0: 1, QoS Class1: 2..."
               ::= {     sispm10403166lQosEgressPortPCPRemarkingMappedEntry 2 }

    sispm10403166lQosEgressPortPCPRemarkingMappedDPLevel OBJECT-TYPE
               SYNTAX      INTEGER { level0(1), level1(2) }
               MAX-ACCESS  not-accessible
               STATUS      current
               DESCRIPTION
                   "range: 1-2,
                    DP Level0: 1, DP Level1: 2."
               ::= {     sispm10403166lQosEgressPortPCPRemarkingMappedEntry 3 }

    sispm10403166lQosEgressPortPCPRemarkingMappedPCP OBJECT-TYPE
               SYNTAX      Integer32(0..7)
               MAX-ACCESS  read-write
               STATUS      current
               DESCRIPTION
                   "range: 0-7."
               ::= {     sispm10403166lQosEgressPortPCPRemarkingMappedEntry 4 }

    sispm10403166lQosEgressPortPCPRemarkingMappedDEI OBJECT-TYPE
               SYNTAX      Integer32 (0|1)
               MAX-ACCESS  read-write
               STATUS      current
               DESCRIPTION
                   "range: 0-1."
               ::= {     sispm10403166lQosEgressPortPCPRemarkingMappedEntry 5 }

--
-- =======================================================================================================================
-- Start sispm10403166lQosPortDSCP group
-- =======================================================================================================================
--sispm10403166lQosPortDSCPTable
    sispm10403166lQosPortDSCPTable OBJECT-TYPE
               SYNTAX      SEQUENCE OF     SISPM10403166LQosPortDSCPEntry
               MAX-ACCESS  not-accessible
               STATUS      current
               DESCRIPTION
                   "The basic QoS Port DSCP Configuration settings.
                    INDEX for this table is ifIndex which is
                    equivalent to the panel port number."
               ::= {     sispm10403166lQosPortDSCP 1 }

    sispm10403166lQosPortDSCPEntry OBJECT-TYPE
               SYNTAX          SISPM10403166LQosPortDSCPEntry
               MAX-ACCESS  not-accessible
               STATUS      current
               DESCRIPTION
                   "The Qos Port DSCP Entry."
               INDEX    {     ifIndex  }
               ::= {     sispm10403166lQosPortDSCPTable 1 }

    SISPM10403166LQosPortDSCPEntry             ::= SEQUENCE {
                sispm10403166lQosPortDSCPIngressTranslate        AdminMode,
                sispm10403166lQosPortDSCPIngressClassify         INTEGER,
                sispm10403166lQosPortDSCPEgressRewrite           INTEGER
                }

    sispm10403166lQosPortDSCPIngressTranslate OBJECT-TYPE
               SYNTAX      AdminMode
               MAX-ACCESS  read-write
               STATUS      current
               DESCRIPTION
                  "Configure DSCP ingress translation mode."
               DEFVAL  { disable }
               ::= {     sispm10403166lQosPortDSCPEntry 2 }

    sispm10403166lQosPortDSCPIngressClassify OBJECT-TYPE
               SYNTAX      INTEGER { disable (0), dscp (1), selected (2), all(3) }
               MAX-ACCESS  read-write
               STATUS      current
               DESCRIPTION
                   "Classification for a port have 4 different values.
                    0: disable,
                    1: DSCP=0,
                    2: Selected,
                    3: All."
               DEFVAL  { disable }
               ::= {     sispm10403166lQosPortDSCPEntry 3 }

    sispm10403166lQosPortDSCPEgressRewrite OBJECT-TYPE
               SYNTAX      INTEGER { disable (0),enable (1),
                                     remap (2) }
               MAX-ACCESS  read-write
               STATUS      current
               DESCRIPTION
                   "Configure the port egress rewriting mode.
                    0: Disable,1: Enable,2: Remap,range: 0-2"
               ::= {     sispm10403166lQosPortDSCPEntry 4 }

--
-- =======================================================================================================================
-- Start sispm10403166lQosDSCPBasedQoS group
-- =======================================================================================================================
    sispm10403166lQosDSCPBasedQoSTable OBJECT-TYPE
               SYNTAX      SEQUENCE OF     SISPM10403166LQosDSCPBasedQoSEntry
               MAX-ACCESS  not-accessible
               STATUS      current
               DESCRIPTION
                   "configure the basic Qos DSCP-Based QoS Ingress Classification settings for all switches."
               ::= {     sispm10403166lQosDSCPBasedQoS 1 }

    sispm10403166lQosDSCPBasedQoSEntry OBJECT-TYPE
               SYNTAX          SISPM10403166LQosDSCPBasedQoSEntry
               MAX-ACCESS  not-accessible
               STATUS      current
               DESCRIPTION
                   "The Qos DSCP Based QoS Entry."
               INDEX    {     sispm10403166lQosDSCPBasedQoSList  }
               ::= {     sispm10403166lQosDSCPBasedQoSTable 1 }

    SISPM10403166LQosDSCPBasedQoSEntry             ::= SEQUENCE {
                sispm10403166lQosDSCPBasedQoSList          Integer32,
                sispm10403166lQosDSCPBasedQoSDSCP          DisplayString,
                sispm10403166lQosDSCPBasedQoSTrust         AdminMode,
                sispm10403166lQosDSCPBasedQoSQueuePriority Integer32,
                sispm10403166lQosDSCPBasedQoSDPL           Integer32
                }

    sispm10403166lQosDSCPBasedQoSList OBJECT-TYPE
               SYNTAX      Integer32(1..64)
               MAX-ACCESS  not-accessible
               STATUS      current
               DESCRIPTION
                  "DSCP mapping table index(1-64)."
               ::= {     sispm10403166lQosDSCPBasedQoSEntry 1 }

    sispm10403166lQosDSCPBasedQoSDSCP OBJECT-TYPE
               SYNTAX      DisplayString
               MAX-ACCESS  read-only
               STATUS      current
               DESCRIPTION
                  "Maximum number of supported DSCP values are 64."
               ::= {     sispm10403166lQosDSCPBasedQoSEntry 2 }

    sispm10403166lQosDSCPBasedQoSTrust OBJECT-TYPE
               SYNTAX      AdminMode
               MAX-ACCESS  read-write
               STATUS      current
               DESCRIPTION
                  "Controls whether a specific DSCP value is trusted. Only frames with
                   trusted DSCP values are mapped to a specific QoS class
                   and Drop Precedence
                   Level. Frames with untrusted DSCP values are
                   treated as a non-IP frame."
               DEFVAL  { disable }
              ::= {     sispm10403166lQosDSCPBasedQoSEntry 3 }

    sispm10403166lQosDSCPBasedQoSQueuePriority OBJECT-TYPE
               SYNTAX      Integer32(0..7)
               MAX-ACCESS  read-write
               STATUS      current
               DESCRIPTION
                  "QoS class.
                   range: 0-7,
                   default: 0."
               ::= {     sispm10403166lQosDSCPBasedQoSEntry 4 }

    sispm10403166lQosDSCPBasedQoSDPL OBJECT-TYPE
               SYNTAX      Integer32(0|1)
               MAX-ACCESS  read-write
               STATUS      current
               DESCRIPTION
                  "Drop Precedence Level.
                   range: 0-1,
                   default: 0."
               ::= {     sispm10403166lQosDSCPBasedQoSEntry 5 }

--
-- =======================================================================================================================
-- Start sispm10403166lQosDSCPTranslation group
-- =======================================================================================================================
--sispm10403166lQosDSCPTranslationTable
    sispm10403166lQosDSCPTranslationTable OBJECT-TYPE
               SYNTAX      SEQUENCE OF     SISPM10403166LQosDSCPTranslationEntry
               MAX-ACCESS  not-accessible
               STATUS      current
               DESCRIPTION
                   "The basic QoS DSCP Translation settings for all switches."
               ::= {     sispm10403166lQosDSCPTranslation  1 }

    sispm10403166lQosDSCPTranslationEntry OBJECT-TYPE
               SYNTAX          SISPM10403166LQosDSCPTranslationEntry
               MAX-ACCESS  not-accessible
               STATUS      current
               DESCRIPTION
                   "The Qos DSCP Translation Entry."
               INDEX    {     sispm10403166lQosDSCPTranslationList  }
               ::= {     sispm10403166lQosDSCPTranslationTable 1 }

    SISPM10403166LQosDSCPTranslationEntry             ::= SEQUENCE {
                sispm10403166lQosDSCPTranslationList                 Integer32,
                sispm10403166lQosDSCPTranslationDSCPBasedId          DisplayString,
                sispm10403166lQosDSCPTranslationIngressTranslate     Integer32,
                sispm10403166lQosDSCPTranslationIngressClassify      AdminMode,
                sispm10403166lQosDSCPTranslationEgressRemap          Integer32
--              sispm10403166lQosDSCPTranslationEgressRemapDP1       Integer32
                }

    sispm10403166lQosDSCPTranslationList OBJECT-TYPE
               SYNTAX      Integer32(1..64)
               MAX-ACCESS  not-accessible
               STATUS      current
               DESCRIPTION
                  "DSCP translation table index(1-64)."
               ::= {     sispm10403166lQosDSCPTranslationEntry 1 }

    sispm10403166lQosDSCPTranslationDSCPBasedId OBJECT-TYPE
               SYNTAX      DisplayString
               MAX-ACCESS  read-only
               STATUS      current
               DESCRIPTION
                  "Configure global ingress DSCP translation table."
               ::= {     sispm10403166lQosDSCPTranslationEntry 2 }

    sispm10403166lQosDSCPTranslationIngressTranslate OBJECT-TYPE
               SYNTAX      Integer32(0..63)
               MAX-ACCESS  read-write
               STATUS      current
               DESCRIPTION
                  "DSCP at Ingress side can be translated to any of DSCP values.
                   range: 0-63,
                   default: 0."
               ::= {     sispm10403166lQosDSCPTranslationEntry 3 }

    sispm10403166lQosDSCPTranslationIngressClassify OBJECT-TYPE
               SYNTAX      AdminMode
               MAX-ACCESS  read-write
               STATUS      current
               DESCRIPTION
                  "Configure DSCP ingress classification."
               DEFVAL  { disable }
               ::= {     sispm10403166lQosDSCPTranslationEntry 4 }

    sispm10403166lQosDSCPTranslationEgressRemap OBJECT-TYPE
               SYNTAX      Integer32(0..63)
               MAX-ACCESS  read-write
               STATUS      current
               DESCRIPTION
                  "Select the DSCP value from select menu to which you want to remap.
                   range: 0-63,
                   default: 0."
               ::= {     sispm10403166lQosDSCPTranslationEntry 5 }

--    sispm10403166lQosDSCPTranslationEgressRemapDP1 OBJECT-TYPE
--               SYNTAX      Integer32(0..63)
--               MAX-ACCESS  read-write
--               STATUS      current
--               DESCRIPTION
--                  "Select the DSCP value from select menu to which you want to remap.
--                   range: 0-63,
--                   default: 0.
--                   Only support LUTON26."
--               ::= {     sispm10403166lQosDSCPTranslationEntry 6 }

--
-- =======================================================================================================================
-- Start sispm10403166lQosDSCPClassification group
-- =======================================================================================================================
--sispm10403166lQosDSCPClassificationTable
    sispm10403166lQosDSCPClassificationTable OBJECT-TYPE
               SYNTAX      SEQUENCE OF     SISPM10403166LQosDSCPClassificationEntry
               MAX-ACCESS  not-accessible
               STATUS      current
               DESCRIPTION
                   "The mapping of QoS class  to DSCP value."
               ::= {     sispm10403166lQosDSCPClassification 1 }

    sispm10403166lQosDSCPClassificationEntry OBJECT-TYPE
               SYNTAX          SISPM10403166LQosDSCPClassificationEntry
               MAX-ACCESS  not-accessible
               STATUS      current
               DESCRIPTION
                   "The Qos DSCP Classification Entry."
               INDEX    {     sispm10403166lQosDSCPClassificationQoSClass  }
               ::= {     sispm10403166lQosDSCPClassificationTable 1 }

    SISPM10403166LQosDSCPClassificationEntry             ::= SEQUENCE {
                sispm10403166lQosDSCPClassificationQoSClass   Integer32,
                sispm10403166lQosDSCPClassificationDSCPDP0    Integer32,
		sispm10403166lQosDSCPClassificationDSCPDP1    Integer32,
		sispm10403166lQosDSCPClassificationDSCPDP2    Integer32,
		sispm10403166lQosDSCPClassificationDSCPDP3    Integer32
                }

    sispm10403166lQosDSCPClassificationQoSClass OBJECT-TYPE
               SYNTAX      Integer32(1..8)
               MAX-ACCESS  not-accessible
               STATUS      current
               DESCRIPTION
                  "This page allows you to configure the mapping of QoS class
                   and Drop Precedence Level to DSCP value.
                   range: 1-8}"
               ::= {     sispm10403166lQosDSCPClassificationEntry 1 }

    sispm10403166lQosDSCPClassificationDSCPDP0 OBJECT-TYPE
               SYNTAX      Integer32(0..63)
               MAX-ACCESS  read-write
               STATUS      current
               DESCRIPTION
                  "Select the classified DSCP value.
                   range: 0-63,
                   default: 0."
               ::= {     sispm10403166lQosDSCPClassificationEntry 2 }

    sispm10403166lQosDSCPClassificationDSCPDP1 OBJECT-TYPE
               SYNTAX      Integer32(0..63)
               MAX-ACCESS  read-write
               STATUS      current
               DESCRIPTION
                  "Select the classified DSCP value.
                   range: 0-63,
                   default: 0."
               ::= {     sispm10403166lQosDSCPClassificationEntry 3 }

    sispm10403166lQosDSCPClassificationDSCPDP2 OBJECT-TYPE
               SYNTAX      Integer32(0..63)
               MAX-ACCESS  read-write
               STATUS      current
               DESCRIPTION
                  "Select the classified DSCP value.
                   range: 0-63,
                   default: 0."
               ::= {     sispm10403166lQosDSCPClassificationEntry 4 }

    sispm10403166lQosDSCPClassificationDSCPDP3 OBJECT-TYPE
               SYNTAX      Integer32(0..63)
               MAX-ACCESS  read-write
               STATUS      current
               DESCRIPTION
                  "Select the classified DSCP value.
                   range: 0-63,
                   default: 0."
               ::= {     sispm10403166lQosDSCPClassificationEntry 5 }

--
-- =======================================================================================================================
-- Start sispm10403166lQosControlList group
-- =======================================================================================================================
--sispm10403166lQosQceTable

    sispm10403166lQosQceTable OBJECT-TYPE
               SYNTAX      SEQUENCE OF     SISPM10403166LQosQceEntry
               MAX-ACCESS  not-accessible
               STATUS      current
               DESCRIPTION
                   "Create Qos QCE entry."
               ::= {     sispm10403166lQosControlList 1 }

    sispm10403166lQosQceEntry OBJECT-TYPE
               SYNTAX          SISPM10403166LQosQceEntry
               MAX-ACCESS  not-accessible
               STATUS      current
               DESCRIPTION
                   "Qos Qce Entry."
               INDEX    {     sispm10403166lQosQceIndex  }
               ::= {     sispm10403166lQosQceTable 1 }

    SISPM10403166LQosQceEntry             ::= SEQUENCE {
                sispm10403166lQosQceIndex                Integer32,
                sispm10403166lQosQceID                   Integer32,
                sispm10403166lQosQceList                 Integer32,
--              sispm10403166lQosQcePortMembersSwitch    Integer32,
                sispm10403166lQosQcePortMembers          DisplayString,
                sispm10403166lQosQceTag                  DisplayString,
                sispm10403166lQosQceVID                  DisplayString,
                sispm10403166lQosPCP                     DisplayString,
                sispm10403166lQosDEI                     DisplayString,
                sispm10403166lQosSMAC                    DisplayString,
                sispm10403166lQosDMACType                DisplayString,
                sispm10403166lQosDMACValue               DisplayString,
                sispm10403166lQosQceInnerTag             DisplayString,
                sispm10403166lQosQceInnerVID             DisplayString,
                sispm10403166lQosInnerPCP                DisplayString,
                sispm10403166lQosInnerDEI                DisplayString,
                sispm10403166lQosFrameType               INTEGER,
                sispm10403166lQosMacEtherType            DisplayString,
                sispm10403166lQosLLCSSAPAddr             DisplayString,
                sispm10403166lQosLLCDSAPAddr             DisplayString,
                sispm10403166lQosLLCControl              DisplayString,
                sispm10403166lQosSNAPPID                 DisplayString,
                sispm10403166lQosIpv4Protocol            DisplayString,
                sispm10403166lQosIpv4ProtocolValue       Integer32,
                sispm10403166lQosIpv4ProtocolUDPSPort    DisplayString,
                sispm10403166lQosIpv4ProtocolUDPDPort    DisplayString,
                sispm10403166lQosIpv4ProtocolTCPSPort    DisplayString,
                sispm10403166lQosIpv4ProtocolTCPDPort    DisplayString,
                sispm10403166lQosIpv4SourceIp            DisplayString,
                sispm10403166lQosIpv4SourceMask          DisplayString,
                sispm10403166lQosIpv4DestIp              DisplayString,
                sispm10403166lQosIpv4DestMask            DisplayString,
                sispm10403166lQosIpv4IPFragment          INTEGER,
                sispm10403166lQosIpv4DSCP                DisplayString,
                sispm10403166lQosIpv6Protocol            DisplayString,
                sispm10403166lQosIpv6ProtocolValue       Integer32,
                sispm10403166lQosIpv6ProtocolUDPSPort    DisplayString,
                sispm10403166lQosIpv6ProtocolUDPDPort    DisplayString,
                sispm10403166lQosIpv6ProtocolTCPSPort    DisplayString,
                sispm10403166lQosIpv6ProtocolTCPDPort    DisplayString,
                sispm10403166lQosIpv6SourceIp            DisplayString,
                sispm10403166lQosIpv6SourceMask          DisplayString,
                sispm10403166lQosIpv6DestIp              DisplayString,
                sispm10403166lQosIpv6DestMask            DisplayString,
                sispm10403166lQosIpv6DSCP                DisplayString,
                sispm10403166lQosActionQueuePriority     Integer32,
                sispm10403166lQosActionDPL               Integer32,
                sispm10403166lQosActionDSCP              Integer32,
                sispm10403166lQosActionPCP               Integer32,
                sispm10403166lQosActionDEI               Integer32,
                sispm10403166lQosActionPolicy            Integer32,
                sispm10403166lQosActionIngressMapID      Integer32,
                sispm10403166lQosQceRowStatus            RowStatus
                }

    sispm10403166lQosQceIndex OBJECT-TYPE
               SYNTAX      Integer32(1..256)
               MAX-ACCESS  not-accessible
               STATUS      current
               DESCRIPTION
                   "the index to this table."
               ::= {     sispm10403166lQosQceEntry 1 }

    sispm10403166lQosQceID OBJECT-TYPE
               SYNTAX      Integer32(1..256)
               MAX-ACCESS  read-only
               STATUS      current
               DESCRIPTION
                   "If the QCE ID is specified and an entry with this QCE ID
                    already exists, the QCE will be modified. Otherwise, a
                    new QCE will be added.
                    range : 1 - 256."
               ::= {     sispm10403166lQosQceEntry 2 }

    sispm10403166lQosQceList OBJECT-TYPE
               SYNTAX      Integer32(0..256)
               MAX-ACCESS  read-create
               STATUS      current
               DESCRIPTION
                   "If the QCE List is non zero, the QCE will be placed in the list.
                    If the QCE List is zero, the QCE will be placed last in the list.
                    range : 0 - 256."
               ::= {     sispm10403166lQosQceEntry 3 }

--    sispm10403166lQosQcePortMembersSwitch OBJECT-TYPE
--               SYNTAX      Integer32
--               MAX-ACCESS  read-create
--               STATUS      current
--               DESCRIPTION
--                   "Switch number for port members.
--                   -1:Any.
--                   Only support stacking switch."
--               ::= {     sispm10403166lQosQceEntry 4 }

    sispm10403166lQosQcePortMembers OBJECT-TYPE
               SYNTAX      DisplayString
               MAX-ACCESS  read-create
               STATUS      current
               DESCRIPTION
                   "Indicates the ingress port of the QCE. Possible values are:
                    All: The QCE will match all ingress port.
                    Port: The QCE will match a specific ingress port.Format: 1,3-6."
               ::= {     sispm10403166lQosQceEntry 5 }

    sispm10403166lQosQceTag OBJECT-TYPE
               SYNTAX      DisplayString
               MAX-ACCESS  read-create
               STATUS      current
               DESCRIPTION
                  "'Any', 'Untagged' or 'Tagged' or 'C-Tag' or 'S-Tag'"
               ::= {     sispm10403166lQosQceEntry 6 }

    sispm10403166lQosQceVID OBJECT-TYPE
               SYNTAX      DisplayString
               MAX-ACCESS  read-create
               STATUS      current
               DESCRIPTION
                   "Valid value of VLAN ID can be any value in
                   'Specific 1~4095' or 'range 1-4095' or 'Any'."
               ::= {     sispm10403166lQosQceEntry 7 }

    sispm10403166lQosPCP OBJECT-TYPE
               SYNTAX      DisplayString
               MAX-ACCESS  read-create
               STATUS      current
               DESCRIPTION
                   "Priority Code Point: Valid value PCP are
                    specific(0, 1, 2, 3, 4, 5, 6, 7)
                    or range(0-1, 2-3, 4-5, 6-7, 0-3, 4-7) or 'Any'."
               ::= {     sispm10403166lQosQceEntry 8 }

    sispm10403166lQosDEI OBJECT-TYPE
               SYNTAX      DisplayString
               MAX-ACCESS  read-create
               STATUS      current
               DESCRIPTION
                   "Drop Eligible Indicator: Valid value of DEI can be
                    any of values between 0, 1 or 'Any'."
               ::= {     sispm10403166lQosQceEntry 9 }

    sispm10403166lQosSMAC  OBJECT-TYPE
               SYNTAX      DisplayString
               MAX-ACCESS  read-create
               STATUS      current
               DESCRIPTION
                   "Source MAC address: xx-xx-xx-xx-xx-xx or 'Any'."
               ::= {     sispm10403166lQosQceEntry 10 }

    sispm10403166lQosDMACType OBJECT-TYPE
               SYNTAX      DisplayString
               MAX-ACCESS  read-create
               STATUS      current
               DESCRIPTION
                   "Destination MAC type: possible values are 'UC'(unicast),
                    'MC'(multicast), 'BC'(broadcast), 'SP'(Specific) or 'Any'."
               ::= {     sispm10403166lQosQceEntry 11 }

    sispm10403166lQosDMACValue OBJECT-TYPE
               SYNTAX      DisplayString
               MAX-ACCESS  read-create
               STATUS      current
               DESCRIPTION
                   "when QosDMACType is 'SP'(specific) can set mac address.
                   "
               ::= {     sispm10403166lQosQceEntry 12 }

    sispm10403166lQosQceInnerTag OBJECT-TYPE
               SYNTAX      DisplayString
               MAX-ACCESS  read-create
               STATUS      current
               DESCRIPTION
                   "Value of Inner Tag field can be 'Any', 'Untagged' or 'Tagged' or
                    'C-tagged' or 'S-tagged'."
               ::= {     sispm10403166lQosQceEntry 13 }

    sispm10403166lQosQceInnerVID OBJECT-TYPE
               SYNTAX      DisplayString
               MAX-ACCESS  read-create
               STATUS      current
               DESCRIPTION
                   "Valid value of Inner VLAN ID can be any value in
                    'Specific 1~4095' or 'range 1-4095' or 'Any'.
                    "
               ::= {     sispm10403166lQosQceEntry 14 }

    sispm10403166lQosInnerPCP OBJECT-TYPE
               SYNTAX      DisplayString
               MAX-ACCESS  read-create
               STATUS      current
               DESCRIPTION
                   "Valid value Inner PCP are specific(0, 1, 2, 3, 4, 5, 6, 7)
                    or range(0-1, 2-3, 4-5, 6-7, 0-3, 4-7) or 'Any'.
                   "
               ::= {     sispm10403166lQosQceEntry 15 }

    sispm10403166lQosInnerDEI OBJECT-TYPE
               SYNTAX      DisplayString
               MAX-ACCESS  read-create
               STATUS      current
               DESCRIPTION
                   "Valid value of Inner DEI can be any of values between
                    0, 1 or 'Any'.
                   "
               ::= {     sispm10403166lQosQceEntry 16 }

    sispm10403166lQosFrameType OBJECT-TYPE
               SYNTAX      INTEGER {
                            any(1),
                            ethernet(2),
                            llc(3),
                            snap(4),
                            ipv4(5),
                            ipv6(6)
                           }
               MAX-ACCESS  read-create
               STATUS      current
               DESCRIPTION
                   "Frame Type can have any of the following values:
                    1: Any,
                    2: Ethernet,
                    3: LLC,
                    4: SNAP,
                    5: IPv4,
                    6: IPv6."
               ::= {     sispm10403166lQosQceEntry 17 }

    sispm10403166lQosMacEtherType OBJECT-TYPE
               SYNTAX      DisplayString
               MAX-ACCESS  read-create
               STATUS      current
               DESCRIPTION
                   "Valid ethernet type can have a value within 0x600-0xFFFF or 'Any' ,
                    but excluding 0x800(IPv4) and 0x86DD(IPv6),
                    range: 0000-FFFF,
                    default: Any."
               ::= {     sispm10403166lQosQceEntry 18 }

    sispm10403166lQosLLCSSAPAddr OBJECT-TYPE
               SYNTAX      DisplayString
               MAX-ACCESS  read-create
               STATUS      current
               DESCRIPTION
                   "Valid SSAP(Source Service Access Point) can vary from
                    0x00 to 0xFF or 'Any',
                    range: 00-FF,
                    default: Any."
               ::= {     sispm10403166lQosQceEntry 19 }

    sispm10403166lQosLLCDSAPAddr OBJECT-TYPE
               SYNTAX      DisplayString
               MAX-ACCESS  read-create
               STATUS      current
               DESCRIPTION
                   "Valid DSAP(Destination Service Access Point) can
                    vary from 0x00 to 0xFF or 'Any',
                    range: 00-FF,
                    default: Any."
               ::= {     sispm10403166lQosQceEntry 20 }

    sispm10403166lQosLLCControl OBJECT-TYPE
               SYNTAX      DisplayString
               MAX-ACCESS  read-create
               STATUS      current
               DESCRIPTION
                   "Valid Control field can vary from 0x00 to 0xFF or 'Any',
                    range: 00-FF,
                    default: Any."
               ::= {     sispm10403166lQosQceEntry 21 }

    sispm10403166lQosSNAPPID OBJECT-TYPE
               SYNTAX      DisplayString
               MAX-ACCESS  read-create
               STATUS      current
               DESCRIPTION
                   "Valid PID(a.k.a ethernet type) can have value within
                    0x00-0xFFFF or 'Any',
                    range: 0000-FFFF,
                    default: Any."
               ::= {     sispm10403166lQosQceEntry 22 }

   sispm10403166lQosIpv4Protocol OBJECT-TYPE
               SYNTAX      DisplayString
               MAX-ACCESS  read-create
               STATUS      current
               DESCRIPTION
                   "IP protocol number: (Other, TCP or UDP) or 'Any'."
               ::= {     sispm10403166lQosQceEntry 23 }

    sispm10403166lQosIpv4ProtocolValue  OBJECT-TYPE
               SYNTAX      Integer32(0..255)
               MAX-ACCESS  read-create
               STATUS      current
               DESCRIPTION
                   "Ipv4 Protocol is Other.
                    range: 0-255
                    default: 0."
               ::= {     sispm10403166lQosQceEntry 24 }

    sispm10403166lQosIpv4ProtocolUDPSPort OBJECT-TYPE
               SYNTAX      DisplayString
               MAX-ACCESS  read-create
               STATUS      current
               DESCRIPTION
                   "Source  TCP/UDP Port:(0-65535) or 'Any',
                    specific or port range applicable for IP protocol UDP/TCP."
               ::= {     sispm10403166lQosQceEntry 25 }

    sispm10403166lQosIpv4ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sispm10403166lQosQceEntry 26 }

    sispm10403166lQosIpv4ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sispm10403166lQosQceEntry 27 }

    sispm10403166lQosIpv4ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sispm10403166lQosQceEntry 28 }

    sispm10403166lQosIpv4SourceIp OBJECT-TYPE
               SYNTAX      DisplayString
               MAX-ACCESS  read-create
               STATUS      current
               DESCRIPTION
                   "Specific Source IP address in value format or value 0.0.0.0 is 'Any'.
                    if Ipv4 Mask value 0.0.0.0 is 'Any' ,IP address value also is 'Any'.
                    (x.y.z.w),x=0 unless y.z.w also 0,x not is 127 or greater than 223."
               ::= {     sispm10403166lQosQceEntry 29 }

    sispm10403166lQosIpv4SourceMask OBJECT-TYPE
               SYNTAX      DisplayString
               MAX-ACCESS  read-create
               STATUS      current
               DESCRIPTION
                   "Specific Source IP address in mask format or value 0.0.0.0 is 'Any'."
               ::= {     sispm10403166lQosQceEntry 30 }

    sispm10403166lQosIpv4DestIp OBJECT-TYPE
               SYNTAX      DisplayString
               MAX-ACCESS  read-create
               STATUS      current
               DESCRIPTION
                   "Specific Destination IP address in value format or value 0.0.0.0 is 'Any'.
                    if Ipv4 Mask value 0.0.0.0 is 'Any' ,IP address value also is 'Any'.
                    (x.y.z.w),x=0 unless y.z.w also 0,x not is 127 or greater than 223."
               ::= {     sispm10403166lQosQceEntry 31 }

    sispm10403166lQosIpv4DestMask OBJECT-TYPE
               SYNTAX      DisplayString
               MAX-ACCESS  read-create
               STATUS      current
               DESCRIPTION
                   "Specific Destination IP address in mask format or value 0.0.0.0 is 'Any'."
               ::= {     sispm10403166lQosQceEntry 32 }

    sispm10403166lQosIpv4IPFragment OBJECT-TYPE
               SYNTAX      INTEGER { any(0), no(1), yes(2) }
               MAX-ACCESS  read-create
               STATUS      current
               DESCRIPTION
                   "IPv4 frame fragmented option:
                    2: yes,
                    1: no,
                    0: any."
               ::= {     sispm10403166lQosQceEntry 33 }

    sispm10403166lQosIpv4DSCP OBJECT-TYPE
               SYNTAX      DisplayString
               MAX-ACCESS  read-create
               STATUS      current
               DESCRIPTION
                   "Diffserv Code Point value (DSCP): It can be a specific value,
                    range of values or 'Any'. DSCP values are in the range 0-63."
               ::= {     sispm10403166lQosQceEntry 34 }

    sispm10403166lQosIpv6Protocol OBJECT-TYPE
               SYNTAX      DisplayString
               MAX-ACCESS  read-create
               STATUS      current
               DESCRIPTION
                   "IP protocol number: (Other, TCP or UDP) or 'Any'."
               ::= {     sispm10403166lQosQceEntry 35 }

    sispm10403166lQosIpv6ProtocolValue OBJECT-TYPE
               SYNTAX      Integer32(0..255)
               MAX-ACCESS  read-create
               STATUS      current
               DESCRIPTION
                   "when IPv6 protocol is Other ,
                    range: 0-255."
               ::= {     sispm10403166lQosQceEntry 36 }

    sispm10403166lQosIpv6ProtocolUDPSPort OBJECT-TYPE
               SYNTAX      DisplayString
               MAX-ACCESS  read-create
               STATUS      current
               DESCRIPTION
                   "Source TCP/UDP port:(0-65535) or 'Any',
                    specific or port range applicable for IP protocol UDP/TCP."
               ::= {     sispm10403166lQosQceEntry 37 }

    sispm10403166lQosIpv6ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sispm10403166lQosQceEntry 38 }

    sispm10403166lQosIpv6ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sispm10403166lQosQceEntry 39 }


    sispm10403166lQosIpv6ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sispm10403166lQosQceEntry 40 }

    sispm10403166lQosIpv6SourceIp OBJECT-TYPE
               SYNTAX      DisplayString
               MAX-ACCESS  read-create
               STATUS      current
               DESCRIPTION
                   "IPv6 source address: (a.b.c.d) or value 0.0.0.0 is 'Any', 32 LS bits."
               ::= {     sispm10403166lQosQceEntry 41 }

    sispm10403166lQosIpv6SourceMask OBJECT-TYPE
               SYNTAX      DisplayString
               MAX-ACCESS  read-create
               STATUS      current
               DESCRIPTION
                   "IPv6 mask address: (a.b.c.d) or value 0.0.0.0 is 'Any', 32 LS bits."
               ::= {     sispm10403166lQosQceEntry 42 }

    sispm10403166lQosIpv6DestIp OBJECT-TYPE
               SYNTAX      DisplayString
               MAX-ACCESS  read-create
               STATUS      current
               DESCRIPTION
                   "IPv6 destination address: (a.b.c.d) or value 0.0.0.0 is 'Any', 32 LS bits."
               ::= {     sispm10403166lQosQceEntry 43 }

    sispm10403166lQosIpv6DestMask OBJECT-TYPE
               SYNTAX      DisplayString
               MAX-ACCESS  read-create
               STATUS      current
               DESCRIPTION
                   "IPv6 mask address: (a.b.c.d) or value 0.0.0.0 is 'Any', 32 LS bits."
               ::= {     sispm10403166lQosQceEntry 44 }

    sispm10403166lQosIpv6DSCP OBJECT-TYPE
               SYNTAX      DisplayString
               MAX-ACCESS  read-create
               STATUS      current
               DESCRIPTION
                   "Diffserv Code Point value (DSCP): It can be a specific value,
                    range of values or 'Any'. DSCP values are in the
                    range 0-63 including BE,
                    CS1-CS7, EF or AF11-AF43."
               ::= {     sispm10403166lQosQceEntry 45 }

    sispm10403166lQosActionQueuePriority  OBJECT-TYPE
               SYNTAX      Integer32(0..8)
               MAX-ACCESS  read-create
               STATUS      current
               DESCRIPTION
                   "QoS class: (0-7) or 8: Default."
               ::= {     sispm10403166lQosQceEntry 46 }

    sispm10403166lQosActionDPL OBJECT-TYPE
               SYNTAX      Integer32 (0..4)
               MAX-ACCESS  read-create
               STATUS      current
               DESCRIPTION
                   "range:0-4. 4: Default"
               ::= {     sispm10403166lQosQceEntry 47 }

    sispm10403166lQosActionDSCP OBJECT-TYPE
               SYNTAX      Integer32(0..64)
               MAX-ACCESS  read-create
               STATUS      current
               DESCRIPTION
                   "Valid DSCP value can be (0-63, BE, CS1-CS7,
                    EF or AF11-AF43) or 64: Default."
               ::= {     sispm10403166lQosQceEntry 48 }

    sispm10403166lQosActionPCP  OBJECT-TYPE
               SYNTAX      Integer32(0..8)
               MAX-ACCESS  read-create
               STATUS      current
               DESCRIPTION
                   "pcp: (0-7) or 8: Default.
                   "
               ::= {     sispm10403166lQosQceEntry 49 }

    sispm10403166lQosActionDEI OBJECT-TYPE
               SYNTAX      Integer32 (0..2)
               MAX-ACCESS  read-create
               STATUS      current
               DESCRIPTION
                   "dei: (0-1) or 2: Default.
                    "
               ::= {     sispm10403166lQosQceEntry 50 }

    sispm10403166lQosActionPolicy OBJECT-TYPE
               SYNTAX      Integer32(0..128)
               MAX-ACCESS  read-create
               STATUS      current
               DESCRIPTION
                   "ACL Policy number: (0-127) or 'empty'(128). Default: empty.
                    "
               ::= {     sispm10403166lQosQceEntry 51 }

    sispm10403166lQosActionIngressMapID OBJECT-TYPE
               SYNTAX      Integer32(-1..255)
               MAX-ACCESS  read-create
               STATUS      current
               DESCRIPTION
                   "Classify Ingress Map ID:
                   Range: 0-255
                   Default: -1
                   "
               ::= {     sispm10403166lQosQceEntry 52 }

    sispm10403166lQosQceRowStatus OBJECT-TYPE
               SYNTAX      RowStatus
               MAX-ACCESS  read-create
               STATUS      current
               DESCRIPTION
                   "This object indicates the status of this entry, and is used
                   to create/delete entries.  Any object in an entry of this table
                   may be modified while the value of the corresponding instance
                   of this object is active(1).
                   createAndGo, notReady not supported."
               ::= {     sispm10403166lQosQceEntry 53 }

--
-- =======================================================================================================================
-- Start  sispm10403166lQosStormControl group
-- =======================================================================================================================
--sispm10403166lQosStormControlTable
    sispm10403166lQosStormControlTable OBJECT-TYPE
               SYNTAX      SEQUENCE OF     SISPM10403166LQosStormControlEntry
               MAX-ACCESS  not-accessible
               STATUS      current
               DESCRIPTION
                   "The basic QoS DSCP Translation settings for all switches."
               ::= {     sispm10403166lQosStormControl  1 }

    sispm10403166lQosStormControlEntry OBJECT-TYPE
               SYNTAX          SISPM10403166LQosStormControlEntry
               MAX-ACCESS  not-accessible
               STATUS      current
               DESCRIPTION
                   "The Qos Storm Control Entry."
               INDEX    {     sispm10403166lQosStormControlFrameType  }
               ::= {     sispm10403166lQosStormControlTable 1 }

    SISPM10403166LQosStormControlEntry             ::= SEQUENCE {
                sispm10403166lQosStormControlFrameType        INTEGER,
                sispm10403166lQosStormControlEnabled          AdminMode,
                sispm10403166lQosStormControlRate             Integer32,
                sispm10403166lQosStormControlUnit             Integer32
                }

    sispm10403166lQosStormControlFrameType OBJECT-TYPE
               SYNTAX      INTEGER { unicast(1), multicast (2), broadcast (3)}
               MAX-ACCESS  not-accessible
               STATUS      current
               DESCRIPTION
                   "The settings in a particular row apply to the frame type listed here.
                    1:Unicast,
                    2:Multicast,
                    3:Broadcast."
               ::= {     sispm10403166lQosStormControlEntry 1 }

    sispm10403166lQosStormControlEnabled OBJECT-TYPE
               SYNTAX      AdminMode
               MAX-ACCESS  read-write
               STATUS      current
               DESCRIPTION
                  "Enable or disable the global storm policer for the given frame type."
               ::= {     sispm10403166lQosStormControlEntry 2 }

    sispm10403166lQosStormControlRate OBJECT-TYPE
               SYNTAX      Integer32
               MAX-ACCESS  read-write
               STATUS      current
               DESCRIPTION
                   "Controls the rate for the global storm policer."
               ::= {     sispm10403166lQosStormControlEntry 3 }

    sispm10403166lQosStormControlUnit OBJECT-TYPE
               SYNTAX      Integer32
               MAX-ACCESS  read-write
               STATUS      current
               DESCRIPTION
                   "Controls the unit of measure for the global storm policer rate as fps or kfps.
                   0: kbps
                   1: Mbps
                   2: fps
                   3: kfps"
               ::= {     sispm10403166lQosStormControlEntry 4 }

--
-- =======================================================================================================================
-- Start  sispm10403166lQosPortStormControl group
-- =======================================================================================================================
--sispm10403166lQosPortStormControlTable
    sispm10403166lQosPortStormControlTable OBJECT-TYPE
               SYNTAX      SEQUENCE OF     SISPM10403166LQosPortStormControlEntry
               MAX-ACCESS  not-accessible
               STATUS      current
               DESCRIPTION
                   "Configure the storm control settings.
                    INDEX for this table is ifIndex which is
                    equivalent to the panel port number."
               ::= {     sispm10403166lQosPortStormControl  1 }

    sispm10403166lQosPortStormControlEntry OBJECT-TYPE
               SYNTAX      SISPM10403166LQosPortStormControlEntry
               MAX-ACCESS  not-accessible
               STATUS      current
               DESCRIPTION
                   "The Qos Port Storm Control Entry."
               INDEX    {     ifIndex  }
               ::= {     sispm10403166lQosPortStormControlTable 1 }

    SISPM10403166LQosPortStormControlEntry             ::= SEQUENCE {
                sispm10403166lQosPortStormControlUnicastEnabled   AdminMode,
                sispm10403166lQosPortStormControlUnicastRate      Integer32,
                sispm10403166lQosPortStormControlUnicastUnit      Integer32,
                sispm10403166lQosPortStormControlBroadcastEnabled AdminMode,
                sispm10403166lQosPortStormControlBroadcastRate    Integer32,
                sispm10403166lQosPortStormControlBroadcastUnit    Integer32,
                sispm10403166lQosPortStormControlUnknownEnabled   AdminMode,
                sispm10403166lQosPortStormControlUnknownRate      Integer32,
                sispm10403166lQosPortStormControlUnknownUnit      Integer32
                }

     sispm10403166lQosPortStormControlUnicastEnabled OBJECT-TYPE
               SYNTAX      AdminMode
               MAX-ACCESS  read-write
               STATUS      current
               DESCRIPTION
                  "Controls whether the storm control is enabled on this
                   switch port."
               ::= {     sispm10403166lQosPortStormControlEntry 2 }

    sispm10403166lQosPortStormControlUnicastRate OBJECT-TYPE
               SYNTAX      Integer32
               MAX-ACCESS  read-write
               STATUS      current
               DESCRIPTION
                   "Controls the rate for the storm control."
               ::= {     sispm10403166lQosPortStormControlEntry 3 }

    sispm10403166lQosPortStormControlUnicastUnit OBJECT-TYPE
               SYNTAX      Integer32
               MAX-ACCESS  read-write
               STATUS      current
               DESCRIPTION
                   "Controls the unit of measure for the storm control rate.
                   0: kbps
                   1: Mbps
                   2: fps
                   3: kfps"
               ::= {     sispm10403166lQosPortStormControlEntry 4 }

     sispm10403166lQosPortStormControlBroadcastEnabled  OBJECT-TYPE
               SYNTAX      AdminMode
               MAX-ACCESS  read-write
               STATUS      current
               DESCRIPTION
                  "Controls whether the storm control is enabled on this
                   switch port."
               ::= {     sispm10403166lQosPortStormControlEntry 5 }

    sispm10403166lQosPortStormControlBroadcastRate OBJECT-TYPE
               SYNTAX      Integer32
               MAX-ACCESS  read-write
               STATUS      current
               DESCRIPTION
                   "Controls the rate for the storm control."
               ::= {     sispm10403166lQosPortStormControlEntry 6 }

    sispm10403166lQosPortStormControlBroadcastUnit OBJECT-TYPE
               SYNTAX      Integer32
               MAX-ACCESS  read-write
               STATUS      current
               DESCRIPTION
                   "Controls the unit of measure for the storm control rate.
                   0: kbps
                   1: Mbps
                   2: fps
                   3: kfps"
               ::= {     sispm10403166lQosPortStormControlEntry 7 }

    sispm10403166lQosPortStormControlUnknownEnabled  OBJECT-TYPE
               SYNTAX      AdminMode
               MAX-ACCESS  read-write
               STATUS      current
               DESCRIPTION
                  "Controls whether the storm control is enabled on this
                   switch port."
               ::= {     sispm10403166lQosPortStormControlEntry 8 }

    sispm10403166lQosPortStormControlUnknownRate OBJECT-TYPE
               SYNTAX      Integer32
               MAX-ACCESS  read-write
               STATUS      current
               DESCRIPTION
                   "Controls the rate for the storm control."
               ::= {     sispm10403166lQosPortStormControlEntry 9 }

    sispm10403166lQosPortStormControlUnknownUnit OBJECT-TYPE
               SYNTAX      Integer32
               MAX-ACCESS  read-write
               STATUS      current
               DESCRIPTION
                   "Controls the unit of measure for the storm control rate.
                   0: kbps
                   1: Mbps
                   2: fps
                   3: kfps"
               ::= {     sispm10403166lQosPortStormControlEntry 10 }

--
-- =======================================================================================================================
-- Start  sispm10403166lQosWRED group
-- =======================================================================================================================
--sispm10403166lQosWREDTable
    sispm10403166lQosWREDTable OBJECT-TYPE
               SYNTAX      SEQUENCE OF     SISPM10403166LQosWREDEntry
               MAX-ACCESS  not-accessible
               STATUS      current
               DESCRIPTION
                   "The basic QoS DSCP Translation settings for all switches."
               ::= {     sispm10403166lQosWRED  1 }

    sispm10403166lQosWREDEntry OBJECT-TYPE
               SYNTAX          SISPM10403166LQosWREDEntry
               MAX-ACCESS  not-accessible
               STATUS      current
               DESCRIPTION
                   "The Qos WRED Entry."
               INDEX    {     sispm10403166lQosWREDQueue  }
               ::= {     sispm10403166lQosWREDTable 1 }

    SISPM10403166LQosWREDEntry             ::= SEQUENCE {
                sispm10403166lQosWREDGroupIndex      Integer32,
                sispm10403166lQosWREDQueue           Integer32,
                sispm10403166lQosWREDDPL             Integer32,
                sispm10403166lQosWREDEnable          AdminMode,
                sispm10403166lQosWREDMinThreshold    Integer32,
                sispm10403166lQosWREDMaxThreshold    Integer32,
                sispm10403166lQosWREDMaxUnit         INTEGER
                }

    sispm10403166lQosWREDGroupIndex OBJECT-TYPE
               SYNTAX      Integer32
               MAX-ACCESS  not-accessible
               STATUS      current
               DESCRIPTION
                   "The group number for which the configuration
                    below applies."
               ::= {     sispm10403166lQosWREDEntry 1 }

    sispm10403166lQosWREDQueue OBJECT-TYPE
               SYNTAX      Integer32(1..65535)
               MAX-ACCESS  not-accessible
               STATUS      current
               DESCRIPTION
                   "The queue number (QoS class) for which the configuration
                    below applies."
               ::= {     sispm10403166lQosWREDEntry 2 }

    sispm10403166lQosWREDDPL OBJECT-TYPE
               SYNTAX      Integer32
               MAX-ACCESS  not-accessible
               STATUS      current
               DESCRIPTION
                   "The dpl number for which the configuration
                    below applies."
               ::= {     sispm10403166lQosWREDEntry 3 }


    sispm10403166lQosWREDEnable OBJECT-TYPE
               SYNTAX      AdminMode
               MAX-ACCESS  read-write
               STATUS      current
               DESCRIPTION
                  "Controls whether RED is enabled for this queue.
                  "
               DEFVAL  { disable }
               ::= {     sispm10403166lQosWREDEntry 4 }

    sispm10403166lQosWREDMinThreshold OBJECT-TYPE
               SYNTAX      Integer32(0..100)
               MAX-ACCESS  read-write
               STATUS      current
               DESCRIPTION
                   "Controls the lower RED fill level threshold. If the queue filling
                    level is below this threshold, the drop probability is zero.
                    range:0-100%,
                    default: 0.
                  "
               ::= {     sispm10403166lQosWREDEntry 5 }

    sispm10403166lQosWREDMaxThreshold OBJECT-TYPE
               SYNTAX      Integer32(0..100)
               MAX-ACCESS  read-write
               STATUS      current
               DESCRIPTION
                   "Controls the upper RED drop probability or fill level threshold
                    for frames marked with Drop Precedence Level 1 (yellow frames).
                    range:0-100%,
                    default: 50.
                  "
               ::= {     sispm10403166lQosWREDEntry 6 }

    sispm10403166lQosWREDMaxUnit OBJECT-TYPE
               SYNTAX      INTEGER {dropProbability (0), fillLevel (1) }
               MAX-ACCESS  read-write
               STATUS      current
               DESCRIPTION
                   "Selects the unit for Max.
                    0: Drop Probability,
                    1: Fill Level,
                    default: Drop Probability.
                  "
               DEFVAL  { dropProbability }
               ::= {     sispm10403166lQosWREDEntry 7 }

--
-- =======================================================================================================================
-- Start  sispm10403166lQosQCLStatus
-- =======================================================================================================================

--sispm10403166lQosQCLStatusTable
    sispm10403166lQosQCLStatusTable OBJECT-TYPE
               SYNTAX      SEQUENCE OF     SISPM10403166LQosQCLStatusEntry
               MAX-ACCESS  not-accessible
               STATUS      current
               DESCRIPTION
                   "The basic QoS DSCP Translation settings for all switches."
               ::= {     sispm10403166lQosQCLStatus 1 }

    sispm10403166lQosQCLStatusEntry OBJECT-TYPE
               SYNTAX          SISPM10403166LQosQCLStatusEntry
               MAX-ACCESS  not-accessible
               STATUS      current
               DESCRIPTION
                   "The Qos QCL Status Entry."
               INDEX    {     sispm10403166lQosQCLStatusList  }
               ::= {     sispm10403166lQosQCLStatusTable 1 }

    SISPM10403166LQosQCLStatusEntry             ::= SEQUENCE {
        sispm10403166lQosQCLStatusList               Integer32,
        sispm10403166lQosQCLStatusUser               DisplayString,
        sispm10403166lQosQCLStatusQCEId              DisplayString,
        sispm10403166lQosQCLStatusFrameType          DisplayString,
        sispm10403166lQosQCLStatusPortlist           DisplayString,
        sispm10403166lQosQCLStatusActionQueuePriority DisplayString,
        sispm10403166lQosQCLStatusActionDPL          DisplayString,
        sispm10403166lQosQCLStatusActionDSCP         DisplayString,
        sispm10403166lQosQCLStatusActionPCP          DisplayString,
        sispm10403166lQosQCLStatusActionDEL          DisplayString,
        sispm10403166lQosQCLStatusActionPolicy       DisplayString,
        sispm10403166lQosQCLStatusConflict           DisplayString,
--      sispm10403166lQosQCLStatusSwitch             Integer32,
		sispm10403166lQosQCLStatusDMAC               DisplayString,
		sispm10403166lQosQCLStatusSMAC               DisplayString,
		sispm10403166lQosQCLStatusTag                DisplayString,
		sispm10403166lQosQCLStatusVID                DisplayString,
		sispm10403166lQosQCLStatusPCP                DisplayString,
		sispm10403166lQosQCLStatusDEI                DisplayString
                }

    sispm10403166lQosQCLStatusList OBJECT-TYPE
               SYNTAX      Integer32(1..4095)
               MAX-ACCESS  not-accessible
               STATUS      current
               DESCRIPTION
                   "QCL table index."
               ::= {     sispm10403166lQosQCLStatusEntry 1}

    sispm10403166lQosQCLStatusUser OBJECT-TYPE
               SYNTAX      DisplayString
               MAX-ACCESS  read-only
               STATUS      current
               DESCRIPTION
                   "Indicates the QCL user."
               ::= {     sispm10403166lQosQCLStatusEntry 2 }

    sispm10403166lQosQCLStatusQCEId OBJECT-TYPE
               SYNTAX      DisplayString
               MAX-ACCESS  read-only
               STATUS      current
               DESCRIPTION
                  "Indicates the index of QCE."
               ::= {     sispm10403166lQosQCLStatusEntry 3}

    sispm10403166lQosQCLStatusFrameType OBJECT-TYPE
               SYNTAX      DisplayString
               MAX-ACCESS  read-only
               STATUS      current
               DESCRIPTION
                   "Indicates the type of frame to look for incomming frames.
                    Any: The QCE will match all frame type.
                    Ethernet: Only Ethernet frames (with Ether Type 0x600-0xFFFF)
                    are allowed.
                    LLC: Only (LLC) frames are allowed.
                    SNAP: Only (SNAP) frames are allowed.
                    IPv4: The QCE will match only IPV4 frames.
                    IPv6: The QCE will match only IPV6 frames."
               ::= {     sispm10403166lQosQCLStatusEntry 4}

    sispm10403166lQosQCLStatusPortlist OBJECT-TYPE
               SYNTAX      DisplayString
               MAX-ACCESS  read-only
               STATUS      current
               DESCRIPTION
                   "Indicates the list of ports configured with the QCE."
               ::= {     sispm10403166lQosQCLStatusEntry 5}

    sispm10403166lQosQCLStatusActionQueuePriority OBJECT-TYPE
               SYNTAX      DisplayString
               MAX-ACCESS  read-only
               STATUS      current
               DESCRIPTION
                   "Classified QoS class; if a frame matches the
                    QCE it will be put in the  queue."
               ::= {     sispm10403166lQosQCLStatusEntry 6}

    sispm10403166lQosQCLStatusActionDPL OBJECT-TYPE
               SYNTAX      DisplayString
               MAX-ACCESS  read-only
               STATUS      current
               DESCRIPTION
                   "Drop Precedence Level; if a frame matches the QCE then
                    DP level will set to value displayed under DPL column."
               ::= {     sispm10403166lQosQCLStatusEntry 7}

    sispm10403166lQosQCLStatusActionDSCP OBJECT-TYPE
               SYNTAX      DisplayString
               MAX-ACCESS  read-only
               STATUS      current
               DESCRIPTION
                   "If a frame matches the QCE then DSCP will be
                    classified with the value
                    displayed under DSCP column."
               ::= {     sispm10403166lQosQCLStatusEntry 8}

    sispm10403166lQosQCLStatusActionPCP OBJECT-TYPE
               SYNTAX      DisplayString
               MAX-ACCESS  read-only
               STATUS      current
               DESCRIPTION
                   "Classify PCP value.
                    Only support SERVAL."
               ::= {     sispm10403166lQosQCLStatusEntry 9}

    sispm10403166lQosQCLStatusActionDEL OBJECT-TYPE
               SYNTAX      DisplayString
               MAX-ACCESS  read-only
               STATUS      current
               DESCRIPTION
                   "Classify DEI value.
                    Only support SERVAL."
               ::= {     sispm10403166lQosQCLStatusEntry 10}

    sispm10403166lQosQCLStatusActionPolicy OBJECT-TYPE
               SYNTAX      DisplayString
               MAX-ACCESS  read-only
               STATUS      current
               DESCRIPTION
                   "Classify ACL Policy number.
                    "
               ::= {     sispm10403166lQosQCLStatusEntry 11}

    sispm10403166lQosQCLStatusConflict OBJECT-TYPE
               SYNTAX      DisplayString
               MAX-ACCESS  read-only
               STATUS      current
               DESCRIPTION
                   "Displays Conflict status of QCL entries."
               ::= {     sispm10403166lQosQCLStatusEntry 12}

--    sispm10403166lQosQCLStatusSwitch OBJECT-TYPE
--               SYNTAX      Integer32
--               MAX-ACCESS  read-only
--               STATUS      current
--               DESCRIPTION
--                   "Switch number for port members. -1:Any.
--                    Only support stacking switch."
--               ::= {     sispm10403166lQosQCLStatusEntry 13}

    sispm10403166lQosQCLStatusDMAC OBJECT-TYPE
               SYNTAX      DisplayString
               MAX-ACCESS  read-only
               STATUS      current
               DESCRIPTION
                   "Destination MAC address: Possible values are 'Unicast', 'Multicast', 'Broadcast' or 'Any'."
               ::= {     sispm10403166lQosQCLStatusEntry 14}

    sispm10403166lQosQCLStatusSMAC OBJECT-TYPE
               SYNTAX      DisplayString
               MAX-ACCESS  read-only
               STATUS      current
               DESCRIPTION
                   "Source MAC address: xx-xx-xx-xx-xx-xx or 'Any'."
               ::= {     sispm10403166lQosQCLStatusEntry 15}

    sispm10403166lQosQCLStatusTag OBJECT-TYPE
               SYNTAX      DisplayString
               MAX-ACCESS  read-only
               STATUS      current
               DESCRIPTION
                   "Value of Tag field can be 'Untagged', 'Tagged', 'C-Tagged', 'S-Tagged' or 'Any'."
               ::= {     sispm10403166lQosQCLStatusEntry 16}

    sispm10403166lQosQCLStatusVID OBJECT-TYPE
               SYNTAX      DisplayString
               MAX-ACCESS  read-only
               STATUS      current
               DESCRIPTION
                   "Valid value of VLAN ID can be any value in the range 1-4095 or 'Any'"
               ::= {     sispm10403166lQosQCLStatusEntry 17}

    sispm10403166lQosQCLStatusPCP OBJECT-TYPE
               SYNTAX      DisplayString
               MAX-ACCESS  read-only
               STATUS      current
               DESCRIPTION
                   "Valid value PCP are specific (0, 1, 2, 3, 4, 5, 6, 7) or range (0-1, 2-3, 4-5, 6-7, 0-3, 4-7) or 'Any'."
               ::= {     sispm10403166lQosQCLStatusEntry 18}

    sispm10403166lQosQCLStatusDEI OBJECT-TYPE
               SYNTAX      DisplayString
               MAX-ACCESS  read-only
               STATUS      current
               DESCRIPTION
                   "Valid value of DEI can be '0', '1' or 'Any'."
               ::= {     sispm10403166lQosQCLStatusEntry 19}

    sispm10403166lQosPortShaperTable OBJECT-TYPE
               SYNTAX      SEQUENCE OF     SISPM10403166LQosPortShaperEntry
               MAX-ACCESS  not-accessible
               STATUS      current
               DESCRIPTION
                   "INDEX for this table is ifIndex which is
                    equivalent to the panel port number."
               ::= {     sispm10403166lQosPortShapers 1 }

    sispm10403166lQosPortShaperEntry OBJECT-TYPE
               SYNTAX          SISPM10403166LQosPortShaperEntry
               MAX-ACCESS  not-accessible
               STATUS      current
               DESCRIPTION
                   "The Qos Port Shaper Entry."
               INDEX    {     ifIndex  }
               ::= {     sispm10403166lQosPortShaperTable 1 }

    SISPM10403166LQosPortShaperEntry             ::= SEQUENCE {
                sispm10403166lQosPortShaperQueue0Enable   AdminMode,
                sispm10403166lQosPortShaperQueue0Rate     Integer32,
                sispm10403166lQosPortShaperQueue0Unit     Integer32,
                sispm10403166lQosPortShaperQueue1Enable   AdminMode,
                sispm10403166lQosPortShaperQueue1Rate     Integer32,
                sispm10403166lQosPortShaperQueue1Unit     Integer32,
                sispm10403166lQosPortShaperQueue2Enable   AdminMode,
                sispm10403166lQosPortShaperQueue2Rate     Integer32,
                sispm10403166lQosPortShaperQueue2Unit     Integer32,
                sispm10403166lQosPortShaperQueue3Enable   AdminMode,
                sispm10403166lQosPortShaperQueue3Rate     Integer32,
                sispm10403166lQosPortShaperQueue3Unit     Integer32,
                sispm10403166lQosPortShaperQueue4Enable   AdminMode,
                sispm10403166lQosPortShaperQueue4Rate     Integer32,
                sispm10403166lQosPortShaperQueue4Unit     Integer32,
                sispm10403166lQosPortShaperQueue5Enable   AdminMode,
                sispm10403166lQosPortShaperQueue5Rate     Integer32,
                sispm10403166lQosPortShaperQueue5Unit     Integer32,
                sispm10403166lQosPortShaperQueue6Enable   AdminMode,
                sispm10403166lQosPortShaperQueue6Rate     Integer32,
                sispm10403166lQosPortShaperQueue6Unit     Integer32,
                sispm10403166lQosPortShaperQueue7Enable   AdminMode,
                sispm10403166lQosPortShaperQueue7Rate     Integer32,
                sispm10403166lQosPortShaperQueue7Unit     Integer32,
                sispm10403166lQosPortShaperEnable         AdminMode,
                sispm10403166lQosPortShaperRate           Integer32,
                sispm10403166lQosPortShaperRateType       Integer32
                }

    sispm10403166lQosPortShaperQueue0Enable OBJECT-TYPE
               SYNTAX      AdminMode
               MAX-ACCESS  read-write
               STATUS      current
               DESCRIPTION
                   "Controls whether the queue shaper is enabled on this switch port."
               DEFVAL  { disable }
               ::= {     sispm10403166lQosPortShaperEntry 3 }

    sispm10403166lQosPortShaperQueue0Rate OBJECT-TYPE
               SYNTAX      Integer32
               MAX-ACCESS  read-write
               STATUS      current
               DESCRIPTION
                   "Controls whether the queue shaper rate.
                    default: 500(Kbps)"
               ::= {     sispm10403166lQosPortShaperEntry 4 }

    sispm10403166lQosPortShaperQueue0Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sispm10403166lQosPortShaperEntry 5 }

    sispm10403166lQosPortShaperQueue1Enable OBJECT-TYPE
               SYNTAX      AdminMode
               MAX-ACCESS  read-write
               STATUS      current
               DESCRIPTION
                   "Controls whether the queue shaper is enabled on this switch port."
               DEFVAL  { disable }
               ::= {     sispm10403166lQosPortShaperEntry 6 }

    sispm10403166lQosPortShaperQueue1Rate OBJECT-TYPE
               SYNTAX      Integer32
               MAX-ACCESS  read-write
               STATUS      current
               DESCRIPTION
                   "Controls whether the queue shaper rate.
                    default: 500(Kbps)"
               ::= {     sispm10403166lQosPortShaperEntry 7 }

    sispm10403166lQosPortShaperQueue1Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sispm10403166lQosPortShaperEntry 8 }

    sispm10403166lQosPortShaperQueue2Enable OBJECT-TYPE
               SYNTAX      AdminMode
               MAX-ACCESS  read-write
               STATUS      current
               DESCRIPTION
                   "Controls whether the queue shaper is enabled on this switch port."
               DEFVAL  { disable }
               ::= {     sispm10403166lQosPortShaperEntry 9 }

    sispm10403166lQosPortShaperQueue2Rate OBJECT-TYPE
               SYNTAX      Integer32
               MAX-ACCESS  read-write
               STATUS      current
               DESCRIPTION
                   "Controls whether the queue shaper rate.
                    default: 500(Kbps)"
               ::= {     sispm10403166lQosPortShaperEntry 10 }

    sispm10403166lQosPortShaperQueue2Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sispm10403166lQosPortShaperEntry 11 }

    sispm10403166lQosPortShaperQueue3Enable OBJECT-TYPE
               SYNTAX      AdminMode
               MAX-ACCESS  read-write
               STATUS      current
               DESCRIPTION
                   "Controls whether the queue shaper is enabled on this switch port."
               DEFVAL  { disable }
               ::= {     sispm10403166lQosPortShaperEntry 12 }

    sispm10403166lQosPortShaperQueue3Rate OBJECT-TYPE
               SYNTAX      Integer32
               MAX-ACCESS  read-write
               STATUS      current
               DESCRIPTION
                   "Controls whether the queue shaper rate.
                    default: 500(Kbps)"
               ::= {     sispm10403166lQosPortShaperEntry 13 }

    sispm10403166lQosPortShaperQueue3Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sispm10403166lQosPortShaperEntry 14 }

    sispm10403166lQosPortShaperQueue4Enable OBJECT-TYPE
               SYNTAX      AdminMode
               MAX-ACCESS  read-write
               STATUS      current
               DESCRIPTION
                   "Controls whether the queue shaper is enabled on this switch port."
               DEFVAL  { disable }
               ::= {     sispm10403166lQosPortShaperEntry 15 }

    sispm10403166lQosPortShaperQueue4Rate OBJECT-TYPE
               SYNTAX      Integer32
               MAX-ACCESS  read-write
               STATUS      current
               DESCRIPTION
                   "Controls whether the queue shaper rate.
                    default: 500(Kbps)"
               ::= {     sispm10403166lQosPortShaperEntry 16 }

    sispm10403166lQosPortShaperQueue4Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sispm10403166lQosPortShaperEntry 17 }

    sispm10403166lQosPortShaperQueue5Enable OBJECT-TYPE
               SYNTAX      AdminMode
               MAX-ACCESS  read-write
               STATUS      current
               DESCRIPTION
                   "Controls whether the queue shaper is enabled on this switch port."
               DEFVAL  { disable }
               ::= {     sispm10403166lQosPortShaperEntry 18 }

    sispm10403166lQosPortShaperQueue5Rate OBJECT-TYPE
               SYNTAX      Integer32
               MAX-ACCESS  read-write
               STATUS      current
               DESCRIPTION
                   "Controls whether the queue shaper rate.
                    default: 500(Kbps)"
               ::= {     sispm10403166lQosPortShaperEntry 19 }

    sispm10403166lQosPortShaperQueue5Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sispm10403166lQosPortShaperEntry 20 }

    sispm10403166lQosPortShaperQueue6Enable OBJECT-TYPE
               SYNTAX      AdminMode
               MAX-ACCESS  read-write
               STATUS      current
               DESCRIPTION
                   "Controls whether the queue shaper is enabled on this switch port."
               DEFVAL  { disable }
               ::= {     sispm10403166lQosPortShaperEntry 21 }

    sispm10403166lQosPortShaperQueue6Rate OBJECT-TYPE
               SYNTAX      Integer32
               MAX-ACCESS  read-write
               STATUS      current
               DESCRIPTION
                   "Controls whether the queue shaper rate.
                    default: 500(Kbps)"
               ::= {     sispm10403166lQosPortShaperEntry 22 }

    sispm10403166lQosPortShaperQueue6Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sispm10403166lQosPortShaperEntry 23 }

    sispm10403166lQosPortShaperQueue7Enable OBJECT-TYPE
               SYNTAX      AdminMode
               MAX-ACCESS  read-write
               STATUS      current
               DESCRIPTION
                   "Controls whether the queue shaper is enabled on this switch port."
               DEFVAL  { disable }
               ::= {     sispm10403166lQosPortShaperEntry 24 }

    sispm10403166lQosPortShaperQueue7Rate OBJECT-TYPE
               SYNTAX      Integer32
               MAX-ACCESS  read-write
               STATUS      current
               DESCRIPTION
                   "Controls whether the queue shaper rate.
                    default: 500(Kbps)"
               ::= {     sispm10403166lQosPortShaperEntry 25 }

    sispm10403166lQosPortShaperQueue7Unit OBJECT-TYPE
               SYNTAX      Integer32(0|1)
               MAX-ACCESS  read-write
               STATUS      current
               DESCRIPTION
                   "Controls the unit of measure for the queue shaper rate as kbps or Mbps.
                    range:
                    0:kbs
                    1:Mbps
                    default: 0(kbps)"
               ::= {     sispm10403166lQosPortShaperEntry 26 }

    sispm10403166lQosPortShaperEnable OBJECT-TYPE
               SYNTAX      AdminMode
               MAX-ACCESS  read-write
               STATUS      current
               DESCRIPTION
                   "Controls whether the port shaper is enabled."
               DEFVAL  { disable }
               ::= {     sispm10403166lQosPortShaperEntry 27 }

    sispm10403166lQosPortShaperRate OBJECT-TYPE
               SYNTAX      Integer32
               MAX-ACCESS  read-write
               STATUS      current
               DESCRIPTION
                   "Controls the rate for the port shaper.
                    default: 500 kbps."
               ::= {     sispm10403166lQosPortShaperEntry 28 }

    sispm10403166lQosPortShaperRateType OBJECT-TYPE
               SYNTAX      Integer32(0|1)
               MAX-ACCESS  read-write
               STATUS      current
               DESCRIPTION
                   "The rate type of the port shaper.
                    0:Line
                    1:Data"
               ::= {     sispm10403166lQosPortShaperEntry 29 }

    sispm10403166lQosPortSchedulersTable OBJECT-TYPE
               SYNTAX      SEQUENCE OF     SISPM10403166LQosPortSchedulersEntry
               MAX-ACCESS  not-accessible
               STATUS      current
               DESCRIPTION
                   "INDEX for this table is ifIndex which is
                    equivalent to the panel port number."
               ::= {     sispm10403166lQosPortSchedulers 1 }

    sispm10403166lQosPortSchedulersEntry OBJECT-TYPE
               SYNTAX          SISPM10403166LQosPortSchedulersEntry
               MAX-ACCESS  not-accessible
               STATUS      current
               DESCRIPTION
                   "The Qos Port Shaper Entry."
               INDEX    {     ifIndex  }
               ::= {     sispm10403166lQosPortSchedulersTable 1 }

    SISPM10403166LQosPortSchedulersEntry             ::= SEQUENCE {
                sispm10403166lQosPortSchedulersMode     Integer32,
                sispm10403166lQosPortSchedulersQ0Weight Integer32,
                sispm10403166lQosPortSchedulersQ1Weight Integer32,
                sispm10403166lQosPortSchedulersQ2Weight Integer32,
                sispm10403166lQosPortSchedulersQ3Weight Integer32,
                sispm10403166lQosPortSchedulersQ4Weight Integer32,
                sispm10403166lQosPortSchedulersQ5Weight Integer32,
                sispm10403166lQosPortSchedulersQ6Weight Integer32,
                sispm10403166lQosPortSchedulersQ7Weight Integer32
                }

    sispm10403166lQosPortSchedulersMode OBJECT-TYPE
               SYNTAX      Integer32(0|8)
               MAX-ACCESS  read-write
               STATUS      current
               DESCRIPTION
                   "0:Strict Priority
                    8:Weighted"
               ::= {     sispm10403166lQosPortSchedulersEntry 2 }

    sispm10403166lQosPortSchedulersQ0Weight OBJECT-TYPE
               SYNTAX      Integer32(1..100)
               MAX-ACCESS  read-write
               STATUS      current
               DESCRIPTION
                   "Controls the weight for this queue. This value is restricted to 1-100."
               ::= {     sispm10403166lQosPortSchedulersEntry 3 }

    sispm10403166lQosPortSchedulersQ1Weight OBJECT-TYPE
               SYNTAX      Integer32(1..100)
               MAX-ACCESS  read-write
               STATUS      current
               DESCRIPTION
                   "Controls the weight for this queue. This value is restricted to 1-100."
               ::= {     sispm10403166lQosPortSchedulersEntry 4 }

    sispm10403166lQosPortSchedulersQ2Weight OBJECT-TYPE
               SYNTAX      Integer32(1..100)
               MAX-ACCESS  read-write
               STATUS      current
               DESCRIPTION
                   "Controls the weight for this queue. This value is restricted to 1-100."
               ::= {     sispm10403166lQosPortSchedulersEntry 5 }

    sispm10403166lQosPortSchedulersQ3Weight OBJECT-TYPE
               SYNTAX      Integer32(1..100)
               MAX-ACCESS  read-write
               STATUS      current
               DESCRIPTION
                   "Controls the weight for this queue. This value is restricted to 1-100."
               ::= {     sispm10403166lQosPortSchedulersEntry 6 }

    sispm10403166lQosPortSchedulersQ4Weight OBJECT-TYPE
               SYNTAX      Integer32(1..100)
               MAX-ACCESS  read-write
               STATUS      current
               DESCRIPTION
                   "Controls the weight for this queue. This value is restricted to 1-100."
               ::= {     sispm10403166lQosPortSchedulersEntry 7 }

    sispm10403166lQosPortSchedulersQ5Weight OBJECT-TYPE
               SYNTAX      Integer32(1..100)
               MAX-ACCESS  read-write
               STATUS      current
               DESCRIPTION
                   "Controls the weight for this queue. This value is restricted to 1-100."
               ::= {     sispm10403166lQosPortSchedulersEntry 8 }

    sispm10403166lQosPortSchedulersQ6Weight OBJECT-TYPE
               SYNTAX      Integer32(1..100)
               MAX-ACCESS  read-write
               STATUS      current
               DESCRIPTION
                   "Controls the weight for this queue. This value is restricted to 1-100."
               ::= {     sispm10403166lQosPortSchedulersEntry 9 }

    sispm10403166lQosPortSchedulersQ7Weight OBJECT-TYPE
               SYNTAX      Integer32(1..100)
               MAX-ACCESS  read-write
               STATUS      current
               DESCRIPTION
                   "Controls the weight for this queue. This value is restricted to 1-100."
               ::= {     sispm10403166lQosPortSchedulersEntry 10 }

-- =======================================================================================================================
--sispm10403166lBroadcastStormProtection                                                  OBJECT IDENTIFIER ::= { sispm10403166lConfiguration 11 }
--
--sispm10403166lBroadcastStormProtectionConfigurationTable OBJECT-TYPE
--   SYNTAX      SEQUENCE OF SISPM10403166LBroadcastStormProtectionConfigurationEntry
--   MAX-ACCESS  not-accessible
--   STATUS      current
--   DESCRIPTION
--       " Show Broadcast Storm Protection configurations. "
--   ::= { sispm10403166lBroadcastStormProtection 1 }
--
--sispm10403166lBroadcastStormProtectionConfigurationEntry OBJECT-TYPE
--   SYNTAX      SISPM10403166LBroadcastStormProtectionConfigurationEntry
--   MAX-ACCESS  not-accessible
--   STATUS      current
--   DESCRIPTION
--       ""
--   INDEX    { sispm10403166lBroadcastStormProtectionConfPort  }
--   ::= { sispm10403166lBroadcastStormProtectionConfigurationTable 1 }
--
--SISPM10403166LBroadcastStormProtectionConfigurationEntry ::= SEQUENCE {
--   sispm10403166lBroadcastStormProtectionConfPort	    Integer32,
--   sispm10403166lBroadcastStormProtectionConfMode	    INTEGER,
--   sispm10403166lBroadcastStormProtectionConfAction	Integer32,
--   sispm10403166lBroadcastStormProtectionConfPPS		Integer32,
--   sispm10403166lBroadcastStormProtectionConfTimer	Integer32,
--   sispm10403166lBroadcastStormProtectionConfstatus	DisplayString
--}
--
--sispm10403166lBroadcastStormProtectionConfPort OBJECT-TYPE
--   SYNTAX      Integer32 (1..4095)
--   MAX-ACCESS  not-accessible
--   STATUS      current
--   DESCRIPTION
--       " port, range : 1 - port number. "
--   ::= { sispm10403166lBroadcastStormProtectionConfigurationEntry 1 }
--
--sispm10403166lBroadcastStormProtectionConfMode OBJECT-TYPE
--   SYNTAX      INTEGER { disable(0), enable(1)}
--   MAX-ACCESS  read-write
--   STATUS      current
--   DESCRIPTION
--       " Configure broadcast storm protection port mode.
--         0: disable,
--         1: enable
--         default: disable. "
--   ::= { sispm10403166lBroadcastStormProtectionConfigurationEntry 2 }
--
--sispm10403166lBroadcastStormProtectionConfAction OBJECT-TYPE
--   SYNTAX      Integer32 (0..2)
--   MAX-ACCESS  read-write
--   STATUS      current
--   DESCRIPTION
--       " Configure broadcast storm protection port action.
--         0: Shutdown port,
--         1: Shutdown port and Log,
--         2: Log Only,
--         default: Shutdown port. "
--   ::= { sispm10403166lBroadcastStormProtectionConfigurationEntry 3 }
--
--sispm10403166lBroadcastStormProtectionConfPPS OBJECT-TYPE
--   SYNTAX      Integer32 (0..1000000)
--   MAX-ACCESS  read-write
--   STATUS      current
--   DESCRIPTION
--       " Configure broadcast storm protection pps.
--         default: 0. "
--   ::= { sispm10403166lBroadcastStormProtectionConfigurationEntry 4 }
--
--sispm10403166lBroadcastStormProtectionConfTimer OBJECT-TYPE
--   SYNTAX      Integer32 (0..65535)
--   MAX-ACCESS  read-write
--   STATUS      current
--   DESCRIPTION
--       "Configure broadcast storm protection timer(seconds)
--        default: 300(seconds). "
--   ::= { sispm10403166lBroadcastStormProtectionConfigurationEntry 5 }
--
--sispm10403166lBroadcastStormProtectionConfstatus OBJECT-TYPE
--   SYNTAX      DisplayString
--   MAX-ACCESS  read-only
--   STATUS      current
--   DESCRIPTION
--       " Show broadcast storm protection status. "
--   ::= { sispm10403166lBroadcastStormProtectionConfigurationEntry 6 }
--
-- =======================================================================================================================
sispm10403166lLoopProtection                                                  OBJECT IDENTIFIER ::= { sispm10403166lConfiguration 12 }

sispm10403166lLoopProtectionConfig                                            OBJECT IDENTIFIER ::= { sispm10403166lLoopProtection 1 }

sispm10403166lLoopProtectionGlobalEnable OBJECT-TYPE
   SYNTAX      Integer32(0|1)
   MAX-ACCESS  read-write
   STATUS      current
   DESCRIPTION
       "Configure loop protection mode.
        0: disable,
        1: enable,
        default: disable. "
   ::= { sispm10403166lLoopProtectionConfig 1 }

sispm10403166lLoopProtectionTranmisstionTime OBJECT-TYPE
   SYNTAX      Integer32(1..10)
   MAX-ACCESS  read-write
   STATUS      current
   DESCRIPTION
       "Configure loop protection transmit interval.
        default: 5,
        range: 1-10. "
   ::= { sispm10403166lLoopProtectionConfig 2 }

sispm10403166lLoopProtectionShutdownTime OBJECT-TYPE
   SYNTAX      Integer32(0..604800)
   MAX-ACCESS  read-write
   STATUS      current
   DESCRIPTION
       "Configure loop protection shutdown time.
        default: 180,
        range: 0-604800. "
   ::= { sispm10403166lLoopProtectionConfig 3 }

sispm10403166lLoopProtectionConfigurationTable OBJECT-TYPE
   SYNTAX      SEQUENCE OF SISPM10403166LLoopProtectionConfigurationEntry
   MAX-ACCESS  not-accessible
   STATUS      current
   DESCRIPTION
       " Show Loop Protection configurations. "
   ::= { sispm10403166lLoopProtectionConfig 4 }

sispm10403166lLoopProtectionConfigurationEntry OBJECT-TYPE
   SYNTAX      SISPM10403166LLoopProtectionConfigurationEntry
   MAX-ACCESS  not-accessible
   STATUS      current
   DESCRIPTION
       " "
   INDEX    { sispm10403166lLoopProtectionConfPort  }
   ::= { sispm10403166lLoopProtectionConfigurationTable 1 }

SISPM10403166LLoopProtectionConfigurationEntry ::= SEQUENCE {
   sispm10403166lLoopProtectionConfPort	    Integer32,
   sispm10403166lLoopProtectionConfEnable	Integer32,
   sispm10403166lLoopProtectionConfAction	Integer32,
   sispm10403166lLoopProtectionConfTxmode	Integer32
}

sispm10403166lLoopProtectionConfPort OBJECT-TYPE
   SYNTAX      Integer32 (1..4095)
   MAX-ACCESS  not-accessible
   STATUS      current
   DESCRIPTION
       " port, range : 1 - port number. "
   ::= { sispm10403166lLoopProtectionConfigurationEntry 1 }

sispm10403166lLoopProtectionConfEnable OBJECT-TYPE
   SYNTAX      Integer32(0|1)
   MAX-ACCESS  read-write
   STATUS      current
   DESCRIPTION
       "Configure loop protection port mode.
        0: disable,
        1: enable,
        default: enable. "
   ::= { sispm10403166lLoopProtectionConfigurationEntry 2 }

sispm10403166lLoopProtectionConfAction OBJECT-TYPE
   SYNTAX      Integer32(0..2)
   MAX-ACCESS  read-write
   STATUS      current
   DESCRIPTION
       " Configure loop protection port action.
         0: Shutdown port,
         1: Shutdown port and Log,
         2: Log Only,
         default: Shutdown port. "
   ::= { sispm10403166lLoopProtectionConfigurationEntry 3 }

sispm10403166lLoopProtectionConfTxmode OBJECT-TYPE
   SYNTAX      Integer32(0|1)
   MAX-ACCESS  read-write
   STATUS      current
   DESCRIPTION
       "Configure loop protection port transmit mode.
        0: disable,
        1: enable,
        default: enable. "
   ::= { sispm10403166lLoopProtectionConfigurationEntry 4 }

sispm10403166lLoopProtectionStatusTable OBJECT-TYPE
   SYNTAX      SEQUENCE OF SISPM10403166LLoopProtectionStatusEntry
   MAX-ACCESS  not-accessible
   STATUS      current
   DESCRIPTION
       " Show Loop Protection Status. "
   ::= { sispm10403166lLoopProtection 2 }

sispm10403166lLoopProtectionStatusEntry OBJECT-TYPE
   SYNTAX      SISPM10403166LLoopProtectionStatusEntry
   MAX-ACCESS  not-accessible
   STATUS      current
   DESCRIPTION
       " "
   INDEX    { sispm10403166lLoopProtectionStatusPort  }
   ::= { sispm10403166lLoopProtectionStatusTable 1 }

SISPM10403166LLoopProtectionStatusEntry ::= SEQUENCE {
   sispm10403166lLoopProtectionStatusPort	       Integer32,
   sispm10403166lLoopProtectionStatusAction	       DisplayString,
   sispm10403166lLoopProtectionStatusTransmit	   DisplayString,
   sispm10403166lLoopProtectionStatusLoops	       Integer32,
   sispm10403166lLoopProtectionStatusStatus	       DisplayString,
   sispm10403166lLoopProtectionStatusLoop	       DisplayString,
   sispm10403166lLoopProtectionStatusTimeLastLoop  DisplayString
}

sispm10403166lLoopProtectionStatusPort OBJECT-TYPE
   SYNTAX      Integer32 (1..4095)
   MAX-ACCESS  not-accessible
   STATUS      current
   DESCRIPTION
       " port, range : 1 - port number. "
   ::= { sispm10403166lLoopProtectionStatusEntry 1 }

sispm10403166lLoopProtectionStatusAction OBJECT-TYPE
   SYNTAX      DisplayString
   MAX-ACCESS  read-only
   STATUS      current
   DESCRIPTION
       " The currently configured port action. "
   ::= { sispm10403166lLoopProtectionStatusEntry 2 }

sispm10403166lLoopProtectionStatusTransmit OBJECT-TYPE
   SYNTAX      DisplayString
   MAX-ACCESS  read-only
   STATUS      current
   DESCRIPTION
       " The currently configured port transmit mode. "
   ::= { sispm10403166lLoopProtectionStatusEntry 3 }

sispm10403166lLoopProtectionStatusLoops OBJECT-TYPE
   SYNTAX      Integer32 (0..1000000)
   MAX-ACCESS  read-only
   STATUS      current
   DESCRIPTION
       " The number of loops detected on this port. "
   ::= { sispm10403166lLoopProtectionStatusEntry 4 }

sispm10403166lLoopProtectionStatusStatus OBJECT-TYPE
   SYNTAX      DisplayString
   MAX-ACCESS  read-only
   STATUS      current
   DESCRIPTION
       " The current loop protection status of the port. "
   ::= { sispm10403166lLoopProtectionStatusEntry 5 }

sispm10403166lLoopProtectionStatusLoop OBJECT-TYPE
   SYNTAX      DisplayString
   MAX-ACCESS  read-only
   STATUS      current
   DESCRIPTION
       " Whether a loop is currently detected on the port. "
   ::= { sispm10403166lLoopProtectionStatusEntry 6 }

sispm10403166lLoopProtectionStatusTimeLastLoop OBJECT-TYPE
   SYNTAX      DisplayString
   MAX-ACCESS  read-only
   STATUS      current
   DESCRIPTION
       " The time of the last loop event detected. "
   ::= { sispm10403166lLoopProtectionStatusEntry 7 }
-- =======================================================================================================================
sispm10403166lPoe                                                           OBJECT IDENTIFIER ::= { sispm10403166lConfiguration 13 }

sispm10403166lPoeStatus                                            OBJECT IDENTIFIER ::= { sispm10403166lPoe 1 }

sispm10403166lPoeStatusTable OBJECT-TYPE
   SYNTAX      SEQUENCE OF SISPM10403166LPoeStatusEntry
   MAX-ACCESS  not-accessible
   STATUS      current
   DESCRIPTION
       " Configure PoE Scheduling Table. "
   ::= { sispm10403166lPoeStatus 1 }

sispm10403166lPoeStatusEntry OBJECT-TYPE
   SYNTAX      SISPM10403166LPoeStatusEntry
   MAX-ACCESS  not-accessible
   STATUS      current
   DESCRIPTION
       " "
   INDEX    { sispm10403166lPoeStatusLocalPort }
   ::= { sispm10403166lPoeStatusTable 1 }

SISPM10403166LPoeStatusEntry ::= SEQUENCE {
   sispm10403166lPoeStatusLocalPort              Integer32,
   sispm10403166lPoeStatusPDclass	          DisplayString,
   sispm10403166lPoeStatusPowerRequested	  DisplayString,
   sispm10403166lPoeStatusPowerAllocated     DisplayString,
   sispm10403166lPoeStatusPowerUsed          DisplayString,
   sispm10403166lPoeStatusCurrentUsed        DisplayString,
   sispm10403166lPoeStatusPriority           DisplayString,
   sispm10403166lPoeStatusPortStatus         DisplayString
}

sispm10403166lPoeStatusLocalPort OBJECT-TYPE
   SYNTAX      Integer32 (1..10)
   MAX-ACCESS  not-accessible
   STATUS      current
   DESCRIPTION
       "Local port Index."
   ::= { sispm10403166lPoeStatusEntry 1 }


sispm10403166lPoeStatusPDclass OBJECT-TYPE
   SYNTAX      DisplayString
   MAX-ACCESS  read-only
   STATUS      current
   DESCRIPTION
       " Indicates the QCL user.
         0: Max. power 15.4 W,
         1: Max. power 4.0 W,
         2: Max. power 7.0 W,
         3: Max. power 15.4 W,
         4: Max. power 30.0 W. "
   ::= { sispm10403166lPoeStatusEntry 2 }

sispm10403166lPoeStatusPowerRequested OBJECT-TYPE
   SYNTAX      DisplayString
   MAX-ACCESS  read-only
   STATUS      current
   DESCRIPTION
      " The Power Requested shows the requested amount of power the PD wants to be reserved. "
   ::= { sispm10403166lPoeStatusEntry 3}

sispm10403166lPoeStatusPowerAllocated OBJECT-TYPE
   SYNTAX      DisplayString
   MAX-ACCESS  read-only
   STATUS      current
   DESCRIPTION
      " The Power Allocated shows the amount of power the switch has allocated for the PD. "
   ::= { sispm10403166lPoeStatusEntry 4}

sispm10403166lPoeStatusPowerUsed OBJECT-TYPE
   SYNTAX      DisplayString
   MAX-ACCESS  read-only
   STATUS      current
   DESCRIPTION
      " The Power Used shows how much power the PD currently is using. "
   ::= { sispm10403166lPoeStatusEntry 5}

sispm10403166lPoeStatusCurrentUsed OBJECT-TYPE
   SYNTAX      DisplayString
   MAX-ACCESS  read-only
   STATUS      current
   DESCRIPTION
      " The Power Used shows how much current the PD currently is using. "
   ::= { sispm10403166lPoeStatusEntry 6}

sispm10403166lPoeStatusPriority OBJECT-TYPE
   SYNTAX      DisplayString
   MAX-ACCESS  read-only
   STATUS      current
   DESCRIPTION
      " The Priority shows the port's priority configured by the user.  "
   ::= { sispm10403166lPoeStatusEntry 7}

sispm10403166lPoeStatusPortStatus OBJECT-TYPE
   SYNTAX      DisplayString
   MAX-ACCESS  read-only
   STATUS      current
   DESCRIPTION
      " The Port Status shows the port's status.  "
   ::= { sispm10403166lPoeStatusEntry 8}

sispm10403166lPoeStatusTotalTable OBJECT-TYPE
   SYNTAX      SEQUENCE OF SISPM10403166LPoeStatusTotalEntry
   MAX-ACCESS  not-accessible
   STATUS      current
   DESCRIPTION
       " Configure PoE Scheduling Total Table. "
   ::= { sispm10403166lPoeStatus 2 }

sispm10403166lPoeStatusTotalEntry OBJECT-TYPE
   SYNTAX      SISPM10403166LPoeStatusTotalEntry
   MAX-ACCESS  not-accessible
   STATUS      current
   DESCRIPTION
       " "
   INDEX    { sispm10403166lPoeStatusSwitchIndex }
   ::= { sispm10403166lPoeStatusTotalTable 1 }

SISPM10403166LPoeStatusTotalEntry ::= SEQUENCE {
   sispm10403166lPoeStatusSwitchIndex            Integer32,
   sispm10403166lPoeStatusTotalPowerRequested    DisplayString,
   sispm10403166lPoeStatusTotalPowerAllocated    DisplayString,
   sispm10403166lPoeStatusTotalPowerUsed         DisplayString,
   sispm10403166lPoeStatusTotalCurrentUsed       DisplayString
}

sispm10403166lPoeStatusSwitchIndex OBJECT-TYPE
   SYNTAX      Integer32 (1..16)
   MAX-ACCESS  not-accessible
   STATUS      current
   DESCRIPTION
       "Switch Index."
   ::= { sispm10403166lPoeStatusTotalEntry 1 }

sispm10403166lPoeStatusTotalPowerRequested OBJECT-TYPE
   SYNTAX      DisplayString
   MAX-ACCESS  read-only
   STATUS      current
   DESCRIPTION
      " Total Power Requested."
   ::= { sispm10403166lPoeStatusTotalEntry 2}

sispm10403166lPoeStatusTotalPowerAllocated OBJECT-TYPE
   SYNTAX      DisplayString
   MAX-ACCESS  read-only
   STATUS      current
   DESCRIPTION
      " Total Power allocated."
   ::= { sispm10403166lPoeStatusTotalEntry 3}

sispm10403166lPoeStatusTotalPowerUsed OBJECT-TYPE
   SYNTAX      DisplayString
   MAX-ACCESS  read-only
   STATUS      current
   DESCRIPTION
      " Total Power Used."
   ::= { sispm10403166lPoeStatusTotalEntry 4}

sispm10403166lPoeStatusTotalCurrentUsed OBJECT-TYPE
   SYNTAX      DisplayString
   MAX-ACCESS  read-only
   STATUS      current
   DESCRIPTION
      " Total Current Used."
   ::= { sispm10403166lPoeStatusTotalEntry 5}


sispm10403166lPoePowerDelay                                                 OBJECT IDENTIFIER ::= { sispm10403166lPoe 2 }

sispm10403166lPoePowerDelayTable OBJECT-TYPE
   SYNTAX      SEQUENCE OF SISPM10403166LPoePowerDelayEntry
   MAX-ACCESS  not-accessible
   STATUS      current
   DESCRIPTION
       " Configure PoE Power Delay mode. "
   ::= { sispm10403166lPoePowerDelay 1 }

sispm10403166lPoePowerDelayEntry OBJECT-TYPE
   SYNTAX      SISPM10403166LPoePowerDelayEntry
   MAX-ACCESS  not-accessible
   STATUS      current
   DESCRIPTION
       " "
   INDEX    { sispm10403166lPoePowerDelayPort  }
   ::= { sispm10403166lPoePowerDelayTable 1 }

SISPM10403166LPoePowerDelayEntry ::= SEQUENCE {
   sispm10403166lPoePowerDelayPort	        Integer32,
   sispm10403166lPoePowerDelayMode	        Integer32,
   sispm10403166lPoePowerDelayTime	        Integer32
}

sispm10403166lPoePowerDelayPort OBJECT-TYPE
   SYNTAX      Integer32 (1..4094)
   MAX-ACCESS  not-accessible
   STATUS      current
   DESCRIPTION
       " port, range : 1 - port number. "
   ::= { sispm10403166lPoePowerDelayEntry 1 }

sispm10403166lPoePowerDelayMode OBJECT-TYPE
   SYNTAX      Integer32(0|1)
   MAX-ACCESS  read-write
   STATUS      current
   DESCRIPTION
       "Turn on / off the power delay function,
        0: disable,
        1: enable,
        default: disable. "
   ::= { sispm10403166lPoePowerDelayEntry 2 }

sispm10403166lPoePowerDelayTime OBJECT-TYPE
   SYNTAX      Integer32(0..300)
   MAX-ACCESS  read-write
   STATUS      current
   DESCRIPTION
       "set Delay Time,
        default: 0,
        range: 0-300 sec. "
   ::= { sispm10403166lPoePowerDelayEntry 3 }

sispm10403166lPoeAutoPowerReset                                                 OBJECT IDENTIFIER ::= { sispm10403166lPoe 3 }

sispm10403166lPoeAutoPowerResetPingCheck OBJECT-TYPE
   SYNTAX      INTEGER { disable(0), enable(1) }
   MAX-ACCESS  read-write
   STATUS      current
   DESCRIPTION
       "connection between PoE port and power device.
        0: disable,
        1: enable,
        default: disable. "
   ::= { sispm10403166lPoeAutoPowerReset 1 }

sispm10403166lPoeAutoPowerResetTable OBJECT-TYPE
   SYNTAX      SEQUENCE OF SISPM10403166LPoeAutoPowerResetEntry
   MAX-ACCESS  not-accessible
   STATUS      current
   DESCRIPTION
       " Configure PoE Auto check mode. "
   ::= { sispm10403166lPoeAutoPowerReset 2 }

sispm10403166lPoeAutoPowerResetEntry OBJECT-TYPE
   SYNTAX      SISPM10403166LPoeAutoPowerResetEntry
   MAX-ACCESS  not-accessible
   STATUS      current
   DESCRIPTION
       " "
   INDEX    { sispm10403166lPoeAutoPowerResetPort  }
   ::= { sispm10403166lPoeAutoPowerResetTable 1 }

SISPM10403166LPoeAutoPowerResetEntry ::= SEQUENCE {
   sispm10403166lPoeAutoPowerResetPort	   Integer32,
   sispm10403166lPoeAutoPowerResetPingIPAddress  DisplayString,
   sispm10403166lPoeAutoPowerResetStartupTime    Integer32,
   sispm10403166lPoeAutoPowerResetIntervalTime   Integer32,
   sispm10403166lPoeAutoPowerResetRetryTime      Integer32,
   sispm10403166lPoeAutoPowerResetFailureLog     DisplayString,
   sispm10403166lPoeAutoPowerResetFailureAction  INTEGER,
   sispm10403166lPoeAutoPowerResetRebootTime     Integer32,
   sispm10403166lPoeAutoPowerResetMaxRebootTimes     Integer32
}

sispm10403166lPoeAutoPowerResetPort OBJECT-TYPE
   SYNTAX      Integer32(1..4094)
   MAX-ACCESS  not-accessible
   STATUS      current
   DESCRIPTION
       " port, range : 1 - port number. "
   ::= { sispm10403166lPoeAutoPowerResetEntry 1 }

sispm10403166lPoeAutoPowerResetPingIPAddress OBJECT-TYPE
   SYNTAX      DisplayString
   MAX-ACCESS  read-write
   STATUS      current
   DESCRIPTION
       "IP Address the system should ping.
        default: 0.0.0.0 . "
   ::= { sispm10403166lPoeAutoPowerResetEntry 2 }

sispm10403166lPoeAutoPowerResetStartupTime OBJECT-TYPE
   SYNTAX      Integer32(30..600)
   MAX-ACCESS  read-write
   STATUS      current
   DESCRIPTION
       "When PD has been start up, the Switch will wait Start up time to do PoE Auto Checking. default: 60, range: 30-600 sec. "
   ::= { sispm10403166lPoeAutoPowerResetEntry 3 }

sispm10403166lPoeAutoPowerResetIntervalTime OBJECT-TYPE
   SYNTAX      Integer32(10..120)
   MAX-ACCESS  read-write
   STATUS      current
   DESCRIPTION
       "Device will send checking message to PD each interval time.
        default: 30,
        range: 10-120 sec.  "
   ::= { sispm10403166lPoeAutoPowerResetEntry 4 }

sispm10403166lPoeAutoPowerResetRetryTime OBJECT-TYPE
   SYNTAX      Integer32(1..5)
   MAX-ACCESS  read-write
   STATUS      current
   DESCRIPTION
       "It will retry to send detection again.
        default: 3,
        range: 1-5.  "
   ::= { sispm10403166lPoeAutoPowerResetEntry 5 }

sispm10403166lPoeAutoPowerResetFailureLog OBJECT-TYPE
   SYNTAX      DisplayString
   MAX-ACCESS  read-only
   STATUS      current
   DESCRIPTION
       "Failure loggings counter. "
   ::= { sispm10403166lPoeAutoPowerResetEntry 6 }

sispm10403166lPoeAutoPowerResetFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { sispm10403166lPoeAutoPowerResetEntry 7 }

sispm10403166lPoeAutoPowerResetRebootTime OBJECT-TYPE
   SYNTAX      Integer32(3..120)
   MAX-ACCESS  read-write
   STATUS      current
   DESCRIPTION
       "When PD has been rebooted, the PoE port restored power after the specified time.
        default: 15,
        range: 3-120 sec. "
   ::= { sispm10403166lPoeAutoPowerResetEntry 8 }

sispm10403166lPoeAutoPowerResetMaxRebootTimes OBJECT-TYPE
   SYNTAX      Integer32(0..10)
   MAX-ACCESS  read-write
   STATUS      current
   DESCRIPTION
        "When Failure Action is Reboot Remote PD, it limits times of Reboot.
         default: 3,
         range: 0-10. 0 means without reboot limits."
   ::= { sispm10403166lPoeAutoPowerResetEntry 10 }

sispm10403166lPoeScheduling                                                 OBJECT IDENTIFIER ::= { sispm10403166lPoe 4 }

sispm10403166lPoeSchedulingProfileNumber OBJECT-TYPE
   SYNTAX      Integer32
   MAX-ACCESS  read-write
   STATUS      current
   DESCRIPTION
       "Specify the PoE Profile Number that want to configure. Range:1-16"
   ::= { sispm10403166lPoeScheduling 1 }

sispm10403166lPoeSchedulingPorofileName OBJECT-TYPE
   SYNTAX      DisplayString
   MAX-ACCESS  read-write
   STATUS      current
   DESCRIPTION
       "Profile Name. Maximum length:32."
   ::= { sispm10403166lPoeScheduling 2 }

sispm10403166lPoeSchedulingTimeTable OBJECT-TYPE
   SYNTAX      SEQUENCE OF SISPM10403166LPoeSchedulingTimeEntry
   MAX-ACCESS  not-accessible
   STATUS      current
   DESCRIPTION
       " Show Poe Scheduling Time Config. "
   ::= { sispm10403166lPoeScheduling 3 }

sispm10403166lPoeSchedulingTimeEntry OBJECT-TYPE
   SYNTAX      SISPM10403166LPoeSchedulingTimeEntry
   MAX-ACCESS  not-accessible
   STATUS      current
   DESCRIPTION
       " "
   INDEX    { sispm10403166lPoeSchedulingTimeWeekIndex  }
   ::= { sispm10403166lPoeSchedulingTimeTable 1 }

SISPM10403166LPoeSchedulingTimeEntry ::= SEQUENCE {
   sispm10403166lPoeSchedulingTimeWeekIndex        Integer32,
   sispm10403166lPoeSchedulingTimeStartTimeHourMinute  DisplayString,
   sispm10403166lPoeSchedulingTimeEndTimeHourMinute    DisplayString
}

sispm10403166lPoeSchedulingTimeWeekIndex OBJECT-TYPE
   SYNTAX      Integer32 (1..7)
   MAX-ACCESS  not-accessible
   STATUS      current
   DESCRIPTION
       "Week Index.
	   1: Mon, 2:Tue, 3: Wed, 4: Thu, 5: Fri, 6: Sat, 7: Sun"
   ::= { sispm10403166lPoeSchedulingTimeEntry 1 }

sispm10403166lPoeSchedulingTimeStartTimeHourMinute OBJECT-TYPE
   SYNTAX      DisplayString
   MAX-ACCESS  read-write
   STATUS      current
   DESCRIPTION
       "PoE Scheduling Start Time. Format: HH:MM. Hour Range: 0-23. Minute Range:0,5,10,...,55."
   ::= { sispm10403166lPoeSchedulingTimeEntry 2 }

sispm10403166lPoeSchedulingTimeEndTimeHourMinute OBJECT-TYPE
   SYNTAX      DisplayString
   MAX-ACCESS  read-write
   STATUS      current
   DESCRIPTION
       "PoE Scheduling End Time. Format: HH:MM. Hour Range: 0-23. Minute Range:0,5,10,...,55."
   ::= { sispm10403166lPoeSchedulingTimeEntry 3 }

sispm10403166lPoeConfiguration                                                 OBJECT IDENTIFIER ::= { sispm10403166lPoe 5 }

sispm10403166lPoeConfigurationPowerManagementMode OBJECT-TYPE
   SYNTAX      Integer32(0..5)
   MAX-ACCESS  read-write
   STATUS      current
   DESCRIPTION
       "The power management mode for PoE port.
        0: CLASS_RESERVED,
        1: CLASS_CONSUMP,
        2: ALLOCATED_RESERVED,
        3: ALLOCATED_CONSUMP,
        4: LLDPMED_RESERVED,
        5: LLDPMED_CONSUMP,
        default: CLASS_RESERVED. "
   ::= { sispm10403166lPoeConfiguration 1 }

sispm10403166lPoeConfigurationCapacitorDetection OBJECT-TYPE
   SYNTAX      Integer32(0..1)
   MAX-ACCESS  read-write
   STATUS      current
   DESCRIPTION
       "The capacitor detection mode.
        0: Disable
        1: Enable
       "
   ::= { sispm10403166lPoeConfiguration 2 }

sispm10403166lPoeConfigurationTable OBJECT-TYPE
   SYNTAX      SEQUENCE OF SISPM10403166LPoeConfigurationEntry
   MAX-ACCESS  not-accessible
   STATUS      current
   DESCRIPTION
       " Configure PoE Configuration mode. "
   ::= { sispm10403166lPoeConfiguration 4 }

sispm10403166lPoeConfigurationEntry OBJECT-TYPE
   SYNTAX      SISPM10403166LPoeConfigurationEntry
   MAX-ACCESS  not-accessible
   STATUS      current
   DESCRIPTION
       " "
   INDEX    { sispm10403166lPoeConfigurationSwitch  }
   ::= { sispm10403166lPoeConfigurationTable 1 }

SISPM10403166LPoeConfigurationEntry ::= SEQUENCE {
   sispm10403166lPoeConfigurationSwitch	                  Integer32,
   sispm10403166lPoeConfigurationPrimaryPowerSupply        Integer32,
   sispm10403166lPoeConfigurationAlwaysOnPoE        Integer32
}

sispm10403166lPoeConfigurationSwitch OBJECT-TYPE
   SYNTAX      Integer32 (1..16)
   MAX-ACCESS  not-accessible
   STATUS      current
   DESCRIPTION
       " switch index, range : 1 - 16. "
   ::= { sispm10403166lPoeConfigurationEntry 1 }

sispm10403166lPoeConfigurationPrimaryPowerSupply  OBJECT-TYPE
   SYNTAX      Integer32(0..2000)
   MAX-ACCESS  read-only
   STATUS      current
   DESCRIPTION
       "It must be defined what amount of power the primary and backup power sources
        can deliver. "
   ::= { sispm10403166lPoeConfigurationEntry 3 }

sispm10403166lPoeConfigurationAlwaysOnPoE  OBJECT-TYPE
   SYNTAX      Integer32(0..1)
   MAX-ACCESS  read-write
   STATUS      current
   DESCRIPTION
       "Configure Non-Stop PoE"
   ::= { sispm10403166lPoeConfigurationEntry 4 }

sispm10403166lPoeConfigurationPortTable OBJECT-TYPE
   SYNTAX      SEQUENCE OF SISPM10403166LPoeConfigurationPortEntry
   MAX-ACCESS  not-accessible
   STATUS      current
   DESCRIPTION
       " Configure PoE Port Configuration mode. "
   ::= { sispm10403166lPoeConfiguration 5 }

sispm10403166lPoeConfigurationPortEntry OBJECT-TYPE
   SYNTAX      SISPM10403166LPoeConfigurationPortEntry
   MAX-ACCESS  not-accessible
   STATUS      current
   DESCRIPTION
       " "
   INDEX    { sispm10403166lPoeConfigurationPort  }
   ::= { sispm10403166lPoeConfigurationPortTable 1 }

SISPM10403166LPoeConfigurationPortEntry ::= SEQUENCE {
   sispm10403166lPoeConfigurationPort	       Integer32,
   sispm10403166lPoeConfigurationPortPoEMode       INTEGER,
   sispm10403166lPoeConfigurationPortPriority      INTEGER,
   sispm10403166lPoeConfigurationPortMaximumPower  DisplayString,
   sispm10403166lPoeConfigurationPortDetection     Integer32,
-- sispm10403166lPoeConfigurationPortPoEScheduleByProfileID     Integer32,
   sispm10403166lPoeConfigurationPortPoEScheduleByProfileName   DisplayString,
   sispm10403166lPoeConfigurationPortDelayMode     Integer32,
   sispm10403166lPoeConfigurationPortDelayTime     Integer32
}

sispm10403166lPoeConfigurationPort OBJECT-TYPE
   SYNTAX      Integer32(1..65535)
   MAX-ACCESS  not-accessible
   STATUS      current
   DESCRIPTION
       " port, range : 1 - port number. "
   ::= { sispm10403166lPoeConfigurationPortEntry 1 }

sispm10403166lPoeConfigurationPortPoEMode OBJECT-TYPE
   SYNTAX      INTEGER { disable(0), poe(1) }
   MAX-ACCESS  read-write
   STATUS      current
   DESCRIPTION
       "The PoE Mode represents the PoE operating mode for the port.
        0: Disable,
        1: Enable,
        default: Enable. "
   ::= { sispm10403166lPoeConfigurationPortEntry 2 }

sispm10403166lPoeConfigurationPortPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { sispm10403166lPoeConfigurationPortEntry 3 }

sispm10403166lPoeConfigurationPortMaximumPower OBJECT-TYPE
   SYNTAX      DisplayString
   MAX-ACCESS  read-write
   STATUS      current
   DESCRIPTION
       "The Maximum Power value contains a numerical value that indicates the maximum
        power in watts that can be delivered to a remote device.
        max: 30[W]. "
   ::= { sispm10403166lPoeConfigurationPortEntry 4 }

sispm10403166lPoeConfigurationPortDetection OBJECT-TYPE
   SYNTAX      Integer32(1..5)
   MAX-ACCESS  read-write
   STATUS      current
   DESCRIPTION
       "The Detection represents the PoE capacitor detection for the port.
	      -1:Not support.
	   1:Legacy : Legacy capacitive detection only.
	   2:4-point : IEEE 802.3af 4-point detection only.
	   3:4-point-legacy : IEEE 802.3af 4-point detection followed by Legacy detection.
	   4:2-point : IEEE 802.3af 2-point detection only.
	   5:2-point-legacy : IEEE 802.3af 2-point detection followed by Legacy detection.
	   "
   ::= { sispm10403166lPoeConfigurationPortEntry 5 }

-- sispm10403166lPoeConfigurationPortPoEScheduleByProfileID OBJECT-TYPE
--   SYNTAX      Integer32(0..16)
--   MAX-ACCESS  read-write
--   STATUS      current
--   DESCRIPTION
--       "Specify a valid PoE schedule profile by profile id. 0:disable,1-16:1-16 profile."
--   ::= { sispm10403166lPoeConfigurationPortEntry 6 }

sispm10403166lPoeConfigurationPortPoEScheduleByProfileName OBJECT-TYPE
   SYNTAX      DisplayString
   MAX-ACCESS  read-write
   STATUS      current
   DESCRIPTION
       "Specify a valid PoE schedule profile by profile name. disabled: disable profile schedule."
   ::= { sispm10403166lPoeConfigurationPortEntry 7 }

sispm10403166lPoeConfigurationPortDelayMode OBJECT-TYPE
   SYNTAX      Integer32(0..1)
   MAX-ACCESS  read-write
   STATUS      current
   DESCRIPTION
       "Turn on off the power delay function.
	   0: Disable
        1: Enable"
   ::= { sispm10403166lPoeConfigurationPortEntry 8 }

sispm10403166lPoeConfigurationPortDelayTime OBJECT-TYPE
   SYNTAX      Integer32(0..300)
   MAX-ACCESS  read-write
   STATUS      current
   DESCRIPTION
       "When rebooting, the PoE port will start to provide power to the PD when it out of delay time.
	   Range:0-300"
   ::= { sispm10403166lPoeConfigurationPortEntry 9 }

sispm10403166lPoeChipsetRebootSchedule OBJECT IDENTIFIER ::= { sispm10403166lPoe 6 }

sispm10403166lPoeChipsetRebootMode OBJECT-TYPE
   SYNTAX      Integer32
   MAX-ACCESS  read-write
   STATUS      current
   DESCRIPTION
       "PoE Chipset Reboot Mode
	    0:disable
		1:enable"
   ::= { sispm10403166lPoeChipsetRebootSchedule 1 }

sispm10403166lPoeChipsetRebootTimeTable OBJECT-TYPE
   SYNTAX      SEQUENCE OF SISPM10403166LPoeChipsetRebootTimeEntry
   MAX-ACCESS  not-accessible
   STATUS      current
   DESCRIPTION
       " Configure PoE Chipset Reboot Time."
   ::= { sispm10403166lPoeChipsetRebootSchedule 2 }

sispm10403166lPoeChipsetRebootTimeEntry OBJECT-TYPE
   SYNTAX      SISPM10403166LPoeChipsetRebootTimeEntry
   MAX-ACCESS  not-accessible
   STATUS      current
   DESCRIPTION
       " "
   INDEX    { sispm10403166lPoeChipsetRebootWeekIndex  }
   ::= { sispm10403166lPoeChipsetRebootTimeTable 1 }

SISPM10403166LPoeChipsetRebootTimeEntry ::= SEQUENCE {
   sispm10403166lPoeChipsetRebootWeekIndex	       Integer32,
   sispm10403166lPoeChipsetRebootTimeHour           Integer32,
   sispm10403166lPoeChipsetRebootTimeMinute         Integer32
}

sispm10403166lPoeChipsetRebootWeekIndex OBJECT-TYPE
   SYNTAX      Integer32 (1..7)
   MAX-ACCESS  not-accessible
   STATUS      current
   DESCRIPTION
       "PoE chipset reboot week index.
	   1: Mon, 2:Tue, 3: Wed, 4: Thu, 5: Fri, 6: Sat, 7: Sun"
   ::= { sispm10403166lPoeChipsetRebootTimeEntry 1 }

sispm10403166lPoeChipsetRebootTimeHour OBJECT-TYPE
   SYNTAX      Integer32 (-1..23)
   MAX-ACCESS  read-write
   STATUS      current
   DESCRIPTION
       "PoE Chipset Reboot Time (Hour). Range: 0-23.
	   -1:disable"
   ::= { sispm10403166lPoeChipsetRebootTimeEntry 2 }

sispm10403166lPoeChipsetRebootTimeMinute OBJECT-TYPE
   SYNTAX      Integer32 (-1..55)
   MAX-ACCESS  read-write
   STATUS      current
   DESCRIPTION
       "PoE Chipset Reboot Time (Minute). Range:0,5,10,...,55.
	   -1:disable"
   ::= { sispm10403166lPoeChipsetRebootTimeEntry 3 }

-- =======================================================================================================================
-- RowStatus Info:  createAndWait, notReady, notInService not supported.
-- =======================================================================================================================
-- Textual Conventions for the sispm10403166l AAA Mib
-- =======================================================================================================================
--
sispm10403166lAAAMIB                   OBJECT IDENTIFIER  ::= { sispm10403166lConfiguration 15 }
    sispm10403166lAAA                  OBJECT IDENTIFIER  ::= { sispm10403166lAAAMIB 1 }
    sispm10403166lRADIUS               OBJECT IDENTIFIER  ::= { sispm10403166lAAA 1 }
    sispm10403166lRADIUSGlobalConfig   OBJECT IDENTIFIER  ::= { sispm10403166lRADIUS 1 }

    sispm10403166lTACACS               OBJECT IDENTIFIER  ::= { sispm10403166lAAA 2 }

--
-- =======================================================================================================================
-- Start sispm10403166lRADIUS group
-- =======================================================================================================================
--sispm10403166lRADIUSGlobalConfig

    sispm10403166lRADIUSGlobalConfigTimeout OBJECT-TYPE
               SYNTAX      Integer32(1..1000)
               MAX-ACCESS  read-write
               STATUS      current
               DESCRIPTION
                   "Timeout is the number of seconds, to wait for a reply
                    from a RADIUS server before retransmitting the request.
                    range: 1-1000."
               ::= {     sispm10403166lRADIUSGlobalConfig 1 }

    sispm10403166lRADIUSGlobalConfigRetransmit OBJECT-TYPE
               SYNTAX      Integer32(1..1000)
               MAX-ACCESS  read-write
               STATUS      current
               DESCRIPTION
                   "Retransmit is the number of times,a RADIUS request is
                    retransmitted to a server that is not responding.If the
                    server has not responded after the last retransmit it is
                    considered to be dead.
                    range: 1-1000."
               ::= {     sispm10403166lRADIUSGlobalConfig 2 }

    sispm10403166lRADIUSGlobalConfigDeadtime OBJECT-TYPE
               SYNTAX      Integer32(0..1440)
               MAX-ACCESS  read-write
               STATUS      current
               DESCRIPTION
                   "This will stop the switch from continually trying to
                    contact a server that it has already determined as dead.
                    range: 0-1440."
               ::= {     sispm10403166lRADIUSGlobalConfig 3 }

    sispm10403166lRADIUSGlobalConfigKey OBJECT-TYPE
               SYNTAX      DisplayString
               MAX-ACCESS  read-write
               STATUS      current
               DESCRIPTION
                   "The secret key shared between the RADIUS server and
                    the switch."
               ::= {     sispm10403166lRADIUSGlobalConfig 4 }

    sispm10403166lRADIUSGlobalConfigNASIPv4 OBJECT-TYPE
               SYNTAX      IpAddress
               MAX-ACCESS  read-write
               STATUS      current
               DESCRIPTION
                   "The IPv4 address to be used as attribute 4 in RADIUS
                    Access-Request packets."
               ::= {     sispm10403166lRADIUSGlobalConfig 5 }

    sispm10403166lRADIUSGlobalConfigNASIPv6 OBJECT-TYPE
               SYNTAX      DisplayString
               MAX-ACCESS  read-write
               STATUS      current
               DESCRIPTION
                   "The IPv6 address to be used as attribute 95 in RADIUS
                    Access-Request packets. "
               ::= {     sispm10403166lRADIUSGlobalConfig 6 }

    sispm10403166lRADIUSGlobalConfigNASIdentifier OBJECT-TYPE
               SYNTAX      DisplayString
               MAX-ACCESS  read-write
               STATUS      current
               DESCRIPTION
                   "The identifier to be used as attribute 32 in RADIUS
                    Access-Request packets. "
               ::= {     sispm10403166lRADIUSGlobalConfig 7 }

--sispm10403166lRADIUSServerConfigTable

    sispm10403166lRADIUSServerConfigTable OBJECT-TYPE
               SYNTAX      SEQUENCE OF     SISPM10403166LRADIUSServerConfigEntry
               MAX-ACCESS  not-accessible
               STATUS      current
               DESCRIPTION
                   "The RADIUS Server Configuration Table."
               ::= {     sispm10403166lRADIUS 2 }

    sispm10403166lRADIUSServerConfigEntry OBJECT-TYPE
               SYNTAX          SISPM10403166LRADIUSServerConfigEntry
               MAX-ACCESS  not-accessible
               STATUS      current
               DESCRIPTION
                   "The RADIUS Server Configuration Entry."
               INDEX    {    sispm10403166lRADIUSServerConfServerNo  }
               ::= {     sispm10403166lRADIUSServerConfigTable 1 }

    SISPM10403166LRADIUSServerConfigEntry             ::= SEQUENCE {
                 sispm10403166lRADIUSServerConfServerNo      Integer32,
                 sispm10403166lRADIUSServerConfHostname      DisplayString,
                 sispm10403166lRADIUSServerConfAuthPort      Integer32,
                 sispm10403166lRADIUSServerConfAcctPort      Integer32,
                 sispm10403166lRADIUSServerConfTimeout       Integer32,
                 sispm10403166lRADIUSServerConfRetransmit    Integer32,
                 sispm10403166lRADIUSServerConfKey           DisplayString,
                 sispm10403166lRADIUSServerConfRowStatus     RowStatus
                 }

    sispm10403166lRADIUSServerConfServerNo OBJECT-TYPE
               SYNTAX      Integer32(1..5)
               MAX-ACCESS  not-accessible
               STATUS      current
               DESCRIPTION
                   "The RADIUS server number.
                    max: 5."
               ::= {     sispm10403166lRADIUSServerConfigEntry 1 }

    sispm10403166lRADIUSServerConfHostname OBJECT-TYPE
               SYNTAX      DisplayString
               MAX-ACCESS  read-create
               STATUS      current
               DESCRIPTION
                   "The IP address or hostname of the RADIUS server. "
               ::= {     sispm10403166lRADIUSServerConfigEntry 2 }

    sispm10403166lRADIUSServerConfAuthPort OBJECT-TYPE
               SYNTAX      Integer32(0..65535)
               MAX-ACCESS  read-create
               STATUS      current
               DESCRIPTION
                   "The UDP port to use on the RADIUS server for
                    authentication.
                    range: 0-65535. "
               ::= {     sispm10403166lRADIUSServerConfigEntry 3 }

    sispm10403166lRADIUSServerConfAcctPort OBJECT-TYPE
               SYNTAX      Integer32(0..65535)
               MAX-ACCESS  read-create
               STATUS      current
               DESCRIPTION
                   "The UDP port to use on the RADIUS server for accounting.
                    range: 0-65535. "
               ::= {     sispm10403166lRADIUSServerConfigEntry 4 }

    sispm10403166lRADIUSServerConfTimeout OBJECT-TYPE
               SYNTAX      Integer32(1..1000)
               MAX-ACCESS  read-create
               STATUS      current
               DESCRIPTION
                   "This optional setting overrides the global timeout value.
                    Leaving it blank will use the global timeout value.
                    range: 1-1000. "
               ::= {     sispm10403166lRADIUSServerConfigEntry 5 }

    sispm10403166lRADIUSServerConfRetransmit OBJECT-TYPE
               SYNTAX      Integer32(1..1000)
               MAX-ACCESS  read-create
               STATUS      current
               DESCRIPTION
                   "This optional setting overrides the global retransmit value.
                    Leaving it blank will use the global retransmit value.
                    range: 1-1000. "
               ::= {     sispm10403166lRADIUSServerConfigEntry 6 }

    sispm10403166lRADIUSServerConfKey OBJECT-TYPE
               SYNTAX      DisplayString
               MAX-ACCESS  read-create
               STATUS      current
               DESCRIPTION
                   "This optional setting overrides the global key. Leaving
                    it blank will use the global key."
               ::= {     sispm10403166lRADIUSServerConfigEntry 7 }

    sispm10403166lRADIUSServerConfRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sispm10403166lRADIUSServerConfigEntry 8 }

--sispm10403166lRADIUSDetailTable

    sispm10403166lRADIUSDetailTable OBJECT-TYPE
               SYNTAX      SEQUENCE OF     SISPM10403166LRADIUSDetailEntry
               MAX-ACCESS  not-accessible
               STATUS      current
               DESCRIPTION
                   "The RADIUS Detail Table."
               ::= {     sispm10403166lRADIUS 3 }

    sispm10403166lRADIUSDetailEntry OBJECT-TYPE
               SYNTAX          SISPM10403166LRADIUSDetailEntry
               MAX-ACCESS  not-accessible
               STATUS      current
               DESCRIPTION
                   "The RADIUS Detail Entry."
               INDEX    {    sispm10403166lRADIUSServerConfServerNo  }
               ::= {     sispm10403166lRADIUSDetailTable 1 }

    SISPM10403166LRADIUSDetailEntry             ::= SEQUENCE {
                 sispm10403166lRADIUSAuthIPAddress               DisplayString,
                 sispm10403166lRADIUSAuthStatus                  DisplayString,
                 sispm10403166lRADIUSAuthRoundTripTime           Integer32,
                 sispm10403166lRADIUSAuthRxAccessAccept          Counter32,
                 sispm10403166lRADIUSAuthRxAccessReject          Counter32,
                 sispm10403166lRADIUSAuthRxAccessChallenge       Counter32,
                 sispm10403166lRADIUSAuthRxAccessResponse        Counter32,
                 sispm10403166lRADIUSAuthRxBadAuth               Counter32,
                 sispm10403166lRADIUSAuthRxUnknownType           Counter32,
                 sispm10403166lRADIUSAuthRxPacketsDropped        Counter32,
                 sispm10403166lRADIUSAuthTxAccessRequest         Counter32,
                 sispm10403166lRADIUSAuthTxAccessRetransmission  Counter32,
                 sispm10403166lRADIUSAuthTxPendingRequest        Counter32,
                 sispm10403166lRADIUSAuthTxTimeout               Counter32,
                 sispm10403166lRADIUSAccountIPAddress            IpAddress,
                 sispm10403166lRADIUSAccountStatus               DisplayString,
                 sispm10403166lRADIUSAccountRoundTripTime        Integer32,
                 sispm10403166lRADIUSAccountRxResponses          Counter32,
                 sispm10403166lRADIUSAccountRxMalformedResponse  Counter32,
                 sispm10403166lRADIUSAccountRxBadAuth            Counter32,
                 sispm10403166lRADIUSAccountRxUnknownType        Counter32,
                 sispm10403166lRADIUSAccountRxPacketsDrop        Counter32,
                 sispm10403166lRADIUSAccountTxRequest            Counter32,
                 sispm10403166lRADIUSAccountTxRetransmission     Counter32,
                 sispm10403166lRADIUSAccountTxPendingRequest     Counter32,
                 sispm10403166lRADIUSAccountTxTimeout            Counter32,
                 sispm10403166lRADIUSDetailClearCmd              ActivateCmd
                 }

    sispm10403166lRADIUSAuthIPAddress OBJECT-TYPE
               SYNTAX      DisplayString
               MAX-ACCESS  read-only
               STATUS      current
               DESCRIPTION
                   "IP address and UDP port for the authentication
                    server in question."
               ::= {     sispm10403166lRADIUSDetailEntry 2 }

    sispm10403166lRADIUSAuthStatus OBJECT-TYPE
               SYNTAX      DisplayString
               MAX-ACCESS  read-only
               STATUS      current
               DESCRIPTION
                   "Shows the state of the server."
               ::= {     sispm10403166lRADIUSDetailEntry 3 }

    sispm10403166lRADIUSAuthRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sispm10403166lRADIUSDetailEntry 4 }

    sispm10403166lRADIUSAuthRxAccessAccept OBJECT-TYPE
               SYNTAX      Counter32
               MAX-ACCESS  read-only
               STATUS      current
               DESCRIPTION
                   "The number of RADIUS Access-Accept packets
                   (valid or invalid) received from the server."
               ::= {     sispm10403166lRADIUSDetailEntry 5 }

    sispm10403166lRADIUSAuthRxAccessReject OBJECT-TYPE
               SYNTAX      Counter32
               MAX-ACCESS  read-only
               STATUS      current
               DESCRIPTION
                   "The number of RADIUS Access-Reject packets
                    (valid or invalid) received from the server."
               ::= {     sispm10403166lRADIUSDetailEntry 6 }

    sispm10403166lRADIUSAuthRxAccessChallenge OBJECT-TYPE
               SYNTAX      Counter32
               MAX-ACCESS  read-only
               STATUS      current
               DESCRIPTION
                   "The number of RADIUS Access-Challenge packets
                    (valid or invalid) received from the server."
               ::= {     sispm10403166lRADIUSDetailEntry 7 }

    sispm10403166lRADIUSAuthRxAccessResponse OBJECT-TYPE
               SYNTAX      Counter32
               MAX-ACCESS  read-only
               STATUS      current
               DESCRIPTION
                   "The number of malformed RADIUS Access-Response
                    packets received from the server."
               ::= {     sispm10403166lRADIUSDetailEntry 8 }

    sispm10403166lRADIUSAuthRxBadAuth OBJECT-TYPE
               SYNTAX      Counter32
               MAX-ACCESS  read-only
               STATUS      current
               DESCRIPTION
                   "The number of RADIUS Access-Response packets containing
                    invalid authenticators or Message Authenticator
                    attributes received from the server."
               ::= {     sispm10403166lRADIUSDetailEntry 9 }

    sispm10403166lRADIUSAuthRxUnknownType OBJECT-TYPE
               SYNTAX      Counter32
               MAX-ACCESS  read-only
               STATUS      current
               DESCRIPTION
                   "The number of RADIUS packets that were received with
                    unknown types from the server on the authentication
                    port and dropped."
               ::= {     sispm10403166lRADIUSDetailEntry 10 }

    sispm10403166lRADIUSAuthRxPacketsDropped OBJECT-TYPE
               SYNTAX      Counter32
               MAX-ACCESS  read-only
               STATUS      current
               DESCRIPTION
                   "The number of RADIUS packets that were received from
                    the server on the authentication port and dropped for
                    some other reason."
               ::= {     sispm10403166lRADIUSDetailEntry 11 }

    sispm10403166lRADIUSAuthTxAccessRequest OBJECT-TYPE
               SYNTAX      Counter32
               MAX-ACCESS  read-only
               STATUS      current
               DESCRIPTION
                   "The number of RADIUS Access-Request packets sent to
                    the server. This does not include retransmissions."
               ::= {     sispm10403166lRADIUSDetailEntry 12 }

    sispm10403166lRADIUSAuthTxAccessRetransmission OBJECT-TYPE
               SYNTAX      Counter32
               MAX-ACCESS  read-only
               STATUS      current
               DESCRIPTION
                   "The number of RADIUS Access-Request packets
                    retransmitted to the RADIUS authentication server."
               ::= {     sispm10403166lRADIUSDetailEntry 13 }

    sispm10403166lRADIUSAuthTxPendingRequest OBJECT-TYPE
               SYNTAX      Counter32
               MAX-ACCESS  read-only
               STATUS      current
               DESCRIPTION
                   "The number of RADIUS Access-Request packets destined
                    for the server that have not yet timed out or received
                    a response. "
               ::= {     sispm10403166lRADIUSDetailEntry 14 }

    sispm10403166lRADIUSAuthTxTimeout OBJECT-TYPE
               SYNTAX      Counter32
               MAX-ACCESS  read-only
               STATUS      current
               DESCRIPTION
                   "The number of authentication timeouts to the server.
                    After a timeout, the client may retry to the same server,
                    send to a different server, or give up."
               ::= {     sispm10403166lRADIUSDetailEntry 15 }

    sispm10403166lRADIUSAccountIPAddress OBJECT-TYPE
               SYNTAX      IpAddress
               MAX-ACCESS  read-only
               STATUS      current
               DESCRIPTION
                   "IP address and UDP port for the authentication server
                    in question."
               ::= {     sispm10403166lRADIUSDetailEntry 16 }

    sispm10403166lRADIUSAccountStatus OBJECT-TYPE
               SYNTAX      DisplayString
               MAX-ACCESS  read-only
               STATUS      current
               DESCRIPTION
                   "Shows the state of the server. "
               ::= {     sispm10403166lRADIUSDetailEntry 17 }

    sispm10403166lRADIUSAccountRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sispm10403166lRADIUSDetailEntry 18 }

    sispm10403166lRADIUSAccountRxResponses OBJECT-TYPE
               SYNTAX      Counter32
               MAX-ACCESS  read-only
               STATUS      current
               DESCRIPTION
                   "The number of RADIUS packets (valid or invalid)
                    received from the server."
               ::= {     sispm10403166lRADIUSDetailEntry 19 }

    sispm10403166lRADIUSAccountRxMalformedResponse OBJECT-TYPE
               SYNTAX      Counter32
               MAX-ACCESS  read-only
               STATUS      current
               DESCRIPTION
                   "The number of malformed RADIUS packets received from
                    the server. "
               ::= {     sispm10403166lRADIUSDetailEntry 20 }

    sispm10403166lRADIUSAccountRxBadAuth OBJECT-TYPE
               SYNTAX      Counter32
               MAX-ACCESS  read-only
               STATUS      current
               DESCRIPTION
                   "The number of RADIUS packets containing invalid
                    authenticators received from the server."
               ::= {     sispm10403166lRADIUSDetailEntry 21 }

    sispm10403166lRADIUSAccountRxUnknownType OBJECT-TYPE
               SYNTAX      Counter32
               MAX-ACCESS  read-only
               STATUS      current
               DESCRIPTION
                   "The number of RADIUS packets of unknown types that were
                    received from the server on the accounting port. "
               ::= {     sispm10403166lRADIUSDetailEntry 22 }

    sispm10403166lRADIUSAccountRxPacketsDrop OBJECT-TYPE
               SYNTAX      Counter32
               MAX-ACCESS  read-only
               STATUS      current
               DESCRIPTION
                   "The number of RADIUS packets that were received from
                    the server on the accounting port and dropped for some
                    other reason."
               ::= {     sispm10403166lRADIUSDetailEntry 23 }

    sispm10403166lRADIUSAccountTxRequest OBJECT-TYPE
               SYNTAX      Counter32
               MAX-ACCESS  read-only
               STATUS      current
               DESCRIPTION
                   "The number of RADIUS packets sent to the server.
                    This does not include retransmissions."
               ::= {     sispm10403166lRADIUSDetailEntry 24 }

    sispm10403166lRADIUSAccountTxRetransmission OBJECT-TYPE
               SYNTAX      Counter32
               MAX-ACCESS  read-only
               STATUS      current
               DESCRIPTION
                   "The number of RADIUS packets retransmitted to the RADIUS
                    accounting server."
               ::= {     sispm10403166lRADIUSDetailEntry 25 }

    sispm10403166lRADIUSAccountTxPendingRequest OBJECT-TYPE
               SYNTAX      Counter32
               MAX-ACCESS  read-only
               STATUS      current
               DESCRIPTION
                   "The number of RADIUS packets destined for the server
                    that have not yet timed out or received a response."
               ::= {     sispm10403166lRADIUSDetailEntry 26 }

    sispm10403166lRADIUSAccountTxTimeout OBJECT-TYPE
               SYNTAX      Counter32
               MAX-ACCESS  read-only
               STATUS      current
               DESCRIPTION
                   "The number of accounting timeouts to the server.
                    After a timeout, the client may retry to the same
                    server, send to a different server, or give up."
               ::= {     sispm10403166lRADIUSDetailEntry 27 }

    sispm10403166lRADIUSDetailClearCmd OBJECT-TYPE
               SYNTAX      ActivateCmd
               MAX-ACCESS  read-only
               STATUS      current
               DESCRIPTION
                   "Clears the counters for the selected server."
               ::= {     sispm10403166lRADIUSDetailEntry 28 }

--
-- =======================================================================================================================
-- Start sispm10403166lTACACS group
-- =======================================================================================================================
--sispm10403166lTACACSGlobalConfig

    sispm10403166lTACACSGlobalConfigTimeout OBJECT-TYPE
               SYNTAX      Integer32(1..1000)
               MAX-ACCESS  read-write
               STATUS      current
               DESCRIPTION
                   "Timeout is the number of seconds,to wait for a reply
                    from a TACACS+ server before it is considered to be dead.
                    range: 1-1000 seconds,
                    default: 5 seconds."
               ::= {     sispm10403166lTACACS 1 }

    sispm10403166lTACACSGlobalConfigDeadtime OBJECT-TYPE
               SYNTAX      Integer32(0..1440)
               MAX-ACCESS  read-write
               STATUS      current
               DESCRIPTION
                   "The period during which the switch will not send new
                    requests to a server that has failed to respond to a
                    previous request. This will stop the switch from
                    continually trying to contact a server that it has
                    already determined as dead.
                    range: 0-1440 minutes,
                    default: 0 minutes."
               ::= {     sispm10403166lTACACS 2 }

    sispm10403166lTACACSGlobalConfigKey OBJECT-TYPE
               SYNTAX      DisplayString
               MAX-ACCESS  read-write
               STATUS      current
               DESCRIPTION
                   "The secret key shared between the TACACS+ server and
                    the switch."
               ::= {     sispm10403166lTACACS 3 }

--sispm10403166lTACACSServerConfigTable

    sispm10403166lTACACSServerConfigTable OBJECT-TYPE
               SYNTAX      SEQUENCE OF     SISPM10403166LTACACSServerConfigEntry
               MAX-ACCESS  not-accessible
               STATUS      current
               DESCRIPTION
                   "The TACACS Server configuration Table."
               ::= {     sispm10403166lTACACS 4 }

    sispm10403166lTACACSServerConfigEntry OBJECT-TYPE
               SYNTAX          SISPM10403166LTACACSServerConfigEntry
               MAX-ACCESS  not-accessible
               STATUS      current
               DESCRIPTION
                   "The TACACS Server configuration Entry."
               INDEX    {    sispm10403166lTACACSServerConfigServerNo  }
               ::= {     sispm10403166lTACACSServerConfigTable 1 }

    SISPM10403166LTACACSServerConfigEntry             ::= SEQUENCE {
                 sispm10403166lTACACSServerConfigServerNo        Integer32,
                 sispm10403166lTACACSServerConfigHostname        DisplayString,
                 sispm10403166lTACACSServerConfigPort            Integer32,
                 sispm10403166lTACACSServerConfigTimeout         Integer32,
                 sispm10403166lTACACSServerConfigKey             DisplayString,
                 sispm10403166lTACACSServerConfigRowStatus       RowStatus
                 }

    sispm10403166lTACACSServerConfigServerNo OBJECT-TYPE
               SYNTAX      Integer32(1..5)
               MAX-ACCESS  not-accessible
               STATUS      current
               DESCRIPTION
                   "The TACACS server number.
                    max: 5."
               ::= {     sispm10403166lTACACSServerConfigEntry 1 }

    sispm10403166lTACACSServerConfigHostname OBJECT-TYPE
               SYNTAX      DisplayString
               MAX-ACCESS  read-create
               STATUS      current
               DESCRIPTION
                   "The IP address or hostname of the TACACS+ server."
               ::= {     sispm10403166lTACACSServerConfigEntry 2 }

    sispm10403166lTACACSServerConfigPort OBJECT-TYPE
               SYNTAX      Integer32(0..65535)
               MAX-ACCESS  read-create
               STATUS      current
               DESCRIPTION
                   "The TCP port to use on the TACACS+ server for
                    authentication."
               ::= {     sispm10403166lTACACSServerConfigEntry 3 }

    sispm10403166lTACACSServerConfigTimeout OBJECT-TYPE
               SYNTAX      Integer32(1..1000)
               MAX-ACCESS  read-create
               STATUS      current
               DESCRIPTION
                   "This optional setting overrides the global timeout
                    value. Leaving it blank will use the global timeout
                    value.
                    range: 1-1000."
               ::= {     sispm10403166lTACACSServerConfigEntry 4 }

    sispm10403166lTACACSServerConfigKey OBJECT-TYPE
               SYNTAX      DisplayString
               MAX-ACCESS  read-create
               STATUS      current
               DESCRIPTION
                   "This optional setting overrides the global key.
                    Leaving it blank will use the global key. "
               ::= {     sispm10403166lTACACSServerConfigEntry 5 }

    sispm10403166lTACACSServerConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sispm10403166lTACACSServerConfigEntry 6 }

-- =======================================================================================================================
--
-- =======================================================================================================================
-- Textual Conventions for the sispm10403166l Nas Mib
-- =======================================================================================================================
--
sispm10403166lNasMIB                   OBJECT IDENTIFIER  ::= { sispm10403166lConfiguration 16 }
    sispm10403166lNAS                  OBJECT IDENTIFIER  ::= { sispm10403166lNasMIB 1 }
    sispm10403166lNASConf              OBJECT IDENTIFIER  ::= { sispm10403166lNAS 1 }
    sispm10403166lNASStatus            OBJECT IDENTIFIER  ::= { sispm10403166lNAS 2 }

--
-- =======================================================================================================================
-- Start sispm10403166lNAS group
-- =======================================================================================================================
--sispm10403166lNASConf

    sispm10403166lNASConfMode OBJECT-TYPE
               SYNTAX      AdminMode
               MAX-ACCESS  read-write
               STATUS      current
               DESCRIPTION
                   "Indicates if NAS is globally enabled or disabled on
                    the switch."
               DEFVAL  { disable }
               ::= {     sispm10403166lNASConf 1 }

    sispm10403166lNASConfReauthenticationEnabled OBJECT-TYPE
               SYNTAX      AdminMode
               MAX-ACCESS  read-write
               STATUS      current
               DESCRIPTION
                   "If enable, successfully authenticated supplicants/clients
                    are reauthenticated after the interval specified by the
                    Reauthentication Period."
               DEFVAL  { disable }
               ::= {     sispm10403166lNASConf 2 }

    sispm10403166lNASConfReauthenticationPeriod OBJECT-TYPE
               SYNTAX      Integer32(1..3600)
               MAX-ACCESS  read-write
               STATUS      current
               DESCRIPTION
                   "Determines the period, in seconds, after which a
                    connected client must be reauthenticated.
                    default: 3600 sec,
                    range: 1-3600 sec."
               ::= {     sispm10403166lNASConf 3 }

    sispm10403166lNASConfEAPOLTimeout OBJECT-TYPE
               SYNTAX      Integer32(1..65535)
               MAX-ACCESS  read-write
               STATUS      current
               DESCRIPTION
                   "Determines the time for retransmission of Request
                    Identity EAPOL frames.
                    default: 30 sec,
                    range: 1-65535 sec."
               ::= {     sispm10403166lNASConf 4 }

    sispm10403166lNASConfAgingPeriod OBJECT-TYPE
               SYNTAX      Integer32(0|10..1000000)
               MAX-ACCESS  read-write
               STATUS      current
               DESCRIPTION
                   "When the NAS module uses the Port Security module to
                    secure MAC addresses, the Port Security module needs to
                    check for activity on the MAC address in question at regular
                    intervals and free resources if no activity is seen within
                    a given period of time.
                    default: 300 sec,
                    0: no support.
                    range: 0,10-1000000 sec."
               ::= {     sispm10403166lNASConf 5 }

    sispm10403166lNASConfHoldTime OBJECT-TYPE
               SYNTAX      Integer32(0|10..1000000)
               MAX-ACCESS  read-write
               STATUS      current
               DESCRIPTION
                   "If a client is denied access - either because the RADIUS
                    server denies the client access or because the RADIUS server
                    request times out - the client is put on hold in the
                    Unauthorized state.
                    default: 10 sec,
                    0: no support.
                    range: 0,10-1000000 sec."
               ::= {     sispm10403166lNASConf 6 }

    sispm10403166lNASConfRADIUSQoSEnabled OBJECT-TYPE
               SYNTAX      AdminMode
               MAX-ACCESS  read-write
               STATUS      current
               DESCRIPTION
                   "RADIUS-assigned QoS provides a means to centrally control
                    the traffic class to which traffic coming from a successfully
                    authenticated supplicant is assigned on the switch."
               DEFVAL  { disable }
               ::= {     sispm10403166lNASConf 7 }

    sispm10403166lNASConfRADIUSVLANEnabled OBJECT-TYPE
               SYNTAX      AdminMode
               MAX-ACCESS  read-write
               STATUS      current
               DESCRIPTION
                   "RADIUS-assigned VLAN provides a means to centrally control
                    the VLAN on which a successfully authenticated supplicant
                    is placed on the switch."
               DEFVAL  { disable }
               ::= {     sispm10403166lNASConf 8 }

    sispm10403166lNASConfGuestVLANEnabled OBJECT-TYPE
               SYNTAX      AdminMode
               MAX-ACCESS  read-write
               STATUS      current
               DESCRIPTION
                   "A Guest VLAN is a special VLAN - typically with limited
                    network access - on which 802.1X-unaware clients are placed
                    after a network administrator-defined timeout."
               DEFVAL  { disable }
               ::= {     sispm10403166lNASConf 9 }

    sispm10403166lNASConfGuestVLANID OBJECT-TYPE
               SYNTAX      Integer32(1..4095)
               MAX-ACCESS  read-write
               STATUS      current
               DESCRIPTION
                   "This is the value that a port's Port VLAN ID is set to if
                    a port is moved into the Guest VLAN.
                    default: 1,
                    range: 1-4095."
               ::= {     sispm10403166lNASConf 10 }

    sispm10403166lNASConfMaxReauthCount OBJECT-TYPE
               SYNTAX      Integer32(1..255)
               MAX-ACCESS  read-write
               STATUS      current
               DESCRIPTION
                   "The number of times the switch transmits an EAPOL Request
                    Identity frame without response before considering entering
                    the Guest VLAN is adjusted with this setting.
                    default: 2,
                    range: 1-255."
               ::= {     sispm10403166lNASConf 11 }

    sispm10403166lNASConfAllowGuestVLAN OBJECT-TYPE
               SYNTAX      AdminMode
               MAX-ACCESS  read-write
               STATUS      current
               DESCRIPTION
                   "The switch remembers if an EAPOL frame has been received
                    on the port for the life-time of the port."
               DEFVAL  { disable }
               ::= {     sispm10403166lNASConf 12 }

--sispm10403166lNASPortConfTable

    sispm10403166lNASPortConfTable OBJECT-TYPE
               SYNTAX      SEQUENCE OF     SISPM10403166LNASPortConfEntry
               MAX-ACCESS  not-accessible
               STATUS      current
               DESCRIPTION
                   "The NAS Port Configuration Table.
                    INDEX for this table is ifIndex which is
                    equivalent to the panel port number."
               ::= {     sispm10403166lNASConf 13 }

    sispm10403166lNASPortConfEntry OBJECT-TYPE
               SYNTAX          SISPM10403166LNASPortConfEntry
               MAX-ACCESS  not-accessible
               STATUS      current
               DESCRIPTION
                   "The NAS Port Configuration Entry."
               INDEX    {    ifIndex  }
               ::= {     sispm10403166lNASPortConfTable 1 }

    SISPM10403166LNASPortConfEntry             ::= SEQUENCE {
                 sispm10403166lNASPortConfAdminState         Integer32,
                 sispm10403166lNASPortConfRADIUSQoSEnabled   AdminMode,
                 sispm10403166lNASPortConfRADIUSVLANEnabled  AdminMode,
                 sispm10403166lNASPortConfGuestVLANEnabled   AdminMode,
                 sispm10403166lNASPortConfPortState          DisplayString,
                 sispm10403166lNASPortConfReauthenticateCmd  INTEGER,
                 sispm10403166lNASPortConfReinitializeCmd    INTEGER
                 }

    sispm10403166lNASPortConfAdminState OBJECT-TYPE
               SYNTAX      Integer32(0..5)
               MAX-ACCESS  read-write
               STATUS      current
               DESCRIPTION
                   "This selection controls the port's authentication mode.
                    0: Force Authorized,
                    1: Force Unauthorized,
                    2: Port-based 802.1X,
                    3: Single 802.1X,
                    4: Multi 802.1X,
                    5: MAC-based Auth,
                    range: 0-5."
               ::= {     sispm10403166lNASPortConfEntry 2 }

    sispm10403166lNASPortConfRADIUSQoSEnabled OBJECT-TYPE
               SYNTAX      AdminMode
               MAX-ACCESS  read-write
               STATUS      current
               DESCRIPTION
                   "When RADIUS-Assigned QoS is both globally enabled and
                    enabled on a given port, the switch reacts to QoS Class
                    information carried in the RADIUS Access-Accept packet
                    transmitted by the RADIUS server when a supplicant is
                    successfully authenticated."
               ::= {     sispm10403166lNASPortConfEntry 3 }

    sispm10403166lNASPortConfRADIUSVLANEnabled OBJECT-TYPE
               SYNTAX      AdminMode
               MAX-ACCESS  read-write
               STATUS      current
               DESCRIPTION
                   "When RADIUS-Assigned VLAN is both globally enabled and
                    enabled for a given port, the switch reacts to VLAN ID
                    information carried in the RADIUS Access-Accept packet
                    transmitted by the RADIUS server when a supplicant is
                    successfully authenticated."
               ::= {     sispm10403166lNASPortConfEntry 4 }

    sispm10403166lNASPortConfGuestVLANEnabled OBJECT-TYPE
               SYNTAX      AdminMode
               MAX-ACCESS  read-write
               STATUS      current
               DESCRIPTION
                   "When Guest VLAN is both globally enabled and enabled for
                    a given port, the switch considers moving the port into
                    the Guest VLAN according to the rules."
               ::= {     sispm10403166lNASPortConfEntry 5 }

    sispm10403166lNASPortConfPortState OBJECT-TYPE
               SYNTAX      DisplayString
               MAX-ACCESS  read-only
               STATUS      current
               DESCRIPTION
                   "The current state of the port."
               ::= {     sispm10403166lNASPortConfEntry 6 }

    sispm10403166lNASPortConfReauthenticateCmd OBJECT-TYPE
               SYNTAX      ActivateCmd
               MAX-ACCESS  read-write
               STATUS      current
               DESCRIPTION
                   "Schedules a reauthentication whenever the quiet-period of
                    the port runs out (EAPOL-based authentication). For
                    MAC-based authentication, reauthentication will be attempted
                    immediately.The button only has effect for successfully
                    authenticated clients on the port and will not cause the
                    clients to get temporarily unauthorized."
               DEFVAL  { noAction }
               ::= {     sispm10403166lNASPortConfEntry 7 }

    sispm10403166lNASPortConfReinitializeCmd OBJECT-TYPE
               SYNTAX      ActivateCmd
               MAX-ACCESS  read-write
               STATUS      current
               DESCRIPTION
                   "Forces a reinitialization of the clients on the port and
                    thereby a reauthentication immediately. The clients will
                    transfer to the unauthorized state while the
                    reauthentication is in progress."
               DEFVAL  { noAction }
               ::= {     sispm10403166lNASPortConfEntry 8 }

--sispm10403166lNASSwitchStatusTable

    sispm10403166lNASSwitchStatusTable OBJECT-TYPE
               SYNTAX      SEQUENCE OF     SISPM10403166LNASSwitchStatusEntry
               MAX-ACCESS  not-accessible
               STATUS      current
               DESCRIPTION
                   "The NAS Switch Status Table.
                    INDEX for this table is ifIndex which is
                    equivalent to the panel port number."
               ::= {     sispm10403166lNASStatus 1 }

    sispm10403166lNASSwitchStatusEntry OBJECT-TYPE
               SYNTAX          SISPM10403166LNASSwitchStatusEntry
               MAX-ACCESS  not-accessible
               STATUS      current
               DESCRIPTION
                   "The NAS Switch Status Entry."
               INDEX    {    ifIndex  }
               ::= {     sispm10403166lNASSwitchStatusTable 1 }

    SISPM10403166LNASSwitchStatusEntry             ::= SEQUENCE {
                 sispm10403166lNASSwitchStatusAdminState   DisplayString,
                 sispm10403166lNASSwitchStatusPortState    DisplayString,
                 sispm10403166lNASSwitchStatusLastSource   DisplayString,
                 sispm10403166lNASSwitchStatusLastID       DisplayString,
                 sispm10403166lNASSwitchStatusQoSClass     DisplayString,
                 sispm10403166lNASSwitchStatusPortVLANID   DisplayString
                 }

    sispm10403166lNASSwitchStatusAdminState OBJECT-TYPE
               SYNTAX      DisplayString
               MAX-ACCESS  read-only
               STATUS      current
               DESCRIPTION
                   "The port's current administrative state."
               ::= {     sispm10403166lNASSwitchStatusEntry 2 }

    sispm10403166lNASSwitchStatusPortState OBJECT-TYPE
               SYNTAX      DisplayString
               MAX-ACCESS  read-only
               STATUS      current
               DESCRIPTION
                   "The current state of the port."
               ::= {     sispm10403166lNASSwitchStatusEntry 3 }

    sispm10403166lNASSwitchStatusLastSource OBJECT-TYPE
               SYNTAX      DisplayString
               MAX-ACCESS  read-only
               STATUS      current
               DESCRIPTION
                   "The source MAC address carried in the most recently
                    received EAPOL frame for EAPOL-based authentication,
                    and the most recently received frame from a new client
                    for MAC-based authentication."
               ::= {     sispm10403166lNASSwitchStatusEntry 4 }

    sispm10403166lNASSwitchStatusLastID OBJECT-TYPE
               SYNTAX      DisplayString
               MAX-ACCESS  read-only
               STATUS      current
               DESCRIPTION
                   "The user name (supplicant identity) carried in the most
                    recently received Response Identity EAPOL frame for
                    EAPOL-based authentication, and the source MAC address
                    from the most recently received frame from a new client
                    for MAC-based authentication."
               ::= {     sispm10403166lNASSwitchStatusEntry 5 }

    sispm10403166lNASSwitchStatusQoSClass OBJECT-TYPE
               SYNTAX      DisplayString
               MAX-ACCESS  read-only
               STATUS      current
               DESCRIPTION
                   "QoS Class assigned to the port by the RADIUS server
                    if enabled."
               ::= {     sispm10403166lNASSwitchStatusEntry 6 }

    sispm10403166lNASSwitchStatusPortVLANID OBJECT-TYPE
               SYNTAX      DisplayString
               MAX-ACCESS  read-only
               STATUS      current
               DESCRIPTION
                   "The VLAN ID that NAS has put the port in."
               ::= {     sispm10403166lNASSwitchStatusEntry 7 }

--sispm10403166lNASPortCounterTable

    sispm10403166lNASPortCounterTable OBJECT-TYPE
               SYNTAX      SEQUENCE OF     SISPM10403166LNASPortCounterEntry
               MAX-ACCESS  not-accessible
               STATUS      current
               DESCRIPTION
                   "The NAS Port Counter Table.
                    INDEX for this table is ifIndex which is
                    equivalent to the panel port number."
               ::= {     sispm10403166lNASStatus 2 }

    sispm10403166lNASPortCounterEntry OBJECT-TYPE
               SYNTAX          SISPM10403166LNASPortCounterEntry
               MAX-ACCESS  not-accessible
               STATUS      current
               DESCRIPTION
                   "The NAS Port Counter Entry."
               INDEX    {    ifIndex  }
               ::= {     sispm10403166lNASPortCounterTable 1 }

    SISPM10403166LNASPortCounterEntry             ::= SEQUENCE {
                 sispm10403166lNASReceiveEAPOLTotal          Integer32,
                 sispm10403166lNASReceiveEAPOLResponseID     Integer32,
                 sispm10403166lNASReceiveEAPOLResponses      Integer32,
                 sispm10403166lNASReceiveEAPOLStart          Integer32,
                 sispm10403166lNASReceiveEAPOLLogoff         Integer32,
                 sispm10403166lNASReceiveEAPOLInvalidType    Integer32,
                 sispm10403166lNASReceiveEAPOLInvalidLength  Integer32,
                 sispm10403166lNASTransmitEAPOLTotal         Integer32,
                 sispm10403166lNASTransmitEAPOLRequestID     Integer32,
                 sispm10403166lNASTransmitEAPOLRequests      Integer32,
                 sispm10403166lNASPortReceiveBackendServerAccessChallenges    Integer32,
                 sispm10403166lNASPortReceiveBackendServerOtherRequests       Integer32,
                 sispm10403166lNASPortReceiveBackendServerAuthSuccesses       Integer32,
                 sispm10403166lNASPortReceiveBackendServerAuthFailures        Integer32,
                 sispm10403166lNASPortTransmitBackendServerResponses          Integer32,
                 sispm10403166lNASSupplicantInfoMAC          DisplayString,
                 sispm10403166lNASSupplicantInfoVlanID       Integer32,
                 sispm10403166lNASSupplicantInfoVersion      Integer32,
                 sispm10403166lNASSupplicantInfoIdentity     DisplayString,
                 sispm10403166lNASPortCounterClearCmd        ActivateCmd
                 }

    sispm10403166lNASReceiveEAPOLTotal OBJECT-TYPE
               SYNTAX      Integer32(-1..1000000)
               MAX-ACCESS  read-only
               STATUS      current
               DESCRIPTION
                   "The number of valid EAPOL frames of any type that have
                    been received by the switch.
                    -1: no support."
               ::= {     sispm10403166lNASPortCounterEntry 2 }

    sispm10403166lNASReceiveEAPOLResponseID OBJECT-TYPE
               SYNTAX      Integer32(-1..1000000)
               MAX-ACCESS  read-only
               STATUS      current
               DESCRIPTION
                   "The number of valid EAPOL Response Identity frames that
                    have been received by the switch.
                    -1: no support."
               ::= {     sispm10403166lNASPortCounterEntry 3 }

    sispm10403166lNASReceiveEAPOLResponses OBJECT-TYPE
               SYNTAX      Integer32(-1..1000000)
               MAX-ACCESS  read-only
               STATUS      current
               DESCRIPTION
                   "The number of valid EAPOL response frames (other than
                    Response Identity frames) that have been received by
                    the switch.
                    -1: no support."
               ::= {     sispm10403166lNASPortCounterEntry 4 }

    sispm10403166lNASReceiveEAPOLStart OBJECT-TYPE
               SYNTAX      Integer32(-1..1000000)
               MAX-ACCESS  read-only
               STATUS      current
               DESCRIPTION
                   "The number of EAPOL Start frames that have been received
                    by the switch.
                    -1: no support."
               ::= {     sispm10403166lNASPortCounterEntry 5 }

    sispm10403166lNASReceiveEAPOLLogoff OBJECT-TYPE
               SYNTAX      Integer32(-1..1000000)
               MAX-ACCESS  read-only
               STATUS      current
               DESCRIPTION
                   "The number of valid EAPOL Logoff frames that have been
                    received by the switch.
                    -1: no support."
               ::= {     sispm10403166lNASPortCounterEntry 6 }

    sispm10403166lNASReceiveEAPOLInvalidType OBJECT-TYPE
               SYNTAX      Integer32(-1..1000000)
               MAX-ACCESS  read-only
               STATUS      current
               DESCRIPTION
                   "The number of EAPOL frames that have been received by
                    the switch in which the frame type is not recognized.
                    -1: no support."
               ::= {     sispm10403166lNASPortCounterEntry 7 }

    sispm10403166lNASReceiveEAPOLInvalidLength OBJECT-TYPE
               SYNTAX      Integer32(-1..1000000)
               MAX-ACCESS  read-only
               STATUS      current
               DESCRIPTION
                   "The number of EAPOL frames that have been received
                    by the switch in which the Packet Body Length field
                    is invalid.
                    -1: no support."
               ::= {     sispm10403166lNASPortCounterEntry 8 }

    sispm10403166lNASTransmitEAPOLTotal OBJECT-TYPE
               SYNTAX      Integer32(-1..1000000)
               MAX-ACCESS  read-only
               STATUS      current
               DESCRIPTION
                   "The number of EAPOL frames of any type that have been
                    transmitted by the switch.
                    -1: no support."
               ::= {     sispm10403166lNASPortCounterEntry 9 }

    sispm10403166lNASTransmitEAPOLRequestID OBJECT-TYPE
               SYNTAX      Integer32(-1..1000000)
               MAX-ACCESS  read-only
               STATUS      current
               DESCRIPTION
                   "The number of EAPOL Request Identity frames that have
                    been transmitted by the switch.
                    -1: no support."
               ::= {     sispm10403166lNASPortCounterEntry 10 }

    sispm10403166lNASTransmitEAPOLRequests OBJECT-TYPE
               SYNTAX      Integer32(-1..1000000)
               MAX-ACCESS  read-only
               STATUS      current
               DESCRIPTION
                   "The number of valid EAPOL Request frames (other than
                    Request Identity frames) that have been transmitted
                    by the switch.
                    -1: no support."
               ::= {     sispm10403166lNASPortCounterEntry 11 }

    sispm10403166lNASPortReceiveBackendServerAccessChallenges OBJECT-TYPE
               SYNTAX      Integer32(-1..1000000)
               MAX-ACCESS  read-only
               STATUS      current
               DESCRIPTION
                   "802.1X-based: Counts the number of times that the switch
                    receives the first request from the backend server following
                    the first response from the supplicant. Indicates that the
                    backend server has communication with the switch.
                    MAC-based:Counts all Access Challenges received from the
                    backend server for this port (left-most table).
                    -1: no support."
               ::= {     sispm10403166lNASPortCounterEntry 12 }

    sispm10403166lNASPortReceiveBackendServerOtherRequests OBJECT-TYPE
               SYNTAX      Integer32(-1..1000000)
               MAX-ACCESS  read-only
               STATUS      current
               DESCRIPTION
                   "802.1X-based: Counts the number of times that the switch
                    sends an EAP Request packet following the first to the
                    supplicant. Indicates that the backend server chose an
                    EAP-method.
                    MAC-based: Not applicable.
                    -1: no support."
               ::= {     sispm10403166lNASPortCounterEntry 13 }

    sispm10403166lNASPortReceiveBackendServerAuthSuccesses OBJECT-TYPE
               SYNTAX      Integer32(-1..1000000)
               MAX-ACCESS  read-only
               STATUS      current
               DESCRIPTION
                   "802.1X- and MAC-based: Counts the number of times that
                    the switch receives a success indication.Indicates that
                    the supplicant has successfully authenticated to
                    the backend server.
                    -1: no support."
               ::= {     sispm10403166lNASPortCounterEntry 14 }

    sispm10403166lNASPortReceiveBackendServerAuthFailures OBJECT-TYPE
               SYNTAX      Integer32(-1..1000000)
               MAX-ACCESS  read-only
               STATUS      current
               DESCRIPTION
                   "802.1X- and MAC-based:Counts the number of times that the
                    switch receives a failure message.This indicates that the
                    supplicant has not authenticated to the backend
                    server.
                    -1: no support."
               ::= {     sispm10403166lNASPortCounterEntry 15 }

    sispm10403166lNASPortTransmitBackendServerResponses OBJECT-TYPE
               SYNTAX      Integer32(-1..1000000)
               MAX-ACCESS  read-only
               STATUS      current
               DESCRIPTION
                   "802.1X-based:Counts the number of times that the switch
                    attempts to send a supplicant's first response packet to
                    the backend server. Indicates the switch attempted
                    communication with the backend server. Possible
                    retransmissions are not counted.
                    MAC-based: Counts all the backend server packets sent from
                    the switch towards the backend server for a given port
                    (left-most table). Possible retransmissions are not
                    counted.
                    -1: no support."
               ::= {     sispm10403166lNASPortCounterEntry 16 }

    sispm10403166lNASSupplicantInfoMAC OBJECT-TYPE
               SYNTAX      DisplayString
               MAX-ACCESS  read-only
               STATUS      current
               DESCRIPTION
                   "The MAC address of the last supplicant. "
               ::= {     sispm10403166lNASPortCounterEntry 17 }

    sispm10403166lNASSupplicantInfoVlanID OBJECT-TYPE
               SYNTAX      Integer32(-1..1000000)
               MAX-ACCESS  read-only
               STATUS      current
               DESCRIPTION
                   "The VLAN ID on which the last frame from the last
                    supplicant was received.
                    -1: no support."
               ::= {     sispm10403166lNASPortCounterEntry 18 }

    sispm10403166lNASSupplicantInfoVersion OBJECT-TYPE
               SYNTAX      Integer32(-1..1000000)
               MAX-ACCESS  read-only
               STATUS      current
               DESCRIPTION
                   "802.1X-based:The protocol version number carried in
                    the most recently received EAPOL frame.
                    MAC-based: Not applicable.
                    -1: no support."
               ::= {     sispm10403166lNASPortCounterEntry 19 }

    sispm10403166lNASSupplicantInfoIdentity OBJECT-TYPE
               SYNTAX      DisplayString
               MAX-ACCESS  read-only
               STATUS      current
               DESCRIPTION
                   "802.1X-based:The user name (supplicant identity) carried
                    in the most recently received Response Identity EAPOL frame.
                    MAC-based: Not applicable. "
               ::= {     sispm10403166lNASPortCounterEntry 20 }

    sispm10403166lNASPortCounterClearCmd OBJECT-TYPE
               SYNTAX      ActivateCmd
               MAX-ACCESS  read-write
               STATUS      current
               DESCRIPTION
                   "Clear the counters for the selected port."
               ::= {     sispm10403166lNASPortCounterEntry 21 }


-- =======================================================================================================================
sispm10403166lMACConf 						OBJECT IDENTIFIER ::= { sispm10403166lConfiguration 17 }

    sispm10403166lMAC                                                    OBJECT IDENTIFIER   ::= { sispm10403166lMACConf 1 }

--
-- =======================================================================================================================
-- Start sispm10403166lMAC group
-- =======================================================================================================================
    sispm10403166lMACDisableAutomaticAging   OBJECT-TYPE
               SYNTAX       AdminMode
               MAX-ACCESS   read-write
               STATUS       current
               DESCRIPTION
                   "Disable the automatic aging of dynamic entries."
                ::= {     sispm10403166lMAC 1 }

    sispm10403166lMACAgingTime  OBJECT-TYPE
               SYNTAX       Integer32 (-1 | 10..1000000)
               MAX-ACCESS   read-write
               STATUS       current
               DESCRIPTION
                   "Configure aging time by entering a value here in seconds.
                   range: 10-1000000 seconds.
                   -1: Automatic Aging is disable."
                ::= {     sispm10403166lMAC 2 }

--sispm10403166lMACLearningTable
    sispm10403166lMACLearningTable OBJECT-TYPE
               SYNTAX      SEQUENCE OF     SISPM10403166LMACLearningEntry
               MAX-ACCESS  not-accessible
               STATUS      current
               DESCRIPTION
                   "The mac learning table.
                    INDEX for this table is ifIndex which is
                    equivalent to the panel port number."
               ::= {     sispm10403166lMAC 3 }

    sispm10403166lMACLearningEntry OBJECT-TYPE
               SYNTAX          SISPM10403166LMACLearningEntry
               MAX-ACCESS  not-accessible
               STATUS      current
               DESCRIPTION
                   "The mac learning entry."
               INDEX    {     ifIndex  }
               ::= {     sispm10403166lMACLearningTable 1 }

    SISPM10403166LMACLearningEntry             ::= SEQUENCE {
                sispm10403166lMACTableLearning     INTEGER
                }

    sispm10403166lMACTableLearning OBJECT-TYPE
               SYNTAX      INTEGER{ auto(0), disable(1), secure(2)}
               MAX-ACCESS  read-write
               STATUS      current
               DESCRIPTION
                   "auto(0)   : Learning is done automatically as soon as a
                                frame with unknown SMAC is received.
                    disable(1): Disable, No learning is done.
                    secure(2) : Secure, Only static MAC entries are learned,
                                all other frames are dropped."
               ::= {     sispm10403166lMACLearningEntry 2 }

    sispm10403166lLearningDisabledVLANs OBJECT-TYPE
               SYNTAX      DisplayString
               MAX-ACCESS  read-write
               STATUS      current
               DESCRIPTION
                   "The Learning Disabled VLANs"
               ::= {     sispm10403166lMAC 4 }

--sispm10403166lMACStaticConfigTable
    sispm10403166lMACStaticConfigTable OBJECT-TYPE
               SYNTAX      SEQUENCE OF     SISPM10403166LMACStaticConfigEntry
               MAX-ACCESS  not-accessible
               STATUS      current
               DESCRIPTION
                   "The static Mac config table."
               ::= {     sispm10403166lMAC 5 }

    sispm10403166lMACStaticConfigEntry OBJECT-TYPE
               SYNTAX          SISPM10403166LMACStaticConfigEntry
               MAX-ACCESS  not-accessible
               STATUS      current
               DESCRIPTION
                   "The static Mac config entry."
               INDEX    {     sispm10403166lMACStaticConfigIndex  }
               ::= {     sispm10403166lMACStaticConfigTable 1 }

    SISPM10403166LMACStaticConfigEntry             ::= SEQUENCE {
                sispm10403166lMACStaticConfigSwitchIndex Integer32,
                sispm10403166lMACStaticConfigIndex       Integer32,
                sispm10403166lMACStaticConfigVID         Integer32,
                sispm10403166lMACStaticConfigMACaddress  DisplayString,
                sispm10403166lMACStaticConfigPortList    DisplayString,
                sispm10403166lMACStaticConfigRowStatus   RowStatus
                }

    sispm10403166lMACStaticConfigSwitchIndex OBJECT-TYPE
               SYNTAX      Integer32(1..16)
               MAX-ACCESS  not-accessible
               STATUS      current
               DESCRIPTION
                   "Switch Index."
               ::= {     sispm10403166lMACStaticConfigEntry 1 }



    sispm10403166lMACStaticConfigIndex OBJECT-TYPE
               SYNTAX      Integer32(1..64)
               MAX-ACCESS  not-accessible
               STATUS      current
               DESCRIPTION
                   "The static entries in the MAC table are shown in this table.
                    The static MAC table can contain 64 entries."
               ::= {     sispm10403166lMACStaticConfigEntry 2 }

    sispm10403166lMACStaticConfigVID OBJECT-TYPE
               SYNTAX      Integer32(1..4095)
               MAX-ACCESS  read-create
               STATUS      current
               DESCRIPTION
                   "The VLAN ID of the entry.
                    range: 1-4095."
               ::= {     sispm10403166lMACStaticConfigEntry 3 }

    sispm10403166lMACStaticConfigMACaddress OBJECT-TYPE
               SYNTAX      DisplayString
               MAX-ACCESS  read-create
               STATUS      current
               DESCRIPTION
                   "The MAC address of the entry."
               ::= {     sispm10403166lMACStaticConfigEntry 4 }

    sispm10403166lMACStaticConfigPortList OBJECT-TYPE
               SYNTAX      DisplayString
               MAX-ACCESS  read-create
               STATUS      current
               DESCRIPTION
                   "Checkmarks indicate which ports are members of the entry.
                    Check or uncheck as needed to
                    modify the entry."
               ::= {     sispm10403166lMACStaticConfigEntry 5 }

    sispm10403166lMACStaticConfigRowStatus OBJECT-TYPE
               SYNTAX      RowStatus
               MAX-ACCESS  read-create
               STATUS      current
               DESCRIPTION
                   "This object indicates the status of this entry,
                    and is used to create/delete entries. Any
                    object in an entry of this table may be modified
                    while the value of the corresponding instance
                    of this object is active(1).
                    createAndGo, notReady not supported."
               ::= {     sispm10403166lMACStaticConfigEntry 6 }


-- =======================================================================================================================
sispm10403166lSpanningTree 						OBJECT IDENTIFIER ::= { sispm10403166lConfiguration 18 }

sispm10403166lBridgeSettings                     OBJECT IDENTIFIER ::= { sispm10403166lSpanningTree 1 }

sispm10403166lSTPProtocolVersion    OBJECT-TYPE
               SYNTAX      Integer32
               MAX-ACCESS  read-write
               STATUS      current
               DESCRIPTION
                   "0:STP
				    2:RSTP
					3:MSTP"
               ::= {     sispm10403166lBridgeSettings 1 }

sispm10403166lBridgePriority    OBJECT-TYPE
               SYNTAX      Integer32
               MAX-ACCESS  read-write
               STATUS      current
               DESCRIPTION
                   "Bridge Priority, range: 0-61440, multiple of 4096."
               ::= {     sispm10403166lBridgeSettings 2 }

sispm10403166lBridgeForwardDelay    OBJECT-TYPE
               SYNTAX      Integer32
               MAX-ACCESS  read-write
               STATUS      current
               DESCRIPTION
                   "Bridge Forward Delay, range: 4-30 seconds."
               ::= {     sispm10403166lBridgeSettings 3 }

sispm10403166lBridgeMaxAge    OBJECT-TYPE
               SYNTAX      Integer32
               MAX-ACCESS  read-write
               STATUS      current
               DESCRIPTION
                   "Bridge MaxAge, range:6-40 seconds."
               ::= {     sispm10403166lBridgeSettings 4 }

sispm10403166lBridgeMaxHops    OBJECT-TYPE
               SYNTAX      Integer32
               MAX-ACCESS  read-write
               STATUS      current
               DESCRIPTION
                   "Bridge Max Hops, range:6-40 hops."
               ::= {     sispm10403166lBridgeSettings 5 }

sispm10403166lBridgetxHoldCount    OBJECT-TYPE
               SYNTAX      Integer32
               MAX-ACCESS  read-write
               STATUS      current
               DESCRIPTION
                   "Bridge Transmit Hold Count,range: 1-10 bpdu's per second. "
               ::= {     sispm10403166lBridgeSettings 6 }

sispm10403166lBridgeBPDUFilter    OBJECT-TYPE
               SYNTAX      Integer32
               MAX-ACCESS  read-write
               STATUS      current
               DESCRIPTION
                   "Bridge BPD UFilter
              		0:disable
                    1:enable					"
               ::= {     sispm10403166lBridgeSettings 7 }

sispm10403166lBridgeBPDUGuard    OBJECT-TYPE
               SYNTAX      Integer32
               MAX-ACCESS  read-write
               STATUS      current
               DESCRIPTION
                   "Bridge BPDU Guard
              		0:disable
                    1:enable					   "
               ::= {     sispm10403166lBridgeSettings 8 }

sispm10403166lBridgeerrorRecoveryDelay    OBJECT-TYPE
               SYNTAX      Integer32
               MAX-ACCESS  read-write
               STATUS      current
               DESCRIPTION
                   "Bridge error Recovery Delay
				   range:30-86400 seconds
				   0:disable
				   "
               ::= {     sispm10403166lBridgeSettings 9 }

sispm10403166lBridgeHelloTime    OBJECT-TYPE
               SYNTAX      Integer32
               MAX-ACCESS  read-write
               STATUS      current
               DESCRIPTION
                   "The interval between sending STP BPDU's. Valid values are in the range 1 to 10 seconds,
				   default:2 seconds."
               ::= {     sispm10403166lBridgeSettings 10 }

sispm10403166lMSTIMapping                        OBJECT IDENTIFIER ::= { sispm10403166lSpanningTree 2 }
sispm10403166lConfigName    OBJECT-TYPE
               SYNTAX      DisplayString
               MAX-ACCESS  read-write
               STATUS      current
               DESCRIPTION
                   "Configuration Name, identify the VLAN to MSTI mapping"
               ::= {     sispm10403166lMSTIMapping 1 }

sispm10403166lConfigRevision    OBJECT-TYPE
               SYNTAX      Integer32
               MAX-ACCESS  read-write
               STATUS      current
               DESCRIPTION
                   "Configuration Revision. range:0-65535 "
               ::= {     sispm10403166lMSTIMapping 2 }

sispm10403166lMSTIMappingVLAN                    OBJECT IDENTIFIER ::= { sispm10403166lSpanningTree 3 }
sispm10403166lConfigMstiName1    OBJECT-TYPE
               SYNTAX      DisplayString
               MAX-ACCESS  read-write
               STATUS      current
               DESCRIPTION
                   "The list of VLANs mapped to the MSTI1.
				    The VLANs can be given as a single (xx, xx being between 1 and 4094) VLAN, or a range (xx-yy), each of which must be separated with comma and/or space. "
               ::= {     sispm10403166lMSTIMappingVLAN 1 }

sispm10403166lConfigMstiName2    OBJECT-TYPE
               SYNTAX      DisplayString
               MAX-ACCESS  read-write
               STATUS      current
               DESCRIPTION
                   "The list of VLANs mapped to the MSTI2.
				    The VLANs can be given as a single (xx, xx being between 1 and 4094) VLAN, or a range (xx-yy), each of which must be separated with comma and/or space.  "
               ::= {     sispm10403166lMSTIMappingVLAN 2 }

sispm10403166lConfigMstiName3    OBJECT-TYPE
               SYNTAX      DisplayString
               MAX-ACCESS  read-write
               STATUS      current
               DESCRIPTION
                   "The list of VLANs mapped to the MSTI3.
				    The VLANs can be given as a single (xx, xx being between 1 and 4094) VLAN, or a range (xx-yy), each of which must be separated with comma and/or space. "
               ::= {     sispm10403166lMSTIMappingVLAN 3 }

sispm10403166lConfigMstiName4    OBJECT-TYPE
               SYNTAX      DisplayString
               MAX-ACCESS  read-write
               STATUS      current
               DESCRIPTION
                   "The list of VLANs mapped to the MSTI4.
				    The VLANs can be given as a single (xx, xx being between 1 and 4094) VLAN, or a range (xx-yy), each of which must be separated with comma and/or space. "
               ::= {     sispm10403166lMSTIMappingVLAN 4 }

sispm10403166lConfigMstiName5    OBJECT-TYPE
               SYNTAX      DisplayString
               MAX-ACCESS  read-write
               STATUS      current
               DESCRIPTION
                   "The list of VLANs mapped to the MSTI5.
				    The VLANs can be given as a single (xx, xx being between 1 and 4094) VLAN, or a range (xx-yy), each of which must be separated with comma and/or space. "
               ::= {     sispm10403166lMSTIMappingVLAN 5 }

sispm10403166lConfigMstiName6    OBJECT-TYPE
               SYNTAX      DisplayString
               MAX-ACCESS  read-write
               STATUS      current
               DESCRIPTION
                   "The list of VLANs mapped to the MSTI6.
				    The VLANs can be given as a single (xx, xx being between 1 and 4094) VLAN, or a range (xx-yy), each of which must be separated with comma and/or space. "
               ::= {     sispm10403166lMSTIMappingVLAN 6 }

sispm10403166lConfigMstiName7    OBJECT-TYPE
               SYNTAX      DisplayString
               MAX-ACCESS  read-write
               STATUS      current
               DESCRIPTION
                   "The list of VLANs mapped to the MSTI7.
				    The VLANs can be given as a single (xx, xx being between 1 and 4094) VLAN, or a range (xx-yy), each of which must be separated with comma and/or space. "
               ::= {     sispm10403166lMSTIMappingVLAN 7 }

sispm10403166lMSTIPriorities                     OBJECT IDENTIFIER ::= { sispm10403166lSpanningTree 4 }

sispm10403166lCSTIPriority   OBJECT-TYPE
               SYNTAX      Integer32
               MAX-ACCESS  read-write
               STATUS      current
               DESCRIPTION
                   "CSTI Priority. range: 0-61440, multiple of 4096. Lower numeric values have better priority."
               ::= {     sispm10403166lMSTIPriorities 1 }

sispm10403166lMSTI1Priority   OBJECT-TYPE
               SYNTAX      Integer32
               MAX-ACCESS  read-write
               STATUS      current
               DESCRIPTION
                   "MSTI1 Priority. range: 0-61440, multiple of 4096. Lower numeric values have better priority."
               ::= {     sispm10403166lMSTIPriorities 2 }

sispm10403166lMSTI2Priority   OBJECT-TYPE
               SYNTAX      Integer32
               MAX-ACCESS  read-write
               STATUS      current
               DESCRIPTION
                   "MSTI2 Priority. range: 0-61440, multiple of 4096. Lower numeric values have better priority."
               ::= {     sispm10403166lMSTIPriorities 3 }

sispm10403166lMSTI3Priority   OBJECT-TYPE
               SYNTAX      Integer32
               MAX-ACCESS  read-write
               STATUS      current
               DESCRIPTION
                   "MSTI3 Priority. range: 0-61440, multiple of 4096. Lower numeric values have better priority."
               ::= {     sispm10403166lMSTIPriorities 4 }
sispm10403166lMSTI4Priority   OBJECT-TYPE
               SYNTAX      Integer32
               MAX-ACCESS  read-write
               STATUS      current
               DESCRIPTION
                   "MSTI4 Priority. range: 0-61440, multiple of 4096. Lower numeric values have better priority."
               ::= {     sispm10403166lMSTIPriorities 5 }
sispm10403166lMSTI5Priority   OBJECT-TYPE
               SYNTAX      Integer32
               MAX-ACCESS  read-write
               STATUS      current
               DESCRIPTION
                   "MSTI5 Priority. range: 0-61440, multiple of 4096. Lower numeric values have better priority."
               ::= {     sispm10403166lMSTIPriorities 6 }

sispm10403166lMSTI6Priority   OBJECT-TYPE
               SYNTAX      Integer32
               MAX-ACCESS  read-write
               STATUS      current
               DESCRIPTION
                   "MSTI6 Priority. range: 0-61440, multiple of 4096. Lower numeric values have better priority."
               ::= {     sispm10403166lMSTIPriorities 7 }
sispm10403166lMSTI7Priority   OBJECT-TYPE
               SYNTAX      Integer32
               MAX-ACCESS  read-write
               STATUS      current
               DESCRIPTION
                   "MSTI7 Priority. range: 0-61440, multiple of 4096. Lower numeric values have better priority."
               ::= {     sispm10403166lMSTIPriorities 8 }


sispm10403166lCISTPorts                          OBJECT IDENTIFIER ::= { sispm10403166lSpanningTree 5 }

sispm10403166lCISTAggregatedEnable   OBJECT-TYPE
               SYNTAX      Integer32 (0|1)
               MAX-ACCESS  read-write
               STATUS      current
               DESCRIPTION
                   "CIST Port Enable. range: 0-1.
				   0:disable
				   1:enable."
               ::= {     sispm10403166lCISTPorts 1 }

sispm10403166lCISTAggregatedPathCost   OBJECT-TYPE
               SYNTAX      Integer32 (0..200000000)
               MAX-ACCESS  read-write
               STATUS      current
               DESCRIPTION
                   "CIST Port Path Cost. range: 0-200000000. 0 is Auto."
               ::= {     sispm10403166lCISTPorts 2 }

sispm10403166lCISTAggregatedPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sispm10403166lCISTPorts 3 }

sispm10403166lCISTAggregatedAdminEdge   OBJECT-TYPE
               SYNTAX      Integer32 (0|1)
               MAX-ACCESS  read-write
               STATUS      current
               DESCRIPTION
                   "CIST Port Admin Edge. range: 0-1.
				   0:Non-Edge
				   1:Edge."
               ::= {     sispm10403166lCISTPorts 4 }

sispm10403166lCISTAggregatedAutoEdge   OBJECT-TYPE
               SYNTAX      Integer32 (0|1)
               MAX-ACCESS  read-write
               STATUS      current
               DESCRIPTION
                   "CIST Port Auto Edge. range: 0-1.
				   0:disable
				   1:enable."
               ::= {     sispm10403166lCISTPorts 5 }

sispm10403166lCISTAggregatedrestrictedRole   OBJECT-TYPE
               SYNTAX      Integer32 (0|1)
               MAX-ACCESS  read-write
               STATUS      current
               DESCRIPTION
                   "CIST Port restricted Role. range: 0-1.
				   0:disable
				   1:enable."
               ::= {     sispm10403166lCISTPorts 6 }

sispm10403166lCISTAggregatedrestrictedTcn   OBJECT-TYPE
               SYNTAX      Integer32 (0|1)
               MAX-ACCESS  read-write
               STATUS      current
               DESCRIPTION
                   "CIST Port restricted Tcn. range: 0-1.
				   0:disable
				   1:enable."
               ::= {     sispm10403166lCISTPorts 7 }

sispm10403166lCISTAggregatedbpduGuard   OBJECT-TYPE
               SYNTAX      Integer32 (0|1)
               MAX-ACCESS  read-write
               STATUS      current
               DESCRIPTION
                   "CIST Port bpdu Guard. range: 0-1.
				   0:disable
				   1:enable."
               ::= {     sispm10403166lCISTPorts 8 }

sispm10403166lCISTAggregatedPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sispm10403166lCISTPorts 9 }


sispm10403166lCISTPortsTable OBJECT-TYPE
   SYNTAX      SEQUENCE OF SISPM10403166LCISTPortsEntry
   MAX-ACCESS  not-accessible
   STATUS      current
   DESCRIPTION
        "CIST port table."
    ::= { sispm10403166lCISTPorts 10 }

sispm10403166lCISTPortsEntry OBJECT-TYPE
    SYNTAX        SISPM10403166LCISTPortsEntry
    MAX-ACCESS    not-accessible
    STATUS        current
    DESCRIPTION
        "An entry in the CIST Ports Table."
    INDEX        { sispm10403166lCISTPortIndex }
    ::= { sispm10403166lCISTPortsTable 1 }

SISPM10403166LCISTPortsEntry ::=
    SEQUENCE {
        sispm10403166lCISTPortIndex                 Integer32,
        sispm10403166lCISTPortEnable                Integer32,
        sispm10403166lCISTPortPathCost              Integer32,
        sispm10403166lCISTPortPortPriority          Integer32,
        sispm10403166lCISTPortAdminEdge             Integer32,
        sispm10403166lCISTPortAutoEdge              Integer32,
        sispm10403166lCISTPortrestrictedRole        Integer32,
        sispm10403166lCISTPortrestrictedTcn         Integer32,
        sispm10403166lCISTPortbpduGuard             Integer32,
        sispm10403166lCISTPortPointToPoint          Integer32,
        sispm10403166lCISTPortRootGuard             Integer32
    }

sispm10403166lCISTPortIndex   OBJECT-TYPE
               SYNTAX      Integer32 (1..53)
               MAX-ACCESS  not-accessible
               STATUS      current
               DESCRIPTION
                   "CIST Port Index. range: 1-53. 53 is Aggregated Port Configuration."
               ::= {     sispm10403166lCISTPortsEntry 1 }

sispm10403166lCISTPortEnable   OBJECT-TYPE
               SYNTAX      Integer32 (0|1)
               MAX-ACCESS  read-write
               STATUS      current
               DESCRIPTION
                   "CIST Port Enable. range: 0-1.
				   0:disable
				   1:enable."
               ::= {     sispm10403166lCISTPortsEntry 2 }

sispm10403166lCISTPortPathCost   OBJECT-TYPE
               SYNTAX      Integer32 (0..200000000)
               MAX-ACCESS  read-write
               STATUS      current
               DESCRIPTION
                   "CIST Port Path Cost. range: 0-200000000. 0 is Auto."
               ::= {     sispm10403166lCISTPortsEntry 3 }

sispm10403166lCISTPortPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sispm10403166lCISTPortsEntry 4 }

sispm10403166lCISTPortAdminEdge   OBJECT-TYPE
               SYNTAX      Integer32 (0|1)
               MAX-ACCESS  read-write
               STATUS      current
               DESCRIPTION
                   "CIST Port Admin Edge. range: 0-1.
				   0:Non-Edge
				   1:Edge."
               ::= {     sispm10403166lCISTPortsEntry 5 }

sispm10403166lCISTPortAutoEdge   OBJECT-TYPE
               SYNTAX      Integer32 (0|1)
               MAX-ACCESS  read-write
               STATUS      current
               DESCRIPTION
                   "CIST Port Auto Edge. range: 0-1.
				   0:disable
				   1:enable."
               ::= {     sispm10403166lCISTPortsEntry 6 }

sispm10403166lCISTPortrestrictedRole   OBJECT-TYPE
               SYNTAX      Integer32 (0|1)
               MAX-ACCESS  read-write
               STATUS      current
               DESCRIPTION
                   "CIST Port restricted Role. range: 0-1.
				   0:disable
				   1:enable."
               ::= {     sispm10403166lCISTPortsEntry 7 }

sispm10403166lCISTPortrestrictedTcn   OBJECT-TYPE
               SYNTAX      Integer32 (0|1)
               MAX-ACCESS  read-write
               STATUS      current
               DESCRIPTION
                   "CIST Port restricted Tcn. range: 0-1.
				   0:disable
				   1:enable."
               ::= {     sispm10403166lCISTPortsEntry 8 }

sispm10403166lCISTPortbpduGuard   OBJECT-TYPE
               SYNTAX      Integer32 (0|1)
               MAX-ACCESS  read-write
               STATUS      current
               DESCRIPTION
                   "CIST Port bpdu Guard. range: 0-1.
				   0:disable
				   1:enable."
               ::= {     sispm10403166lCISTPortsEntry 9 }

sispm10403166lCISTPortPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sispm10403166lCISTPortsEntry 10 }

sispm10403166lCISTPortRootGuard   OBJECT-TYPE
               SYNTAX      Integer32 (0|1)
               MAX-ACCESS  read-write
               STATUS      current
               DESCRIPTION
                   "CIST Port root guard. range: 0-1.
				   0:disable
				   1:enable."
               ::= {     sispm10403166lCISTPortsEntry 11 }

sispm10403166lMSTIPorts                          OBJECT IDENTIFIER ::= { sispm10403166lSpanningTree 6 }


sispm10403166lMSTIAggregatedPortsTable OBJECT-TYPE
   SYNTAX      SEQUENCE OF SISPM10403166LMSTIAggregatedPortsEntry
   MAX-ACCESS  not-accessible
   STATUS      current
   DESCRIPTION
       "A table of MSTI ports."
    ::= { sispm10403166lMSTIPorts 1 }

sispm10403166lMSTIAggregatedPortsEntry OBJECT-TYPE
    SYNTAX        SISPM10403166LMSTIAggregatedPortsEntry
    MAX-ACCESS    not-accessible
    STATUS        current
    DESCRIPTION
        "An entry in the MSTI ports Table."
    INDEX        { sispm10403166lMSTIAggregatedPortsMSTIndex }
    ::= { sispm10403166lMSTIAggregatedPortsTable 1 }

SISPM10403166LMSTIAggregatedPortsEntry ::=
    SEQUENCE {
        sispm10403166lMSTIAggregatedPortsMSTIndex                        Integer32,
        sispm10403166lMSTIAggregatedPortsPathCost                        Integer32,
        sispm10403166lMSTIAggregatedPortsPortPriority                    Integer32
    }

sispm10403166lMSTIAggregatedPortsMSTIndex OBJECT-TYPE
   SYNTAX      Integer32 (1..7)
   MAX-ACCESS  not-accessible
   STATUS      current
   DESCRIPTION
       "MST index, range:1-7"
   ::= {sispm10403166lMSTIAggregatedPortsEntry 1 }

sispm10403166lMSTIAggregatedPortsPathCost   OBJECT-TYPE
   SYNTAX      Integer32 (0..200000000)
   MAX-ACCESS  read-write
   STATUS      current
   DESCRIPTION
       "MST Path Cost. range: 0-200000000. 0 is Auto."
   ::= {sispm10403166lMSTIAggregatedPortsEntry 3 }

sispm10403166lMSTIAggregatedPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sispm10403166lMSTIAggregatedPortsEntry 4 }


sispm10403166lMSTIPortsTable OBJECT-TYPE
   SYNTAX      SEQUENCE OF SISPM10403166LMSTIPortsEntry
   MAX-ACCESS  not-accessible
   STATUS      current
   DESCRIPTION
       "A table of MSTI ports."
    ::= { sispm10403166lMSTIPorts 2 }

sispm10403166lMSTIPortsEntry OBJECT-TYPE
    SYNTAX        SISPM10403166LMSTIPortsEntry
    MAX-ACCESS    not-accessible
    STATUS        current
    DESCRIPTION
        "An entry in the MSTI ports Table."
    INDEX        { sispm10403166lMSTIPortsMSTIndex, sispm10403166lMSTIPortsPortIndex }
    ::= { sispm10403166lMSTIPortsTable 1 }

SISPM10403166LMSTIPortsEntry ::=
    SEQUENCE {
        sispm10403166lMSTIPortsMSTIndex                        Integer32,
        sispm10403166lMSTIPortsPortIndex                       Integer32,
        sispm10403166lMSTIPortsPathCost                        Integer32,
        sispm10403166lMSTIPortsPortPriority                    Integer32
    }

sispm10403166lMSTIPortsMSTIndex OBJECT-TYPE
   SYNTAX      Integer32 (1..7)
   MAX-ACCESS  not-accessible
   STATUS      current
   DESCRIPTION
       "MST index, range:1-7"
   ::= {sispm10403166lMSTIPortsEntry 1 }

sispm10403166lMSTIPortsPortIndex OBJECT-TYPE
   SYNTAX      Integer32 (1..53)
   MAX-ACCESS  not-accessible
   STATUS      current
   DESCRIPTION
       "Port index, range 1-53, 53 is Aggregated Ports Configuration."
   ::= {sispm10403166lMSTIPortsEntry 2 }

sispm10403166lMSTIPortsPathCost   OBJECT-TYPE
   SYNTAX      Integer32 (0..200000000)
   MAX-ACCESS  read-write
   STATUS      current
   DESCRIPTION
       "MST Path Cost. range: 0-200000000. 0 is Auto."
   ::= {sispm10403166lMSTIPortsEntry 3 }

sispm10403166lMSTIPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sispm10403166lMSTIPortsEntry 4 }

-- =======================================================================================================================
sispm10403166lPrivateVLANs 						OBJECT IDENTIFIER ::= { sispm10403166lConfiguration 19 }

sispm10403166lPVLANMembershipTable  OBJECT-TYPE
   SYNTAX      SEQUENCE OF SISPM10403166LPVLANMembershipEntry
   MAX-ACCESS  not-accessible
   STATUS      current
   DESCRIPTION
       "A table of Private VLAN Membership."
 ::= { sispm10403166lPrivateVLANs 1 }

sispm10403166lPVLANMembershipEntry OBJECT-TYPE
    SYNTAX        SISPM10403166LPVLANMembershipEntry
    MAX-ACCESS    not-accessible
    STATUS        current
    DESCRIPTION
        "An entry in the private VLAN table."
    INDEX        { sispm10403166lPVLANMembershipIndex }
    ::= { sispm10403166lPVLANMembershipTable 1 }

SISPM10403166LPVLANMembershipEntry ::=
    SEQUENCE {
        sispm10403166lPVLANMembershipIndex                    Integer32,
        sispm10403166lPVLANID                                 Integer32,
        sispm10403166lPVLANMembers                            DisplayString,
        sispm10403166lPVLANRowStatus                          RowStatus
    }

sispm10403166lPVLANMembershipIndex OBJECT-TYPE
   SYNTAX      Integer32 (1..28)
   MAX-ACCESS  not-accessible
   STATUS      current
   DESCRIPTION
       "PVLAN membership index. Range:1-28."
   ::= {sispm10403166lPVLANMembershipEntry 1 }

sispm10403166lPVLANID OBJECT-TYPE
   SYNTAX      Integer32 (1..28)
   MAX-ACCESS  read-create
   STATUS      current
   DESCRIPTION
       "PVLAN ID. Range:1-28."
   ::= {sispm10403166lPVLANMembershipEntry 2 }

sispm10403166lPVLANMembers OBJECT-TYPE
   SYNTAX      DisplayString
   MAX-ACCESS  read-create
   STATUS      current
   DESCRIPTION
       "PVLAN Members. Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1',
        then that port is included in the set of ports; the port
        is not included if its bit has a value of '0'."
   ::= {sispm10403166lPVLANMembershipEntry 3 }

sispm10403166lPVLANRowStatus OBJECT-TYPE
   SYNTAX      RowStatus
   MAX-ACCESS  read-create
   STATUS      current
   DESCRIPTION
       "PVLAN Row Status."
   ::= {sispm10403166lPVLANMembershipEntry 4 }

sispm10403166lPVLANPortIsolationTable  OBJECT-TYPE
   SYNTAX      SEQUENCE OF SISPM10403166LPVLANPortIsolationEntry
   MAX-ACCESS  not-accessible
   STATUS      current
   DESCRIPTION
       "A table of Private VLAN Port Isolation."
 ::= { sispm10403166lPrivateVLANs 2 }

sispm10403166lPVLANPortIsolationEntry OBJECT-TYPE
    SYNTAX        SISPM10403166LPVLANPortIsolationEntry
    MAX-ACCESS    not-accessible
    STATUS        current
    DESCRIPTION
        "An entry in the private VLAN table."
    INDEX        { sispm10403166lPVLANPortIsolationIndex }
    ::= { sispm10403166lPVLANPortIsolationTable 1 }

SISPM10403166LPVLANPortIsolationEntry ::=
    SEQUENCE {
        sispm10403166lPVLANPortIsolationIndex                 Integer32,
        sispm10403166lPVLANPortIsolationPortMembers           Integer32
    }

sispm10403166lPVLANPortIsolationIndex OBJECT-TYPE
   SYNTAX      Integer32 (1..28)
   MAX-ACCESS  not-accessible
   STATUS      current
   DESCRIPTION
       "PVLAN Port Isolation Index. Range:1-28."
   ::= {sispm10403166lPVLANPortIsolationEntry 1 }

sispm10403166lPVLANPortIsolationPortMembers OBJECT-TYPE
   SYNTAX      Integer32 (0|1)
   MAX-ACCESS  read-write
   STATUS      current
   DESCRIPTION
       "PVLAN Port Isolation Port Members enable/disable. Range:0-1.
	   1:Port Isolation enable  on that port.
	   0:Port Isolation disable on that port."
   ::= {sispm10403166lPVLANPortIsolationEntry 2 }

-- =======================================================================================================================


sispm10403166lsFlow 						OBJECT IDENTIFIER ::= { sispm10403166lConfiguration 20 }

      sispm10403166lsFlowVersion OBJECT-TYPE
              SYNTAX      SnmpAdminString
              MAX-ACCESS  read-only
              STATUS      current
              DESCRIPTION "Uniquely identifies the version and implementation of this MIB. The version string must have the following structure: <MIB Version>;<Organization>;<Software Revision> where: <MIB Version>  must be '1.3', the version of this MIB.
                    <Organization> the name of the organization responsible for the agent implementation. <Revision>     the specific software build of this agent.
                 As an example, the string '1.3;InMon Corp.;2.1.1' indicates that this agent implements version '1.2' of the SFLOW MIB, that
                 it was developed by 'InMon Corp.' and that the software build is '2.1.1'.
                 The MIB Version will change with each revision of the SFLOW MIB.
                 Management entities must check the MIB Version and not attempt to manage agents with MIB Versions greater than that for which
                 they were designed.
                 Note: The sFlow Datagram Format has an independent version number which may change independently from <MIB Version>.
                       <MIB Version> applies to the structure and semantics of the SFLOW MIB only." DEFVAL { "1.3;;" }
              ::= { sispm10403166lsFlow 1 }

      sispm10403166lsFlowAgentAddressType OBJECT-TYPE
              SYNTAX      InetAddressType
              MAX-ACCESS  read-only
              STATUS      current
              DESCRIPTION "The address type of the address associated with this agent. Only ipv4 and ipv6 types are supported. ipv4:1, ipv6:2."
              ::= { sispm10403166lsFlow 2 }

      sispm10403166lsFlowAgentAddress OBJECT-TYPE
              SYNTAX      IpAddress
              MAX-ACCESS  read-write
              STATUS      current
              DESCRIPTION "The IP address associated with this agent. In the case of a multi-homed agent, this should be the loopback address of the
                 agent. The sFlowAgent address must provide SNMP connectivity to the agent. The address should be an invariant that does not
                 change as interfaces are reconfigured, enabled, disabled, added or removed. A manager should be able to use the
                 sFlowAgentAddress as a unique key that will identify this agent over extended periods of time so that a history can
                 be maintained."
              ::= { sispm10403166lsFlow 3 }
      --
      -- Receiver Table
      --
      sispm10403166lsFlowRcvrTable OBJECT-TYPE
              SYNTAX      SEQUENCE OF SISPM10403166LSFlowRcvrEntry
              MAX-ACCESS  not-accessible
              STATUS      current
              DESCRIPTION "A table of the receivers of sFlow information."
              ::= { sispm10403166lsFlow 4 }

      sispm10403166lsFlowRcvrEntry OBJECT-TYPE
              SYNTAX SISPM10403166LSFlowRcvrEntry
              MAX-ACCESS  not-accessible
              STATUS      current
              DESCRIPTION "Attributes of an sFlow Receiver."
              INDEX { sispm10403166lsFlowRcvrIndex }
              ::= { sispm10403166lsFlowRcvrTable 1 }

      SISPM10403166LSFlowRcvrEntry ::= SEQUENCE {
              sispm10403166lsFlowRcvrIndex                    Integer32,
              sispm10403166lsFlowRcvrOwner                    OwnerString,
              sispm10403166lsFlowRcvrTimeout                  Integer32,
              sispm10403166lsFlowRcvrMaximumDatagramSize      Integer32,
              sispm10403166lsFlowRcvrAddressType              InetAddressType,
              sispm10403166lsFlowRcvrAddress                  IpAddress,
              sispm10403166lsFlowRcvrPort                     Integer32,
              sispm10403166lsFlowRcvrDatagramVersion          Integer32 }

      sispm10403166lsFlowRcvrIndex OBJECT-TYPE
              SYNTAX      Integer32 (1..65535)
              MAX-ACCESS  not-accessible
              STATUS      current
              DESCRIPTION "Index into sFlowReceiverTable."
              ::= { sispm10403166lsFlowRcvrEntry 1 }

      sispm10403166lsFlowRcvrOwner OBJECT-TYPE
              SYNTAX      OwnerString
              MAX-ACCESS  read-write
              STATUS      current
              DESCRIPTION "The entity making use of this sFlowRcvrTable entry. The empty string indicates that the entry is currently unclaimed.
                 An entity wishing to claim an sFlowRcvrTable entry must ensure that the entry is unclaimed before trying to claim it.
                 The entry is claimed by setting the owner string. The entry must be claimed before any changes can be made to other sampler
                 objects.
                 In order to avoid a race condition, the entity taking control of the sampler must set both the owner and a value for
                 sFlowRcvrTimeout in the same SNMP set request.
                 When a management entity is finished using the sampler, it should set the value of sFlowRcvrOwner back to unclaimed.
                 The agent must restore all other entities this row to their default values when the owner is set to unclaimed. It must
                 also free all other resources associated with this sFlowRcvrTable entry.
                 This mechanism provides no enforcement and relies on the cooperation of management entities in order to ensure that
                 competition for a receiver entry is fairly resolved." DEFVAL { "" }
              ::= { sispm10403166lsFlowRcvrEntry 2 }

      sispm10403166lsFlowRcvrTimeout OBJECT-TYPE
              SYNTAX      Integer32
              MAX-ACCESS  read-write
              STATUS      current
              DESCRIPTION "The time (in seconds) remaining before the sampler is released and stops sampling. When set, the owner establishes control
                 for the specified period. When read, the remaining time in the interval is returned.
                 A management entity wanting to maintain control of the sampler is responsible for setting a new value before the old one
                 expires.
                 When the interval expires, the agent is responsible for restoring all other entities in this row to their default
                 values. It must also free all other resources associated with this sFlowRcvrTable entry." DEFVAL { 0 }
              ::= { sispm10403166lsFlowRcvrEntry 3 }

      sispm10403166lsFlowRcvrMaximumDatagramSize OBJECT-TYPE
              SYNTAX      Integer32
              MAX-ACCESS  read-write
              STATUS      current
              DESCRIPTION "The maximum number of data bytes that can be sent in a single sample datagram. The manager should set this value to avoid fragmentation of the sFlow datagrams." DEFVAL { 1400 }
              ::= { sispm10403166lsFlowRcvrEntry 4 }

      sispm10403166lsFlowRcvrAddressType OBJECT-TYPE
              SYNTAX      InetAddressType
              MAX-ACCESS  read-write
              STATUS      current
              DESCRIPTION "The type of sFlowRcvrCollectorAddress." DEFVAL { ipv4 }
              ::= { sispm10403166lsFlowRcvrEntry 5 }

      sispm10403166lsFlowRcvrAddress OBJECT-TYPE
              SYNTAX      IpAddress
              MAX-ACCESS  read-write
              STATUS      current
              DESCRIPTION "The IP address of the sFlow collector. If set to 0.0.0.0 not sFlow datagrams will be sent." DEFVAL { '00000000'h }  -- 0.0.0.0
              ::= { sispm10403166lsFlowRcvrEntry 6 }

      sispm10403166lsFlowRcvrPort OBJECT-TYPE
              SYNTAX      Integer32
              MAX-ACCESS  read-write
              STATUS      current
              DESCRIPTION "The destination port for sFlow datagrams." DEFVAL { 6343 }
              ::= { sispm10403166lsFlowRcvrEntry 7 }

      sispm10403166lsFlowRcvrDatagramVersion OBJECT-TYPE
              SYNTAX      Integer32
              MAX-ACCESS  read-write
              STATUS      current
              DESCRIPTION "The version of sFlow datagrams that should be sent.
                 When set to a value not support by the agent, the agent should adjust the value to the highest supported value less than the
                 requested value, or return an SNMP bad value error if no such value exists." DEFVAL { 5 }
              ::= { sispm10403166lsFlowRcvrEntry 8 }

      --
      -- Flow Sampling Table
      --
      sispm10403166lsFlowFsTable OBJECT-TYPE
              SYNTAX      SEQUENCE OF SISPM10403166LSFlowFsEntry
              MAX-ACCESS  not-accessible
              STATUS      current
              DESCRIPTION "A table of the flow samplers within a device."
              ::= { sispm10403166lsFlow 5 }

      sispm10403166lsFlowFsEntry OBJECT-TYPE
              SYNTAX      SISPM10403166LSFlowFsEntry
              MAX-ACCESS  not-accessible
              STATUS      current
              DESCRIPTION "Attributes of a flow sampler."
              INDEX { sispm10403166lsFlowFsDataSource, sispm10403166lsFlowFsInstance }
              ::= { sispm10403166lsFlowFsTable 1 }

      SISPM10403166LSFlowFsEntry ::= SEQUENCE {
              sispm10403166lsFlowFsDataSource               Integer32,
              sispm10403166lsFlowFsInstance                 Integer32,
              sispm10403166lsFlowFsReceiver                 Integer32,
              sispm10403166lsFlowFsPacketSamplingRate       Integer32,
              sispm10403166lsFlowFsMaximumHeaderSize        Integer32,
              sispm10403166lsFlowFsType                     Integer32
              }

      sispm10403166lsFlowFsDataSource OBJECT-TYPE
              SYNTAX      Integer32(1..65535)
              MAX-ACCESS  not-accessible
              STATUS      current
              DESCRIPTION "sFlowDataSource for this flow sampler."
              ::= { sispm10403166lsFlowFsEntry 1 }

      sispm10403166lsFlowFsInstance OBJECT-TYPE
              SYNTAX      Integer32 (1..65535)
              MAX-ACCESS  not-accessible
              STATUS      current
              DESCRIPTION "The sFlow instance for this flow sampler."
              ::= { sispm10403166lsFlowFsEntry 2 }

      sispm10403166lsFlowFsReceiver OBJECT-TYPE
              SYNTAX      Integer32
              MAX-ACCESS  read-write
              STATUS      current
              DESCRIPTION "The SFlowReceiver for this flow sampler." DEFVAL { 0 }
              ::= { sispm10403166lsFlowFsEntry 3 }

      sispm10403166lsFlowFsPacketSamplingRate OBJECT-TYPE
              SYNTAX      Integer32
              MAX-ACCESS  read-write
              STATUS      current
              DESCRIPTION "The statistical sampling rate for packet sampling from this source.
                 Set to N to sample 1/Nth of the packets in the monitored flows. An agent should choose its own algorithm to introduce variance
                 into the sampling so that exactly every Nth packet is not counted. A sampling rate of 1 counts all packets. A sampling
                 rate of 0 disables sampling.
                 The agent is permitted to have minimum and maximum allowable values for the sampling rate. A minimum rate lets the agent
                 designer set an upper bound on the overhead associated with sampling, and a maximum rate may be the result of hardware
                 restrictions (such as counter size). In addition not all values between the maximum and minimum may be realizable as the
                 sampling rate (again because of implementation considerations).
                 When the sampling rate is set the agent is free to adjust the value so that it lies between the maximum and minimum values
                 and has the closest achievable value.
                 When read, the agent must return the actual sampling rate it will be using (after the adjustments previously described). The
                 sampling algorithm must converge so that over time the number of packets sampled approaches 1/Nth of the total number of
                 packets in the monitored flows." DEFVAL { 0 }
              ::= { sispm10403166lsFlowFsEntry 4 }

      sispm10403166lsFlowFsMaximumHeaderSize OBJECT-TYPE
              SYNTAX      Integer32
              MAX-ACCESS  read-write
              STATUS      current
              DESCRIPTION "The maximum number of bytes that should be copied from a sampled packet. The agent may have an internal maximum and
                 minimum permissible sizes. If an attempt is made to set this value outside the permissible range then the agent should
                 adjust the value to the closest permissible value." DEFVAL { 128 }
              ::= { sispm10403166lsFlowFsEntry 5 }

      sispm10403166lsFlowFsType OBJECT-TYPE
              SYNTAX      Integer32
              MAX-ACCESS  read-write
              STATUS      current
              DESCRIPTION "Flow Sample Type.
			  1:Rx
			  2:Tx
			  3:All."
			  DEFVAL { 2 }
              ::= { sispm10403166lsFlowFsEntry 6 }
      --
      -- Counter Polling Table
      --
      sispm10403166lsFlowCpTable OBJECT-TYPE
              SYNTAX      SEQUENCE OF SISPM10403166LSFlowCpEntry
              MAX-ACCESS  not-accessible
              STATUS      current
              DESCRIPTION "A table of the counter pollers within a device."
              ::= { sispm10403166lsFlow 6 }

      sispm10403166lsFlowCpEntry OBJECT-TYPE
              SYNTAX      SISPM10403166LSFlowCpEntry
              MAX-ACCESS  not-accessible
              STATUS      current
              DESCRIPTION "Attributes of a counter poller."
              INDEX { sispm10403166lsFlowCpDataSource, sispm10403166lsFlowCpInstance }
              ::= { sispm10403166lsFlowCpTable 1 }

      SISPM10403166LSFlowCpEntry ::= SEQUENCE {
              sispm10403166lsFlowCpDataSource               Integer32,
              sispm10403166lsFlowCpInstance                 Integer32,
              sispm10403166lsFlowCpReceiver                 Integer32,
              sispm10403166lsFlowCpInterval                 Integer32
              }

      sispm10403166lsFlowCpDataSource OBJECT-TYPE
              SYNTAX      Integer32(1..65535)
              MAX-ACCESS  not-accessible
              STATUS      current
              DESCRIPTION "Identifies the source of the data for the counter poller."
              ::= { sispm10403166lsFlowCpEntry 1 }

      sispm10403166lsFlowCpInstance OBJECT-TYPE
              SYNTAX      Integer32 (1..65535)
              MAX-ACCESS  not-accessible
              STATUS      current
              DESCRIPTION "The sFlowInstance for this counter poller."
              ::= { sispm10403166lsFlowCpEntry 2 }

      sispm10403166lsFlowCpReceiver OBJECT-TYPE
              SYNTAX      Integer32
              MAX-ACCESS  read-write
              STATUS      current
              DESCRIPTION "The SFlowReciever associated with this counter poller." DEFVAL { 0 }
              ::= { sispm10403166lsFlowCpEntry 3 }

      sispm10403166lsFlowCpInterval OBJECT-TYPE
              SYNTAX      Integer32
              MAX-ACCESS  read-write
              STATUS      current
              DESCRIPTION "The maximum number of seconds between successive samples of the counters associated with this data source. A sampling interval
                 of 0 disables counter sampling.
                 The agent is permitted to have minimum and maximum allowable values for the counter polling interval. A minimum interval
                 lets the agent designer set an upper bound on the overhead associated with polling, and a maximum interval may be the
                 result of implementation restrictions (such as counter size). In addition not all values between the maximum and minimum may
                 be realizable as the sampling interval (again because of implementation considerations).
                 When the sampling rate is set the agent is free to adjust the value so that it lies between the maximum and minimum values
                 and has the closest achievable value.
                 When read, the agent must return the actual sampling interval it will be using (after the adjustments previously described).
                 The sampling algorithm must converge so that over time the number of packets sampled approaches 1/Nth of the total number
                 of packets in the monitored flows." DEFVAL { 0 }
              ::= { sispm10403166lsFlowCpEntry 4 }

sispm10403166lLLDP                  OBJECT IDENTIFIER ::= { sispm10403166lConfiguration 21 }

    sispm10403166lLLDPConfTable OBJECT-TYPE
               SYNTAX      SEQUENCE OF     SISPM10403166LLLDPConfEntry
               MAX-ACCESS  not-accessible
               STATUS      current
               DESCRIPTION
                   " "
               ::= {     sispm10403166lLLDP 1 }

    sispm10403166lLLDPConfEntry OBJECT-TYPE
               SYNTAX          SISPM10403166LLLDPConfEntry
               MAX-ACCESS  not-accessible
               STATUS      current
               DESCRIPTION
                   " "
               INDEX    {    sispm10403166lLLDPIndex  }
               ::= {     sispm10403166lLLDPConfTable 1 }

    SISPM10403166LLLDPConfEntry             ::= SEQUENCE {
         sispm10403166lLLDPIndex        Integer32,
         sispm10403166lLLDPMode         Integer32,
         sispm10403166lLLDPCDPAware     Integer32,
         sispm10403166lLLDPTrap         Integer32,
         sispm10403166lLLDPPortDescr    Integer32,
		 sispm10403166lLLDPSysName      Integer32,
		 sispm10403166lLLDPSysDescr     Integer32,
		 sispm10403166lLLDPSysCapa      Integer32,
		 sispm10403166lLLDPMgmtAddr     Integer32
    }

    sispm10403166lLLDPIndex OBJECT-TYPE
               SYNTAX      Integer32(1..65535)
               MAX-ACCESS  read-write
               STATUS      current
               DESCRIPTION
                   "LLDP configuration index."
               ::= {     sispm10403166lLLDPConfEntry 1 }

    sispm10403166lLLDPMode OBJECT-TYPE
               SYNTAX      Integer32
               MAX-ACCESS  read-write
               STATUS      current
               DESCRIPTION
                   "0:Disable
		   1:Tx only
		   2:Rx only
		   3:Enabled"
               ::= {     sispm10403166lLLDPConfEntry 2 }

    sispm10403166lLLDPCDPAware OBJECT-TYPE
               SYNTAX      Integer32
               MAX-ACCESS  read-write
               STATUS      current
               DESCRIPTION
                   "0:Disable
		   1:Enable"
               ::= {     sispm10403166lLLDPConfEntry 3 }

    sispm10403166lLLDPTrap OBJECT-TYPE
               SYNTAX      Integer32
               MAX-ACCESS  read-write
               STATUS      current
               DESCRIPTION
               "0:Disable
		        1:Enable"
               ::= {     sispm10403166lLLDPConfEntry 4 }

    sispm10403166lLLDPPortDescr OBJECT-TYPE
               SYNTAX      Integer32
               MAX-ACCESS  read-write
               STATUS      current
               DESCRIPTION
                   "0:Disable
		   1:Enable"
               ::= {     sispm10403166lLLDPConfEntry 5 }

    sispm10403166lLLDPSysName OBJECT-TYPE
               SYNTAX      Integer32
               MAX-ACCESS  read-write
               STATUS      current
               DESCRIPTION
                   "0:Disable
		   1:Enable"
               ::= {     sispm10403166lLLDPConfEntry 6 }

    sispm10403166lLLDPSysDescr OBJECT-TYPE
               SYNTAX      Integer32
               MAX-ACCESS  read-write
               STATUS      current
               DESCRIPTION
                   "0:Disable
		   1:Enable"
               ::= {     sispm10403166lLLDPConfEntry 7 }

    sispm10403166lLLDPSysCapa OBJECT-TYPE
               SYNTAX      Integer32
               MAX-ACCESS  read-write
               STATUS      current
               DESCRIPTION
                   "0:Disable
		   1:Enable"
               ::= {     sispm10403166lLLDPConfEntry 8 }

    sispm10403166lLLDPMgmtAddr OBJECT-TYPE
               SYNTAX      Integer32
               MAX-ACCESS  read-write
               STATUS      current
               DESCRIPTION
                   "0:Disable
		   1:Enable"
               ::= {     sispm10403166lLLDPConfEntry 9 }

sispm10403166lLLDPMEDCoordinatesLocation                          OBJECT IDENTIFIER ::= { sispm10403166lLLDP 2 }

sispm10403166lLLDPMEDLatitude   OBJECT-TYPE
   SYNTAX      DisplayString
   MAX-ACCESS  read-write
   STATUS      current
   DESCRIPTION
	   "Latitude SHOULD be normalized to within 0-90 degrees with a maximum of 4 digits."
   ::= { sispm10403166lLLDPMEDCoordinatesLocation 2 }

sispm10403166lLLDPMEDLatitudeDirection OBJECT-TYPE
   SYNTAX      Integer32(0|1)
   MAX-ACCESS  read-write
   STATUS      current
   DESCRIPTION
       "0:North
	    1:South"
   ::= { sispm10403166lLLDPMEDCoordinatesLocation 3 }

sispm10403166lLLDPMEDLongitude   OBJECT-TYPE
   SYNTAX      DisplayString
   MAX-ACCESS  read-write
   STATUS      current
   DESCRIPTION
	   "Longitude SHOULD be normalized to within 0-180 degrees with a maximum of 4 digits."
   ::= { sispm10403166lLLDPMEDCoordinatesLocation 4 }

sispm10403166lLLDPMEDLongitudeDirection OBJECT-TYPE
   SYNTAX      Integer32(0|1)
   MAX-ACCESS  read-write
   STATUS      current
   DESCRIPTION
       "0:East
	    1:West"
   ::= { sispm10403166lLLDPMEDCoordinatesLocation 5 }

sispm10403166lLLDPMEDAltitude   OBJECT-TYPE
   SYNTAX      DisplayString
   MAX-ACCESS  read-write
   STATUS      current
   DESCRIPTION
	   "Altitude SHOULD be normalized to within -2097151.9 to 2097151.9 with a maximum of 1 digits."
   ::= { sispm10403166lLLDPMEDCoordinatesLocation 6 }

sispm10403166lLLDPMEDAltitudeType OBJECT-TYPE
   SYNTAX      Integer32(1|2)
   MAX-ACCESS  read-write
   STATUS      current
   DESCRIPTION
       "1:Meters
	    2:Floors"
   ::= { sispm10403166lLLDPMEDCoordinatesLocation 7 }

sispm10403166lLLDPMEDMapDatum OBJECT-TYPE
   SYNTAX      Integer32(0..2)
   MAX-ACCESS  read-write
   STATUS      current
   DESCRIPTION
       "The Map Datum is used for the coordinates given in these options:
	    1:WGS84
	    2:NAD83/NAVD88
	    3:NAD83/MLLW
		"
   ::= { sispm10403166lLLDPMEDCoordinatesLocation 8 }

sispm10403166lLLDPMEDCivicAddressLocation                          OBJECT IDENTIFIER ::= { sispm10403166lLLDP 4 }

sispm10403166lLLDPMEDCivicAddressLocationCountryCode   OBJECT-TYPE
   SYNTAX      DisplayString
   MAX-ACCESS  read-write
   STATUS      current
   DESCRIPTION
	   " "
   ::= { sispm10403166lLLDPMEDCivicAddressLocation 2 }

sispm10403166lLLDPMEDCivicAddressLocationStateProvince   OBJECT-TYPE
   SYNTAX      DisplayString
   MAX-ACCESS  read-write
   STATUS      current
   DESCRIPTION
	   " "
   ::= { sispm10403166lLLDPMEDCivicAddressLocation 3 }

sispm10403166lLLDPMEDCivicAddressLocationCounty   OBJECT-TYPE
   SYNTAX      DisplayString
   MAX-ACCESS  read-write
   STATUS      current
   DESCRIPTION
	   " "
   ::= { sispm10403166lLLDPMEDCivicAddressLocation 4 }

sispm10403166lLLDPMEDCivicAddressLocationCity   OBJECT-TYPE
   SYNTAX      DisplayString
   MAX-ACCESS  read-write
   STATUS      current
   DESCRIPTION
	   " "
   ::= { sispm10403166lLLDPMEDCivicAddressLocation 5 }

sispm10403166lLLDPMEDCivicAddressLocationCityDistrict   OBJECT-TYPE
   SYNTAX      DisplayString
   MAX-ACCESS  read-write
   STATUS      current
   DESCRIPTION
	   " "
   ::= { sispm10403166lLLDPMEDCivicAddressLocation 6 }

sispm10403166lLLDPMEDCivicAddressLocationBlockNeighborhood   OBJECT-TYPE
   SYNTAX      DisplayString
   MAX-ACCESS  read-write
   STATUS      current
   DESCRIPTION
	   " "
   ::= { sispm10403166lLLDPMEDCivicAddressLocation 7 }

sispm10403166lLLDPMEDCivicAddressLocationStreet   OBJECT-TYPE
   SYNTAX      DisplayString
   MAX-ACCESS  read-write
   STATUS      current
   DESCRIPTION
	   " "
   ::= { sispm10403166lLLDPMEDCivicAddressLocation 8 }

sispm10403166lLLDPMEDCivicAddressLocationLeadingStreetDirection   OBJECT-TYPE
   SYNTAX      DisplayString
   MAX-ACCESS  read-write
   STATUS      current
   DESCRIPTION
	   " "
   ::= { sispm10403166lLLDPMEDCivicAddressLocation 9 }

sispm10403166lLLDPMEDCivicAddressLocationTrailingStreetSuffix   OBJECT-TYPE
   SYNTAX      DisplayString
   MAX-ACCESS  read-write
   STATUS      current
   DESCRIPTION
	   " "
   ::= { sispm10403166lLLDPMEDCivicAddressLocation 10 }

sispm10403166lLLDPMEDCivicAddressLocationStreetSuffix   OBJECT-TYPE
   SYNTAX      DisplayString
   MAX-ACCESS  read-write
   STATUS      current
   DESCRIPTION
	   " "
   ::= { sispm10403166lLLDPMEDCivicAddressLocation 11 }

sispm10403166lLLDPMEDCivicAddressLocationHouseNo   OBJECT-TYPE
   SYNTAX      DisplayString
   MAX-ACCESS  read-write
   STATUS      current
   DESCRIPTION
	   " "
   ::= { sispm10403166lLLDPMEDCivicAddressLocation 12 }

sispm10403166lLLDPMEDCivicAddressLocationHouseNoSuffix   OBJECT-TYPE
   SYNTAX      DisplayString
   MAX-ACCESS  read-write
   STATUS      current
   DESCRIPTION
	   " "
   ::= { sispm10403166lLLDPMEDCivicAddressLocation 13 }

sispm10403166lLLDPMEDCivicAddressLocationLandmark   OBJECT-TYPE
   SYNTAX      DisplayString
   MAX-ACCESS  read-write
   STATUS      current
   DESCRIPTION
	   " "
   ::= { sispm10403166lLLDPMEDCivicAddressLocation 14 }

sispm10403166lLLDPMEDCivicAddressLocationAdditionalLocationInfo   OBJECT-TYPE
   SYNTAX      DisplayString
   MAX-ACCESS  read-write
   STATUS      current
   DESCRIPTION
	   " "
   ::= { sispm10403166lLLDPMEDCivicAddressLocation 15 }

sispm10403166lLLDPMEDCivicAddressLocationName   OBJECT-TYPE
   SYNTAX      DisplayString
   MAX-ACCESS  read-write
   STATUS      current
   DESCRIPTION
	   " "
   ::= { sispm10403166lLLDPMEDCivicAddressLocation 16 }

sispm10403166lLLDPMEDCivicAddressLocationZipCode   OBJECT-TYPE
   SYNTAX      DisplayString
   MAX-ACCESS  read-write
   STATUS      current
   DESCRIPTION
	   " "
   ::= { sispm10403166lLLDPMEDCivicAddressLocation 17 }

sispm10403166lLLDPMEDCivicAddressLocationBuilding   OBJECT-TYPE
   SYNTAX      DisplayString
   MAX-ACCESS  read-write
   STATUS      current
   DESCRIPTION
	   " "
   ::= { sispm10403166lLLDPMEDCivicAddressLocation 18 }

sispm10403166lLLDPMEDCivicAddressLocationApartment   OBJECT-TYPE
   SYNTAX      DisplayString
   MAX-ACCESS  read-write
   STATUS      current
   DESCRIPTION
	   " "
   ::= { sispm10403166lLLDPMEDCivicAddressLocation 19 }

sispm10403166lLLDPMEDCivicAddressLocationFloor   OBJECT-TYPE
   SYNTAX      DisplayString
   MAX-ACCESS  read-write
   STATUS      current
   DESCRIPTION
	   " "
   ::= { sispm10403166lLLDPMEDCivicAddressLocation 20 }

sispm10403166lLLDPMEDCivicAddressLocationRoomNo   OBJECT-TYPE
   SYNTAX      DisplayString
   MAX-ACCESS  read-write
   STATUS      current
   DESCRIPTION
	   " "
   ::= { sispm10403166lLLDPMEDCivicAddressLocation 21 }

sispm10403166lLLDPMEDCivicAddressLocationPlaceType   OBJECT-TYPE
   SYNTAX      DisplayString
   MAX-ACCESS  read-write
   STATUS      current
   DESCRIPTION
	   " "
   ::= { sispm10403166lLLDPMEDCivicAddressLocation 22 }

sispm10403166lLLDPMEDCivicAddressLocationPostalCommunityName   OBJECT-TYPE
   SYNTAX      DisplayString
   MAX-ACCESS  read-write
   STATUS      current
   DESCRIPTION
	   " "
   ::= { sispm10403166lLLDPMEDCivicAddressLocation 23 }

sispm10403166lLLDPMEDCivicAddressLocationPOBox   OBJECT-TYPE
   SYNTAX      DisplayString
   MAX-ACCESS  read-write
   STATUS      current
   DESCRIPTION
	   " "
   ::= { sispm10403166lLLDPMEDCivicAddressLocation 24 }

sispm10403166lLLDPMEDCivicAddressLocationAdditionalCode   OBJECT-TYPE
   SYNTAX      DisplayString
   MAX-ACCESS  read-write
   STATUS      current
   DESCRIPTION
	   " "
   ::= { sispm10403166lLLDPMEDCivicAddressLocation 25 }


sispm10403166lLLDPMEDPoliciesTable OBJECT-TYPE
   SYNTAX      SEQUENCE OF SISPM10403166LLLDPMEDPoliciesEntry
   MAX-ACCESS  not-accessible
   STATUS      current
   DESCRIPTION
       " "
   ::= { sispm10403166lLLDP 5 }

sispm10403166lLLDPMEDPoliciesEntry OBJECT-TYPE
   SYNTAX      SISPM10403166LLLDPMEDPoliciesEntry
   MAX-ACCESS  not-accessible
   STATUS      current
   DESCRIPTION
       " "
   INDEX    { sispm10403166lLLDPMEDPoliciesIndex  }
   ::= { sispm10403166lLLDPMEDPoliciesTable 1 }

SISPM10403166LLLDPMEDPoliciesEntry ::= SEQUENCE {
   sispm10403166lLLDPMEDPoliciesIndex            Integer32,
   sispm10403166lLLDPMEDPoliciesPolicyID         Integer32,
   sispm10403166lLLDPMEDPoliciesApplicationType  Integer32,
   sispm10403166lLLDPMEDPoliciesTag              Integer32,
   sispm10403166lLLDPMEDPoliciesVLANID           Integer32,
   sispm10403166lLLDPMEDPoliciesL2Priority       Integer32,
   sispm10403166lLLDPMEDPoliciesDSCP             Integer32,
   sispm10403166lLLDPMEDPoliciesRowStatus        RowStatus
}

sispm10403166lLLDPMEDPoliciesIndex OBJECT-TYPE
   SYNTAX      Integer32(1..65535)
   MAX-ACCESS  not-accessible
   STATUS      current
   DESCRIPTION
       "Index"
   ::= { sispm10403166lLLDPMEDPoliciesEntry 1 }

sispm10403166lLLDPMEDPoliciesPolicyID OBJECT-TYPE
   SYNTAX      Integer32
   MAX-ACCESS  read-only
   STATUS      current
   DESCRIPTION
       " "
   ::= { sispm10403166lLLDPMEDPoliciesEntry 2 }

sispm10403166lLLDPMEDPoliciesApplicationType OBJECT-TYPE
   SYNTAX      Integer32 (1..8)
   MAX-ACCESS  read-write
   STATUS      current
   DESCRIPTION
       "1:Voice
		2:Voice Signalling
		3:Guest Voice
		4:Guest Voice Signalling
		5:Softphone Voice
		6:Video Conferencing
		7:Streaming Video
		8:Video Signalling"
   ::= { sispm10403166lLLDPMEDPoliciesEntry 3 }

sispm10403166lLLDPMEDPoliciesTag OBJECT-TYPE
   SYNTAX      Integer32 (0|1)
   MAX-ACCESS  read-write
   STATUS      current
   DESCRIPTION
       "0:Untagged
	    1:Tagged"
   ::= { sispm10403166lLLDPMEDPoliciesEntry 4 }

sispm10403166lLLDPMEDPoliciesVLANID OBJECT-TYPE
   SYNTAX      Integer32 (1..4095)
   MAX-ACCESS  read-write
   STATUS      current
   DESCRIPTION
       "Range:1-4095"
   ::= { sispm10403166lLLDPMEDPoliciesEntry 5 }

sispm10403166lLLDPMEDPoliciesL2Priority OBJECT-TYPE
   SYNTAX      Integer32 (0..7)
   MAX-ACCESS  read-write
   STATUS      current
   DESCRIPTION
       "Range:0-7"
   ::= { sispm10403166lLLDPMEDPoliciesEntry 6 }

sispm10403166lLLDPMEDPoliciesDSCP OBJECT-TYPE
   SYNTAX      Integer32 (0..63)
   MAX-ACCESS  read-write
   STATUS      current
   DESCRIPTION
       "Range:0-63"
   ::= { sispm10403166lLLDPMEDPoliciesEntry 7 }

sispm10403166lLLDPMEDPoliciesRowStatus OBJECT-TYPE
   SYNTAX      RowStatus
   MAX-ACCESS  read-create
   STATUS      current
   DESCRIPTION
       "Row Status."
   ::= { sispm10403166lLLDPMEDPoliciesEntry 8 }

sispm10403166lLLDPMEDPolicyPortConfTable OBJECT-TYPE
   SYNTAX      SEQUENCE OF SISPM10403166LLLDPMEDPolicyPortConfEntry
   MAX-ACCESS  not-accessible
   STATUS      current
   DESCRIPTION
       " "
   ::= { sispm10403166lLLDP 6 }

sispm10403166lLLDPMEDPolicyPortConfEntry OBJECT-TYPE
   SYNTAX      SISPM10403166LLLDPMEDPolicyPortConfEntry
   MAX-ACCESS  not-accessible
   STATUS      current
   DESCRIPTION
       " "
   INDEX    { sispm10403166lLLDPMEDPolicyPortConfPort  }
   ::= { sispm10403166lLLDPMEDPolicyPortConfTable 1 }

SISPM10403166LLLDPMEDPolicyPortConfEntry ::= SEQUENCE {
   sispm10403166lLLDPMEDPolicyPortConfPort        Integer32,
   sispm10403166lLLDPMEDPolicyPortConf            Integer32
}

sispm10403166lLLDPMEDPolicyPortConfPort OBJECT-TYPE
   SYNTAX      Integer32(1..65535)
   MAX-ACCESS  not-accessible
   STATUS      current
   DESCRIPTION
       "Index"
   ::= { sispm10403166lLLDPMEDPolicyPortConfEntry 1 }

sispm10403166lLLDPMEDPolicyPortConf OBJECT-TYPE
   SYNTAX      Integer32 (0|1)
   MAX-ACCESS  read-write
   STATUS      current
   DESCRIPTION
       "0:Disable
	    1:Enable"
   ::= { sispm10403166lLLDPMEDPolicyPortConfEntry 2 }

sispm10403166lLLDPMEDFastStartRepeatCount OBJECT-TYPE
   SYNTAX      Integer32 (1..10)
   MAX-ACCESS  read-write
   STATUS      current
   DESCRIPTION
       "Range:1-10"
   ::= { sispm10403166lLLDP 7 }

sispm10403166lLLDPMEDEmergencyCallService OBJECT-TYPE
   SYNTAX      DisplayString
   MAX-ACCESS  read-write
   STATUS      current
   DESCRIPTION
       " "
   ::= { sispm10403166lLLDP 8 }

sispm10403166lUDLD    OBJECT IDENTIFIER ::= { sispm10403166lConfiguration 22 }

sispm10403166lUDLDPortConfigTable OBJECT-TYPE
   SYNTAX      SEQUENCE OF SISPM10403166LUDLDPortConfigEntry
   MAX-ACCESS  not-accessible
   STATUS      current
   DESCRIPTION
       " "
   ::= { sispm10403166lUDLD 1 }

sispm10403166lUDLDPortConfigEntry OBJECT-TYPE
   SYNTAX      SISPM10403166LUDLDPortConfigEntry
   MAX-ACCESS  not-accessible
   STATUS      current
   DESCRIPTION
       " "
   INDEX    { sispm10403166lUDLDPort  }
   ::= { sispm10403166lUDLDPortConfigTable 1 }

SISPM10403166LUDLDPortConfigEntry ::= SEQUENCE {
   sispm10403166lUDLDPort                       Integer32,
   sispm10403166lUDLDPortMode                   Integer32,
   sispm10403166lUDLDPortMessageInterval        Integer32
}

sispm10403166lUDLDPort OBJECT-TYPE
   SYNTAX      Integer32(1..65535)
   MAX-ACCESS  not-accessible
   STATUS      current
   DESCRIPTION
       " "
   ::= { sispm10403166lUDLDPortConfigEntry 1 }

sispm10403166lUDLDPortMode OBJECT-TYPE
   SYNTAX      Integer32 (0|1|2)
   MAX-ACCESS  read-write
   STATUS      current
   DESCRIPTION
       "default: 0
       0: disable
       1: Normal
	   2: Aggressive"
   ::= { sispm10403166lUDLDPortConfigEntry 2 }

sispm10403166lUDLDPortMessageInterval OBJECT-TYPE
   SYNTAX      Integer32(7..90)
   MAX-ACCESS  read-write
   STATUS      current
   DESCRIPTION
       "default: 7, range: 7-90"
   ::= { sispm10403166lUDLDPortConfigEntry 3 }


sispm10403166lUDLDPortStatusTable OBJECT-TYPE
   SYNTAX      SEQUENCE OF SISPM10403166LUDLDPortStatusEntry
   MAX-ACCESS  not-accessible
   STATUS      current
   DESCRIPTION
       " "
   ::= { sispm10403166lUDLD 2 }

sispm10403166lUDLDPortStatusEntry OBJECT-TYPE
   SYNTAX      SISPM10403166LUDLDPortStatusEntry
   MAX-ACCESS  not-accessible
   STATUS      current
   DESCRIPTION
       " "
   INDEX    { sispm10403166lUDLDPortStatusPort  }
   ::= { sispm10403166lUDLDPortStatusTable 1 }

SISPM10403166LUDLDPortStatusEntry ::= SEQUENCE {
   sispm10403166lUDLDPortStatusPort                   Integer32,
   sispm10403166lUDLDStatusAdminState                 Integer32,
   sispm10403166lUDLDStatusDeviceIDLocal          DisplayString,
   sispm10403166lUDLDStatusDeviceNameLocal        DisplayString,
   sispm10403166lUDLDStatusBidirectionalState     DisplayString
}

sispm10403166lUDLDPortStatusPort OBJECT-TYPE
   SYNTAX      Integer32(1..65535)
   MAX-ACCESS  not-accessible
   STATUS      current
   DESCRIPTION
       "Port index"
   ::= { sispm10403166lUDLDPortStatusEntry 1 }

sispm10403166lUDLDStatusAdminState OBJECT-TYPE
   SYNTAX      Integer32
   MAX-ACCESS  read-only
   STATUS      current
   DESCRIPTION
       "0:disable
	   1:enable"
   ::= { sispm10403166lUDLDPortStatusEntry 2 }

sispm10403166lUDLDStatusDeviceIDLocal OBJECT-TYPE
   SYNTAX      DisplayString
   MAX-ACCESS  read-only
   STATUS      current
   DESCRIPTION
       " "
   ::= { sispm10403166lUDLDPortStatusEntry 3 }

sispm10403166lUDLDStatusDeviceNameLocal OBJECT-TYPE
   SYNTAX      DisplayString
   MAX-ACCESS  read-only
   STATUS      current
   DESCRIPTION
       " "
   ::= { sispm10403166lUDLDPortStatusEntry 4 }

sispm10403166lUDLDStatusBidirectionalState OBJECT-TYPE
   SYNTAX      DisplayString
   MAX-ACCESS  read-only
   STATUS      current
   DESCRIPTION
       " "
   ::= { sispm10403166lUDLDPortStatusEntry 5 }


sispm10403166lUDLDStatusPort OBJECT-TYPE
   SYNTAX      Integer32
   MAX-ACCESS  read-write
   STATUS      current
   DESCRIPTION
       "Specify port number for check neighbour status"
   ::= { sispm10403166lUDLD 3 }

sispm10403166lUDLDPortNeighbourStatusTable OBJECT-TYPE
   SYNTAX      SEQUENCE OF SISPM10403166LUDLDPortNeighbourStatusEntry
   MAX-ACCESS  not-accessible
   STATUS      current
   DESCRIPTION
       " "
   ::= { sispm10403166lUDLD 4 }

sispm10403166lUDLDPortNeighbourStatusEntry OBJECT-TYPE
   SYNTAX      SISPM10403166LUDLDPortNeighbourStatusEntry
   MAX-ACCESS  not-accessible
   STATUS      current
   DESCRIPTION
       " "
   INDEX    { sispm10403166lUDLDNeighbourPort  }
   ::= { sispm10403166lUDLDPortNeighbourStatusTable 1 }

SISPM10403166LUDLDPortNeighbourStatusEntry ::= SEQUENCE {
   sispm10403166lUDLDNeighbourPort                 Integer32,
   sispm10403166lUDLDNeighbourStatusPort           DisplayString,
   sispm10403166lUDLDNeighbourStatusDeviceId       DisplayString,
   sispm10403166lUDLDNeighbourStatusLinkStatus     DisplayString,
   sispm10403166lUDLDNeighbourStatusDeviceName     DisplayString
}

sispm10403166lUDLDNeighbourPort OBJECT-TYPE
   SYNTAX      Integer32(1..65535)
   MAX-ACCESS  not-accessible
   STATUS      current
   DESCRIPTION
       "Index"
   ::= { sispm10403166lUDLDPortNeighbourStatusEntry 1 }

sispm10403166lUDLDNeighbourStatusPort OBJECT-TYPE
   SYNTAX      DisplayString
   MAX-ACCESS  read-only
   STATUS      current
   DESCRIPTION
       " "
   ::= { sispm10403166lUDLDPortNeighbourStatusEntry 2 }

sispm10403166lUDLDNeighbourStatusDeviceId OBJECT-TYPE
   SYNTAX      DisplayString
   MAX-ACCESS  read-only
   STATUS      current
   DESCRIPTION
       " "
   ::= { sispm10403166lUDLDPortNeighbourStatusEntry 3 }

sispm10403166lUDLDNeighbourStatusLinkStatus OBJECT-TYPE
   SYNTAX      DisplayString
   MAX-ACCESS  read-only
   STATUS      current
   DESCRIPTION
       " "
   ::= { sispm10403166lUDLDPortNeighbourStatusEntry 4 }

sispm10403166lUDLDNeighbourStatusDeviceName OBJECT-TYPE
   SYNTAX      DisplayString
   MAX-ACCESS  read-only
   STATUS      current
   DESCRIPTION
       " "
   ::= { sispm10403166lUDLDPortNeighbourStatusEntry 5 }
-- =======================================================================================================================
sispm10403166lEPS    OBJECT IDENTIFIER ::= { sispm10403166lConfiguration 23 }

sispm10403166lEPSTable  OBJECT-TYPE
   SYNTAX      SEQUENCE OF SISPM10403166LEPSEntry
   MAX-ACCESS  not-accessible
   STATUS      current
   DESCRIPTION
       "A table of EPS."
 ::= { sispm10403166lEPS 1 }

sispm10403166lEPSEntry OBJECT-TYPE
    SYNTAX        SISPM10403166LEPSEntry
    MAX-ACCESS    not-accessible
    STATUS        current
    DESCRIPTION
        ""
    INDEX        { sispm10403166lEPSIndex }
    ::= { sispm10403166lEPSTable 1 }

SISPM10403166LEPSEntry ::=
    SEQUENCE {
        sispm10403166lEPSIndex                                Integer32,
        sispm10403166lEpsID                                   Integer32,
		sispm10403166lEpsDomain                               Integer32,
        sispm10403166lEpsArchitecture                         Integer32,
        sispm10403166lEpsWFlow                                Integer32,
        sispm10403166lEpsPFlow                                Integer32,
        sispm10403166lEpsWSFMEP                               Integer32,
        sispm10403166lEpsPSFMEP                               Integer32,
        sispm10403166lEpsAPSMEP                               Integer32,
        sispm10403166lEpsAlarm                                Integer32,
        sispm10403166lEpsRowStatus                            RowStatus
    }

sispm10403166lEPSIndex OBJECT-TYPE
   SYNTAX      Integer32(1..65535)
   MAX-ACCESS  not-accessible
   STATUS      current
   DESCRIPTION
       "Index"
   ::= { sispm10403166lEPSEntry 1 }

sispm10403166lEpsID OBJECT-TYPE
   SYNTAX      Integer32 (1..100)
   MAX-ACCESS  read-create
   STATUS      current
   DESCRIPTION
       "EPS ID. Range:1-100."
   ::= {sispm10403166lEPSEntry 2 }

sispm10403166lEpsDomain OBJECT-TYPE
   SYNTAX      Integer32
   MAX-ACCESS  read-create
   STATUS      current
   DESCRIPTION
       "EPS Domain. Range:0.
	   0:Domain is Port"
   ::= {sispm10403166lEPSEntry 3 }

sispm10403166lEpsArchitecture OBJECT-TYPE
   SYNTAX      Integer32
   MAX-ACCESS  read-create
   STATUS      current
   DESCRIPTION
       "EPS Architecture. Range:0-1.
	   0:Architecture is 1+1
	   1:Architecture is 1:1"
   ::= {sispm10403166lEPSEntry 4 }

sispm10403166lEpsWFlow OBJECT-TYPE
   SYNTAX      Integer32
   MAX-ACCESS  read-create
   STATUS      current
   DESCRIPTION
       "The working flow for the EPS."
   ::= {sispm10403166lEPSEntry 5 }

sispm10403166lEpsPFlow OBJECT-TYPE
   SYNTAX      Integer32
   MAX-ACCESS  read-create
   STATUS      current
   DESCRIPTION
       "The protecting flow for the EPS"
   ::= {sispm10403166lEPSEntry 6 }

sispm10403166lEpsWSFMEP OBJECT-TYPE
   SYNTAX      Integer32
   MAX-ACCESS  read-create
   STATUS      current
   DESCRIPTION
       "The working Signal Fail reporting MEP."
   ::= {sispm10403166lEPSEntry 7 }

sispm10403166lEpsPSFMEP OBJECT-TYPE
   SYNTAX      Integer32
   MAX-ACCESS  read-create
   STATUS      current
   DESCRIPTION
       "The protecting Signal Fail reporting MEP."
   ::= {sispm10403166lEPSEntry 8 }

sispm10403166lEpsAPSMEP OBJECT-TYPE
   SYNTAX      Integer32
   MAX-ACCESS  read-create
   STATUS      current
   DESCRIPTION
       "The APS PDU handling MEP."
   ::= {sispm10403166lEPSEntry 9 }

sispm10403166lEpsAlarm OBJECT-TYPE
   SYNTAX      Integer32
   MAX-ACCESS  read-only
   STATUS      current
   DESCRIPTION
       "There is an active alarm on the EPS."
   ::= {sispm10403166lEPSEntry 10 }

sispm10403166lEpsRowStatus OBJECT-TYPE
   SYNTAX      RowStatus
   MAX-ACCESS  read-create
   STATUS      current
   DESCRIPTION
       "EPS Row Status."
   ::= {sispm10403166lEPSEntry 11 }

sispm10403166lEpsConfigInstanceEpsID   OBJECT-TYPE
   SYNTAX      Integer32
   MAX-ACCESS  read-write
   STATUS      current
   DESCRIPTION
	   "Specify EPS ID for table uesd."
   ::= {sispm10403166lEPS 2 }


sispm10403166lEPSConfigInstanceEntry    OBJECT IDENTIFIER ::= { sispm10403166lEPS 3 }

sispm10403166lEpsConfigInstanceProtectionType OBJECT-TYPE
   SYNTAX      Integer32
   MAX-ACCESS  read-write
   STATUS      current
   DESCRIPTION
       "Range:0-1.
	   0:Unidirectional: EPS in the two ends can select traffic from different working/protecting flow. This is only possible in case of 1+1.
       1:Bidirectional: EPS in the two ends is selecting traffic from the same working/protecting flow. This requires APS enabled. This is mandatory for 1:1"
   ::= { sispm10403166lEPSConfigInstanceEntry 2 }

sispm10403166lEpsConfigInstanceAPS OBJECT-TYPE
   SYNTAX      Integer32
   MAX-ACCESS  read-write
   STATUS      current
   DESCRIPTION
       "Range:0-1.
	    0:disable
	    1:enable
	    The Automatic Protection Switching protocol can be enabled/disabled. This is mandatory for 1:1."
   ::= { sispm10403166lEPSConfigInstanceEntry 3 }

sispm10403166lEpsConfigInstanceRevertive OBJECT-TYPE
   SYNTAX      Integer32
   MAX-ACCESS  read-write
   STATUS      current
   DESCRIPTION
       "Range:0-1.
	    0:disable
	    1:enable
		The revertive switching to working flow can be enabled/disabled.
		"
   ::= { sispm10403166lEPSConfigInstanceEntry 4 }

sispm10403166lEpsConfigInstanceWTRTime OBJECT-TYPE
   SYNTAX      Integer32
   MAX-ACCESS  read-write
   STATUS      current
   DESCRIPTION
       "The Wait To Restore timing value to be used in revertive switching. Range is 1 to 720 seconds.
		"
   ::= { sispm10403166lEPSConfigInstanceEntry 5 }

sispm10403166lEpsConfigInstanceHoldOffTime OBJECT-TYPE
   SYNTAX      Integer32
   MAX-ACCESS  read-write
   STATUS      current
   DESCRIPTION
       "The timing value to be used to make persistent check on Signal Fail before switching. This is in 100 ms. and the max value is 100 (10 sec)."
   ::= { sispm10403166lEPSConfigInstanceEntry 6 }

sispm10403166lEpsConfigInstanceCommand OBJECT-TYPE
   SYNTAX      Integer32
   MAX-ACCESS  read-write
   STATUS      current
   DESCRIPTION
       "0:None
	    1:Clear
		2:Lock Out
		3:Forced switch
		4:Manual switch P
		5:Manual switch W
		6:Exercise
		7:Freeze
		8:Lock Out Local
	   "
   ::= { sispm10403166lEPSConfigInstanceEntry 7 }

sispm10403166lEpsStatusProtectionState OBJECT-TYPE
   SYNTAX      DisplayString
   MAX-ACCESS  read-only
   STATUS      current
   DESCRIPTION
       "EPS state according to State Transition Tables in G.8031.
	   "
   ::= { sispm10403166lEPSConfigInstanceEntry 8 }

sispm10403166lEpsStatusWorkingFlowState OBJECT-TYPE
   SYNTAX      DisplayString
   MAX-ACCESS  read-only
   STATUS      current
   DESCRIPTION
       "OK: State of working flow is ok
        SF: State of working flow is Signal Fail
		SD: State of working flow is Signal Degrade (for future use)
	   "
   ::= { sispm10403166lEPSConfigInstanceEntry 9 }

sispm10403166lEpsStatusProtectingFlowState OBJECT-TYPE
   SYNTAX      DisplayString
   MAX-ACCESS  read-only
   STATUS      current
   DESCRIPTION
       "OK: State of protecting flow is ok
        SF: State of protecting flow is Signal Fail
        SD: State of protecting flow is Signal Degrade (for future use)
	   "
   ::= { sispm10403166lEPSConfigInstanceEntry 10 }

sispm10403166lEpsStatusTransmittedApsRequest OBJECT-TYPE
   SYNTAX      DisplayString
   MAX-ACCESS  read-only
   STATUS      current
   DESCRIPTION
       "The transmitted APS according to State Transition Tables in G.8031.
	   "
   ::= { sispm10403166lEPSConfigInstanceEntry 11 }

sispm10403166lEpsStatusTransmittedApsReSignal OBJECT-TYPE
   SYNTAX      Integer32
   MAX-ACCESS  read-only
   STATUS      current
   DESCRIPTION
       "The transmitted APS according to State Transition Tables in G.8031.
	   "
   ::= { sispm10403166lEPSConfigInstanceEntry 12 }

sispm10403166lEpsStatusTransmittedApsBrSignal OBJECT-TYPE
   SYNTAX      Integer32
   MAX-ACCESS  read-only
   STATUS      current
   DESCRIPTION
       "The transmitted APS according to State Transition Tables in G.8031.
	   "
   ::= { sispm10403166lEPSConfigInstanceEntry 13 }

sispm10403166lEpsStatusReceivedApsRequest OBJECT-TYPE
   SYNTAX      DisplayString
   MAX-ACCESS  read-only
   STATUS      current
   DESCRIPTION
       "The received APS according to State Transition Tables in G.8031.
	   "
   ::= { sispm10403166lEPSConfigInstanceEntry 14 }

sispm10403166lEpsStatusReceivedApsReSignal OBJECT-TYPE
   SYNTAX      Integer32
   MAX-ACCESS  read-only
   STATUS      current
   DESCRIPTION
       "The received APS according to State Transition Tables in G.8031.
	   "
   ::= { sispm10403166lEPSConfigInstanceEntry 15 }

sispm10403166lEpsStatusReceivedApsBrSignal OBJECT-TYPE
   SYNTAX      Integer32
   MAX-ACCESS  read-only
   STATUS      current
   DESCRIPTION
       "The received APS according to State Transition Tables in G.8031.
	   "
   ::= { sispm10403166lEPSConfigInstanceEntry 16 }

sispm10403166lEpsStatusArchitectureMismatch OBJECT-TYPE
   SYNTAX      DisplayString
   MAX-ACCESS  read-only
   STATUS      current
   DESCRIPTION
       "The architecture indicated in the received APS does not match the locally configured.
	   "
   ::= { sispm10403166lEPSConfigInstanceEntry 17 }

sispm10403166lEpsStatusAPSOnWorking OBJECT-TYPE
   SYNTAX      DisplayString
   MAX-ACCESS  read-only
   STATUS      current
   DESCRIPTION
       "APS is received on the working flow.
	   "
   ::= { sispm10403166lEPSConfigInstanceEntry 18 }

sispm10403166lEpsStatusSwitchingIncomplete OBJECT-TYPE
   SYNTAX      DisplayString
   MAX-ACCESS  read-only
   STATUS      current
   DESCRIPTION
       "Traffic is not selected from the same flow instance in the two ends.
	   "
   ::= { sispm10403166lEPSConfigInstanceEntry 19 }

sispm10403166lEpsStatusNoApsReceived OBJECT-TYPE
   SYNTAX      DisplayString
   MAX-ACCESS  read-only
   STATUS      current
   DESCRIPTION
       "APS PDU is not received from the other end.
	   "
   ::= { sispm10403166lEPSConfigInstanceEntry 20 }

-- =======================================================================================================================

sispm10403166lERPS    OBJECT IDENTIFIER ::= { sispm10403166lConfiguration 24 }

sispm10403166lERPSTable  OBJECT-TYPE
   SYNTAX      SEQUENCE OF SISPM10403166LERPSEntry
   MAX-ACCESS  not-accessible
   STATUS      current
   DESCRIPTION
       "A table of ERPS."
 ::= { sispm10403166lERPS 1 }

sispm10403166lERPSEntry OBJECT-TYPE
    SYNTAX        SISPM10403166LERPSEntry
    MAX-ACCESS    not-accessible
    STATUS        current
    DESCRIPTION
        ""
    INDEX        { sispm10403166lErpsIndex }
    ::= { sispm10403166lERPSTable 1 }

SISPM10403166LERPSEntry ::=
    SEQUENCE {
        sispm10403166lErpsIndex                                Integer32,
        sispm10403166lErpsID                                   Integer32,
		sispm10403166lErpsPort0                                Integer32,
		sispm10403166lErpsPort1                                Integer32,
		sispm10403166lErpsPort0APSMEP                          Integer32,
        sispm10403166lErpsPort1APSMEP                          Integer32,
        sispm10403166lErpsPort0SFMEP                           Integer32,
        sispm10403166lErpsPort1SFMEP                           Integer32,
        sispm10403166lErpsRingType                             Integer32,
        sispm10403166lErpsInterconnectedNode                   Integer32,
        sispm10403166lErpsVirtualChannel                       Integer32,
        sispm10403166lErpsMajorRingID                          Integer32,
        sispm10403166lErpsAlarm		                          Integer32,
        sispm10403166lErpsRowStatus                            RowStatus
    }

sispm10403166lErpsIndex OBJECT-TYPE
   SYNTAX      Integer32(1..65535)
   MAX-ACCESS  not-accessible
   STATUS      current
   DESCRIPTION
       "Index"
   ::= { sispm10403166lERPSEntry 1 }

sispm10403166lErpsID OBJECT-TYPE
   SYNTAX      Integer32 (1..64)
   MAX-ACCESS  read-create
   STATUS      current
   DESCRIPTION
       "ERPS ID. Range:1-64."
   ::= {sispm10403166lERPSEntry 2 }

sispm10403166lErpsPort0 OBJECT-TYPE
   SYNTAX      Integer32
   MAX-ACCESS  read-create
   STATUS      current
   DESCRIPTION
       "This will create a Port 0 of the switch in the ring."
   ::= {sispm10403166lERPSEntry 3 }

sispm10403166lErpsPort1 OBJECT-TYPE
   SYNTAX      Integer32
   MAX-ACCESS  read-create
   STATUS      current
   DESCRIPTION
       "This will create Port 1 of the switch in the Ring.
	   As interconnected sub-ring will have only one ring port, Port 1 is configured as 0 for interconnected sub-ring.
	   0 in this field indicates that no Port 1 is associated with this instance"
   ::= {sispm10403166lERPSEntry 4 }

sispm10403166lErpsPort0APSMEP OBJECT-TYPE
   SYNTAX      Integer32
   MAX-ACCESS  read-create
   STATUS      current
   DESCRIPTION
       "The Port 0 APS PDU handling MEP.
	   Range: 1-100."
   ::= {sispm10403166lERPSEntry 5 }

sispm10403166lErpsPort1APSMEP OBJECT-TYPE
   SYNTAX      Integer32
   MAX-ACCESS  read-create
   STATUS      current
   DESCRIPTION
       "The Port 1 APS PDU handling MEP.
	   Range: 1-100."
   ::= {sispm10403166lERPSEntry 6 }

sispm10403166lErpsPort0SFMEP OBJECT-TYPE
   SYNTAX      Integer32
   MAX-ACCESS  read-create
   STATUS      current
   DESCRIPTION
       "The Port 0 Signal Fail reporting MEP.
	   Range: 1-100."
   ::= {sispm10403166lERPSEntry 7 }

 sispm10403166lErpsPort1SFMEP OBJECT-TYPE
   SYNTAX      Integer32
   MAX-ACCESS  read-create
   STATUS      current
   DESCRIPTION
       "The Port 1 Signal Fail reporting MEP.
	   Range: 1-100."
   ::= {sispm10403166lERPSEntry 8 }

sispm10403166lErpsRingType OBJECT-TYPE
   SYNTAX      Integer32
   MAX-ACCESS  read-create
   STATUS      current
   DESCRIPTION
       "Type of Protecting ring. It can be either major ring or sub-ring.
	   0:Major
	   1:Sub"
   ::= {sispm10403166lERPSEntry 9 }

sispm10403166lErpsInterconnectedNode OBJECT-TYPE
   SYNTAX      Integer32
   MAX-ACCESS  read-create
   STATUS      current
   DESCRIPTION
       "Interconnected Node indicates that the ring instance is interconnected.
	   0: not interconnected
	   1: interconnected"
   ::= {sispm10403166lERPSEntry 10 }

sispm10403166lErpsVirtualChannel OBJECT-TYPE
   SYNTAX      Integer32
   MAX-ACCESS  read-create
   STATUS      current
   DESCRIPTION
       "1: indicates it is a sub-ring with virtual channel.
	    0: indicates, sub-ring doesn't have virtual channel."
   ::= {sispm10403166lERPSEntry 11 }

sispm10403166lErpsMajorRingID OBJECT-TYPE
   SYNTAX      Integer32
   MAX-ACCESS  read-create
   STATUS      current
   DESCRIPTION
       "Major ring group ID for the interconnected sub-ring.
	   Range:1-64"
   ::= {sispm10403166lERPSEntry 12 }

sispm10403166lErpsAlarm OBJECT-TYPE
   SYNTAX      Integer32
   MAX-ACCESS  read-create
   STATUS      current
   DESCRIPTION
       "There is an active alarm on the ERPS."
   ::= {sispm10403166lERPSEntry 13 }

sispm10403166lErpsRowStatus OBJECT-TYPE
   SYNTAX      RowStatus
   MAX-ACCESS  read-create
   STATUS      current
   DESCRIPTION
       "ERPS Row Status."
   ::= {sispm10403166lERPSEntry 14 }


sispm10403166lErpsConfigInstanceErpsID   OBJECT-TYPE
   SYNTAX      Integer32
   MAX-ACCESS  read-write
   STATUS      current
   DESCRIPTION
	   "Specify ERPS ID for ERPSConfigInstanceEntry and ErpsConfigInstanceVLANConfigTable uesd."
   ::= {sispm10403166lERPS 2 }


sispm10403166lERPSConfigInstanceEntry    OBJECT IDENTIFIER ::= { sispm10403166lERPS 3 }

sispm10403166lErpsConfigInstanceConfigured OBJECT-TYPE
   SYNTAX      DisplayString
   MAX-ACCESS  read-only
   STATUS      current
   DESCRIPTION
       "Down: This ERPS is only created and has not yet been configured - is not active.
        Up: This ERPS is configured - is active."
   ::= { sispm10403166lERPSConfigInstanceEntry 2 }

sispm10403166lErpsConfigInstanceGuardTime OBJECT-TYPE
   SYNTAX      Integer32
   MAX-ACCESS  read-write
   STATUS      current
   DESCRIPTION
       "The period of the guard timer can be configured in 10 ms steps between 10 ms and 2 seconds, with a default value of 500 ms.
	    Guard timeout value to be used to prevent ring nodes from receiving outdated R-APS messages."
   ::= { sispm10403166lERPSConfigInstanceEntry 3 }

sispm10403166lErpsConfigInstanceWTRTime OBJECT-TYPE
   SYNTAX      Integer32
   MAX-ACCESS  read-write
   STATUS      current
   DESCRIPTION
       "The Wait To Restore timing value to be used in revertive switching.
        The period of the WTR time can be configured by the operator in 1 minute steps between 5 and 12 minutes with a default value of 5 minutes.
		"
   ::= { sispm10403166lERPSConfigInstanceEntry 4 }

sispm10403166lErpsConfigInstanceHoldOffTime OBJECT-TYPE
   SYNTAX      Integer32
   MAX-ACCESS  read-write
   STATUS      current
   DESCRIPTION
       "The timing value to be used to make persistent check on Signal Fail before switching.
        The range of the hold off timer is 0 to 10 seconds in steps of 100 ms
		"
   ::= { sispm10403166lERPSConfigInstanceEntry 5 }

sispm10403166lErpsConfigInstanceVersion OBJECT-TYPE
   SYNTAX      Integer32
   MAX-ACCESS  read-write
   STATUS      current
   DESCRIPTION
       "ERPS Protocol Version - v1 or v2
	   1:v1
	   2:v2"
   ::= { sispm10403166lERPSConfigInstanceEntry 6 }

sispm10403166lErpsConfigInstanceRevertive OBJECT-TYPE
   SYNTAX      Integer32
   MAX-ACCESS  read-write
   STATUS      current
   DESCRIPTION
       "1:Revertive mode
	    0:Non-Revertive mode"
   ::= { sispm10403166lERPSConfigInstanceEntry 7 }

sispm10403166lErpsConfigInstanceRPLRole OBJECT-TYPE
   SYNTAX      Integer32
   MAX-ACCESS  read-write
   STATUS      current
   DESCRIPTION
       "It can be either RPL owner or RPL Neighbor.
	   0:None
	   1:RPL owner
	   2:RPL Neighbor
	   Please set RPLPort first.
	   "
   ::= { sispm10403166lERPSConfigInstanceEntry 8 }

sispm10403166lErpsConfigInstanceRPLPort OBJECT-TYPE
   SYNTAX      Integer32
   MAX-ACCESS  read-write
   STATUS      current
   DESCRIPTION
       "This allows to select the east port or west port as the RPL block.
	   0:None
	   1:Port0
	   2:Port1
	   Please set RPLRole after specify RPLPort.
	   "
   ::= { sispm10403166lERPSConfigInstanceEntry 9 }

sispm10403166lErpsConfigInstanceClear OBJECT-TYPE
   SYNTAX      Integer32
   MAX-ACCESS  read-write
   STATUS      current
   DESCRIPTION
       "If the owner has to be changed, then the clear check box allows to clear the RPL owner for that ERPS ring.
	   0: no clear
	   1: clear
	   "
   ::= { sispm10403166lERPSConfigInstanceEntry 10 }

sispm10403166lErpsConfigInstanceTopologyChange OBJECT-TYPE
   SYNTAX      Integer32
   MAX-ACCESS  read-write
   STATUS      current
   DESCRIPTION
       "1: indicates that the topology changes in the sub-ring are propagated in the major ring.
	    0: indicates that the topology changes in the sub-ring are not propagated in the major ring.
	   "
   ::= { sispm10403166lERPSConfigInstanceEntry 11 }

sispm10403166lErpsConfigInstanceCommand OBJECT-TYPE
   SYNTAX      Integer32
   MAX-ACCESS  read-write
   STATUS      current
   DESCRIPTION
       "0:None
	    1:Manual Switch
		2:Forced Switch
		3:Clear
		Please set InstancePort first.
	   "
   ::= { sispm10403166lERPSConfigInstanceEntry 12 }

sispm10403166lErpsConfigInstancePort OBJECT-TYPE
   SYNTAX      Integer32
   MAX-ACCESS  read-write
   STATUS      current
   DESCRIPTION
       "0:None
	   1:Port0
	   2:Port1
	   Please set InstanceCommand after specify InstancePort.
	   "
   ::= { sispm10403166lERPSConfigInstanceEntry 13 }

sispm10403166lErpsStatusProtectionState OBJECT-TYPE
   SYNTAX      DisplayString
   MAX-ACCESS  read-only
   STATUS      current
   DESCRIPTION
       "ERPS state according to State Transition Tables in G.8032.
	   "
   ::= { sispm10403166lERPSConfigInstanceEntry 14 }

sispm10403166lErpsStatusPort0 OBJECT-TYPE
   SYNTAX      DisplayString
   MAX-ACCESS  read-only
   STATUS      current
   DESCRIPTION
       "OK: State of East port is ok
        SF: State of East port is Signal Fail
	   "
   ::= { sispm10403166lERPSConfigInstanceEntry 15 }

sispm10403166lErpsStatusPort1 OBJECT-TYPE
   SYNTAX      DisplayString
   MAX-ACCESS  read-only
   STATUS      current
   DESCRIPTION
       "OK: State of West port is ok
        SF: State of West port is Signal Fail
	   "
   ::= { sispm10403166lERPSConfigInstanceEntry 16 }

sispm10403166lErpsStatusTransmitAPS OBJECT-TYPE
   SYNTAX      DisplayString
   MAX-ACCESS  read-only
   STATUS      current
   DESCRIPTION
       "The transmitted APS according to State Transition Tables in G.8032.
	   "
   ::= { sispm10403166lERPSConfigInstanceEntry 17 }

sispm10403166lErpsStatusPort0ReceiveAPS OBJECT-TYPE
   SYNTAX      DisplayString
   MAX-ACCESS  read-only
   STATUS      current
   DESCRIPTION
       "The received APS on Port 0 according to State Transition Tables in G.8032.
	   "
   ::= { sispm10403166lERPSConfigInstanceEntry 18 }

sispm10403166lErpsStatusPort1ReceiveAPS OBJECT-TYPE
   SYNTAX      DisplayString
   MAX-ACCESS  read-only
   STATUS      current
   DESCRIPTION
       "The received APS on Port 1 according to State Transition Tables in G.8032.
	   "
   ::= { sispm10403166lERPSConfigInstanceEntry 19 }

sispm10403166lErpsStatusWTRRemaining OBJECT-TYPE
   SYNTAX      Integer32
   MAX-ACCESS  read-only
   STATUS      current
   DESCRIPTION
       "Remaining WTR timeout in milliseconds.
	   "
   ::= { sispm10403166lERPSConfigInstanceEntry 20 }

sispm10403166lErpsStatusRPLUnblocked OBJECT-TYPE
   SYNTAX      DisplayString
   MAX-ACCESS  read-only
   STATUS      current
   DESCRIPTION
       "APS is received on the working flow.
	   "
   ::= { sispm10403166lERPSConfigInstanceEntry 21 }

sispm10403166lErpsStatusNoAPSReceived OBJECT-TYPE
   SYNTAX      DisplayString
   MAX-ACCESS  read-only
   STATUS      current
   DESCRIPTION
       "RAPS PDU is not received from the other end.
	   "
   ::= { sispm10403166lERPSConfigInstanceEntry 22 }

sispm10403166lErpsStatusPort0BlockStatus OBJECT-TYPE
   SYNTAX      DisplayString
   MAX-ACCESS  read-only
   STATUS      current
   DESCRIPTION
       "Block status for Port 0 (Both traffic and R-APS block status). R-APS channel is never blocked on sub-rings without virtual channel.
	   "
   ::= { sispm10403166lERPSConfigInstanceEntry 23 }

sispm10403166lErpsStatusPort1BlockStatus OBJECT-TYPE
   SYNTAX      DisplayString
   MAX-ACCESS  read-only
   STATUS      current
   DESCRIPTION
       "Block status for Port 1 (Both traffic and R-APS block status). R-APS channel is never blocked on sub-rings without virtual channel.
	   "
   ::= { sispm10403166lERPSConfigInstanceEntry 24 }

sispm10403166lErpsStatusFOPAlarm OBJECT-TYPE
   SYNTAX      DisplayString
   MAX-ACCESS  read-only
   STATUS      current
   DESCRIPTION
       "Failure of Protocol Defect(FOP) status:
	   FOP is not detected
	   FOP is detected
	   "
   ::= { sispm10403166lERPSConfigInstanceEntry 25 }

sispm10403166lErpsConfigInstanceVLANConfigTable  OBJECT-TYPE
   SYNTAX      SEQUENCE OF SISPM10403166LErpsConfigInstanceVLANConfigEntry
   MAX-ACCESS  not-accessible
   STATUS      current
   DESCRIPTION
       "A table of ERPS VLANConfig."
 ::= { sispm10403166lERPS 4 }

sispm10403166lErpsConfigInstanceVLANConfigEntry OBJECT-TYPE
    SYNTAX        SISPM10403166LErpsConfigInstanceVLANConfigEntry
    MAX-ACCESS    not-accessible
    STATUS        current
    DESCRIPTION
        ""
    INDEX        { sispm10403166lErpsConfigInstanceVLANConfigIndex }
    ::= { sispm10403166lErpsConfigInstanceVLANConfigTable 1 }

SISPM10403166LErpsConfigInstanceVLANConfigEntry ::=
    SEQUENCE {
        sispm10403166lErpsConfigInstanceVLANConfigIndex            Integer32,
        sispm10403166lErpsConfigInstanceVLANConfigVLANID           Integer32,
        sispm10403166lErpsConfigInstanceVLANConfigRowStatus        RowStatus
    }

sispm10403166lErpsConfigInstanceVLANConfigIndex OBJECT-TYPE
   SYNTAX      Integer32(1..65535)
   MAX-ACCESS  not-accessible
   STATUS      current
   DESCRIPTION
       "Index"
   ::= { sispm10403166lErpsConfigInstanceVLANConfigEntry 1 }

sispm10403166lErpsConfigInstanceVLANConfigVLANID OBJECT-TYPE
   SYNTAX      Integer32 (1..4095)
   MAX-ACCESS  read-create
   STATUS      current
   DESCRIPTION
       "ERPS VLAN Config ID. Range:1-4095."
   ::= {sispm10403166lErpsConfigInstanceVLANConfigEntry 2 }

sispm10403166lErpsConfigInstanceVLANConfigRowStatus OBJECT-TYPE
   SYNTAX      RowStatus
   MAX-ACCESS  read-create
   STATUS      current
   DESCRIPTION
       "ERPS VLAN Config Row Status."
   ::= {sispm10403166lErpsConfigInstanceVLANConfigEntry 3 }
-- =======================================================================================================================

sispm10403166lVLANTranslation    OBJECT IDENTIFIER ::= { sispm10403166lConfiguration 25 }

sispm10403166lVLANTranslationPortTable  OBJECT-TYPE
   SYNTAX      SEQUENCE OF SISPM10403166LVLANTranslationPortEntry
   MAX-ACCESS  not-accessible
   STATUS      current
   DESCRIPTION
       "A table of VLANTranslationPort."
 ::= { sispm10403166lVLANTranslation 1 }

sispm10403166lVLANTranslationPortEntry OBJECT-TYPE
    SYNTAX        SISPM10403166LVLANTranslationPortEntry
    MAX-ACCESS    not-accessible
    STATUS        current
    DESCRIPTION
        "An entry in the VLANTranslationPort table."
    INDEX        { sispm10403166lVLANTranslationPortIndex }
    ::= { sispm10403166lVLANTranslationPortTable 1 }

SISPM10403166LVLANTranslationPortEntry ::=
    SEQUENCE {
        sispm10403166lVLANTranslationPortIndex                Integer32,
        sispm10403166lVLANTranslationPortDefault              Integer32,
        sispm10403166lVLANTranslationPortGroupID              Integer32
    }

sispm10403166lVLANTranslationPortIndex OBJECT-TYPE
   SYNTAX      Integer32(1..65535)
   MAX-ACCESS  not-accessible
   STATUS      current
   DESCRIPTION
       "VLANTranslationPort index."
   ::= {sispm10403166lVLANTranslationPortEntry 1 }

sispm10403166lVLANTranslationPortDefault OBJECT-TYPE
   SYNTAX      Integer32
   MAX-ACCESS  read-write
   STATUS      current
   DESCRIPTION
       "Set the switch port to use the default VLAN Translation Group.
	   1:set
	   0:not set"
   ::= {sispm10403166lVLANTranslationPortEntry 2 }

sispm10403166lVLANTranslationPortGroupID OBJECT-TYPE
   SYNTAX      Integer32
   MAX-ACCESS  read-write
   STATUS      current
   DESCRIPTION
       "The VLAN Translation mappings are organized into Groups, identified by the Group ID."
   ::= {sispm10403166lVLANTranslationPortEntry 3 }



sispm10403166lVLANTranslationMappingTable  OBJECT-TYPE
   SYNTAX      SEQUENCE OF SISPM10403166LVLANTranslationMappingEntry
   MAX-ACCESS  not-accessible
   STATUS      current
   DESCRIPTION
       "A table of VLANTranslationMapping."
 ::= { sispm10403166lVLANTranslation 2 }

sispm10403166lVLANTranslationMappingEntry OBJECT-TYPE
    SYNTAX        SISPM10403166LVLANTranslationMappingEntry
    MAX-ACCESS    not-accessible
    STATUS        current
    DESCRIPTION
        "An entry in the VLANTranslationMapping table."
    INDEX        { sispm10403166lVLANTranslationMappingIndex }
    ::= { sispm10403166lVLANTranslationMappingTable 1 }

SISPM10403166LVLANTranslationMappingEntry ::=
    SEQUENCE {
        sispm10403166lVLANTranslationMappingIndex                Integer32,
        sispm10403166lVLANTranslationMappingGroupID              Integer32,
        sispm10403166lVLANTranslationMappingVID                  Integer32,
		sispm10403166lVLANTranslationMappingTVID                 Integer32,
		sispm10403166lVLANTranslationMappingRowStatus            RowStatus
    }

sispm10403166lVLANTranslationMappingIndex OBJECT-TYPE
   SYNTAX      Integer32(1..65535)
   MAX-ACCESS  not-accessible
   STATUS      current
   DESCRIPTION
       "VLANTranslationMapping index."
   ::= {sispm10403166lVLANTranslationMappingEntry 1 }

sispm10403166lVLANTranslationMappingGroupID OBJECT-TYPE
   SYNTAX      Integer32
   MAX-ACCESS  read-create
   STATUS      current
   DESCRIPTION
       "The VLAN Translation mappings are organized into Groups, identified by the Group ID."
   ::= {sispm10403166lVLANTranslationMappingEntry 2 }

sispm10403166lVLANTranslationMappingVID OBJECT-TYPE
   SYNTAX      Integer32
   MAX-ACCESS  read-create
   STATUS      current
   DESCRIPTION
       "Range:1-4095"
   ::= {sispm10403166lVLANTranslationMappingEntry 3 }

sispm10403166lVLANTranslationMappingTVID OBJECT-TYPE
   SYNTAX      Integer32
   MAX-ACCESS  read-create
   STATUS      current
   DESCRIPTION
       "Range:1-4095"
   ::= {sispm10403166lVLANTranslationMappingEntry 4 }

sispm10403166lVLANTranslationMappingRowStatus OBJECT-TYPE
   SYNTAX      RowStatus
   MAX-ACCESS  read-create
   STATUS      current
   DESCRIPTION
       "VLANTranslationMapping Row Status."
   ::= {sispm10403166lVLANTranslationMappingEntry 5 }
-- ========================================================================================================
sispm10403166lMEP    OBJECT IDENTIFIER ::= { sispm10403166lConfiguration 26 }

sispm10403166lMEPTable  OBJECT-TYPE
   SYNTAX      SEQUENCE OF SISPM10403166LMEPEntry
   MAX-ACCESS  not-accessible
   STATUS      current
   DESCRIPTION
       "A table of MEP."
 ::= { sispm10403166lMEP 1 }

sispm10403166lMEPEntry OBJECT-TYPE
    SYNTAX        SISPM10403166LMEPEntry
    MAX-ACCESS    not-accessible
    STATUS        current
    DESCRIPTION
        "An entry in the MEP table."
    INDEX        { sispm10403166lMEPIndex }
    ::= { sispm10403166lMEPTable 1 }

SISPM10403166LMEPEntry ::=
    SEQUENCE {
        sispm10403166lMEPIndex                         Integer32,
        sispm10403166lMepInstance                      Integer32,
        sispm10403166lMepDomain                        Integer32,
        sispm10403166lMepMode                          Integer32,
		sispm10403166lMepDirection                     Integer32,
		sispm10403166lMepResidencePort                 Integer32,
		sispm10403166lMepLevel                         Integer32,
		sispm10403166lMepFlowInstance                  Integer32,
		sispm10403166lMepTaggedVID                     Integer32,
		sispm10403166lMepEPSInstance                   DisplayString,
		sispm10403166lMepThisMAC                       DisplayString,
		sispm10403166lMepAlarm                         DisplayString,
        sispm10403166lMepRowStatus                     RowStatus
    }

sispm10403166lMEPIndex OBJECT-TYPE
   SYNTAX      Integer32(1..65535)
   MAX-ACCESS  not-accessible
   STATUS      current
   DESCRIPTION
       "MEP Table index."
   ::= {sispm10403166lMEPEntry 1 }

sispm10403166lMepInstance OBJECT-TYPE
   SYNTAX      Integer32
   MAX-ACCESS  read-create
   STATUS      current
   DESCRIPTION
       ""
   ::= {sispm10403166lMEPEntry 2 }

sispm10403166lMepDomain OBJECT-TYPE
   SYNTAX      Integer32
   MAX-ACCESS  read-create
   STATUS      current
   DESCRIPTION
       ""
   ::= {sispm10403166lMEPEntry 3 }

sispm10403166lMepMode OBJECT-TYPE
   SYNTAX      Integer32
   MAX-ACCESS  read-create
   STATUS      current
   DESCRIPTION
       ""
   ::= {sispm10403166lMEPEntry 4 }

sispm10403166lMepDirection OBJECT-TYPE
   SYNTAX      Integer32
   MAX-ACCESS  read-create
   STATUS      current
   DESCRIPTION
       ""
   ::= {sispm10403166lMEPEntry 5 }

sispm10403166lMepResidencePort OBJECT-TYPE
   SYNTAX      Integer32
   MAX-ACCESS  read-create
   STATUS      current
   DESCRIPTION
       ""
   ::= {sispm10403166lMEPEntry 6 }

sispm10403166lMepLevel OBJECT-TYPE
   SYNTAX      Integer32
   MAX-ACCESS  read-create
   STATUS      current
   DESCRIPTION
       ""
   ::= {sispm10403166lMEPEntry 7 }

sispm10403166lMepFlowInstance OBJECT-TYPE
   SYNTAX      Integer32
   MAX-ACCESS  read-create
   STATUS      current
   DESCRIPTION
       ""
   ::= {sispm10403166lMEPEntry 8 }

sispm10403166lMepTaggedVID OBJECT-TYPE
   SYNTAX      Integer32
   MAX-ACCESS  read-create
   STATUS      current
   DESCRIPTION
       ""
   ::= {sispm10403166lMEPEntry 9 }

sispm10403166lMepEPSInstance OBJECT-TYPE
   SYNTAX      DisplayString
   MAX-ACCESS  read-only
   STATUS      current
   DESCRIPTION
       ""
   ::= {sispm10403166lMEPEntry 10 }

sispm10403166lMepThisMAC OBJECT-TYPE
   SYNTAX      DisplayString
   MAX-ACCESS  read-only
   STATUS      current
   DESCRIPTION
       ""
   ::= {sispm10403166lMEPEntry 11 }

sispm10403166lMepAlarm OBJECT-TYPE
   SYNTAX      DisplayString
   MAX-ACCESS  read-only
   STATUS      current
   DESCRIPTION
       ""
   ::= {sispm10403166lMEPEntry 12 }

sispm10403166lMepRowStatus OBJECT-TYPE
   SYNTAX      RowStatus
   MAX-ACCESS  read-create
   STATUS      current
   DESCRIPTION
       "MEP Row Status."
   ::= {sispm10403166lMEPEntry 13 }

sispm10403166lMepInstanceID   OBJECT-TYPE
   SYNTAX      Integer32
   MAX-ACCESS  read-write
   STATUS      current
   DESCRIPTION
	   "Specify MEP Instance ID for the following item and table uesd."
   ::= {sispm10403166lMEP 2 }


sispm10403166lMepInstanceConfEntry    OBJECT IDENTIFIER ::= { sispm10403166lMEP 3 }

sispm10403166lMepInstanceConfLevel OBJECT-TYPE
   SYNTAX      Integer32
   MAX-ACCESS  read-write
   STATUS      current
   DESCRIPTION
       ""
   ::= {sispm10403166lMepInstanceConfEntry 2 }

sispm10403166lMepInstanceConfFormat OBJECT-TYPE
   SYNTAX      Integer32
   MAX-ACCESS  read-write
   STATUS      current
   DESCRIPTION
       ""
   ::= {sispm10403166lMepInstanceConfEntry 3 }

sispm10403166lMepInstanceConfDomainName OBJECT-TYPE
   SYNTAX      DisplayString
   MAX-ACCESS  read-write
   STATUS      current
   DESCRIPTION
       ""
   ::= {sispm10403166lMepInstanceConfEntry 4 }

sispm10403166lMepInstanceConfMEGid OBJECT-TYPE
   SYNTAX      DisplayString
   MAX-ACCESS  read-write
   STATUS      current
   DESCRIPTION
       ""
   ::= {sispm10403166lMepInstanceConfEntry 5 }

sispm10403166lMepInstanceConfMEPid OBJECT-TYPE
   SYNTAX      Integer32
   MAX-ACCESS  read-write
   STATUS      current
   DESCRIPTION
       ""
   ::= {sispm10403166lMepInstanceConfEntry 6 }

sispm10403166lMepInstanceConfTaggedVID OBJECT-TYPE
   SYNTAX      Integer32
   MAX-ACCESS  read-write
   STATUS      current
   DESCRIPTION
       ""
   ::= {sispm10403166lMepInstanceConfEntry 7 }

sispm10403166lMepInstanceConfSyslog OBJECT-TYPE
   SYNTAX      Integer32
   MAX-ACCESS  read-write
   STATUS      current
   DESCRIPTION
       ""
   ::= {sispm10403166lMepInstanceConfEntry 8 }

sispm10403166lMepInstanceConfcLevel OBJECT-TYPE
   SYNTAX      DisplayString
   MAX-ACCESS  read-only
   STATUS      current
   DESCRIPTION
       ""
   ::= {sispm10403166lMepInstanceConfEntry 9 }

sispm10403166lMepInstanceConfcMEG OBJECT-TYPE
   SYNTAX      DisplayString
   MAX-ACCESS  read-only
   STATUS      current
   DESCRIPTION
       ""
   ::= {sispm10403166lMepInstanceConfEntry 10 }

sispm10403166lMepInstanceConfcMEP OBJECT-TYPE
   SYNTAX      DisplayString
   MAX-ACCESS  read-only
   STATUS      current
   DESCRIPTION
       ""
   ::= {sispm10403166lMepInstanceConfEntry 11 }

sispm10403166lMepInstanceConfcAIS OBJECT-TYPE
   SYNTAX      DisplayString
   MAX-ACCESS  read-only
   STATUS      current
   DESCRIPTION
       ""
   ::= {sispm10403166lMepInstanceConfEntry 12 }

sispm10403166lMepInstanceConfcLCK OBJECT-TYPE
   SYNTAX      DisplayString
   MAX-ACCESS  read-only
   STATUS      current
   DESCRIPTION
       ""
   ::= {sispm10403166lMepInstanceConfEntry 13 }

sispm10403166lMepInstanceConfcLoop OBJECT-TYPE
   SYNTAX      DisplayString
   MAX-ACCESS  read-only
   STATUS      current
   DESCRIPTION
       ""
   ::= {sispm10403166lMepInstanceConfEntry 14 }

sispm10403166lMepInstanceConfcConfig OBJECT-TYPE
   SYNTAX      DisplayString
   MAX-ACCESS  read-only
   STATUS      current
   DESCRIPTION
       ""
   ::= {sispm10403166lMepInstanceConfEntry 15 }

sispm10403166lMepInstanceConfcDEG OBJECT-TYPE
   SYNTAX      DisplayString
   MAX-ACCESS  read-only
   STATUS      current
   DESCRIPTION
       ""
   ::= {sispm10403166lMepInstanceConfEntry 16 }

sispm10403166lMepInstanceConfcSSF OBJECT-TYPE
   SYNTAX      DisplayString
   MAX-ACCESS  read-only
   STATUS      current
   DESCRIPTION
       ""
   ::= {sispm10403166lMepInstanceConfEntry 17 }

sispm10403166lMepInstanceConfaBLK OBJECT-TYPE
   SYNTAX      DisplayString
   MAX-ACCESS  read-only
   STATUS      current
   DESCRIPTION
       ""
   ::= {sispm10403166lMepInstanceConfEntry 18 }

sispm10403166lMepInstanceConfaTSD OBJECT-TYPE
   SYNTAX      DisplayString
   MAX-ACCESS  read-only
   STATUS      current
   DESCRIPTION
       ""
   ::= {sispm10403166lMepInstanceConfEntry 19 }

sispm10403166lMepInstanceConfaTSF OBJECT-TYPE
   SYNTAX      DisplayString
   MAX-ACCESS  read-only
   STATUS      current
   DESCRIPTION
       ""
   ::= {sispm10403166lMepInstanceConfEntry 20 }


sispm10403166lPeerMepConfTable  OBJECT-TYPE
   SYNTAX      SEQUENCE OF SISPM10403166LPeerMepConfEntry
   MAX-ACCESS  not-accessible
   STATUS      current
   DESCRIPTION
       "A table of MEP."
 ::= { sispm10403166lMEP 4 }

sispm10403166lPeerMepConfEntry OBJECT-TYPE
    SYNTAX        SISPM10403166LPeerMepConfEntry
    MAX-ACCESS    not-accessible
    STATUS        current
    DESCRIPTION
        ""
    INDEX        { sispm10403166lPeerMepConfIndex }
    ::= { sispm10403166lPeerMepConfTable 1 }

SISPM10403166LPeerMepConfEntry ::=
    SEQUENCE {
        sispm10403166lPeerMepConfIndex                       Integer32,
        sispm10403166lPeerMepConfPeerMEPID                   Integer32,
		sispm10403166lPeerMepConfUnicastPeerMAC              DisplayString,
        sispm10403166lPeerMepConfcLOC                        DisplayString,
        sispm10403166lPeerMepConfcRDI                        DisplayString,
        sispm10403166lPeerMepConfcPeriod                     DisplayString,
        sispm10403166lPeerMepConfcPriority                   DisplayString,
        sispm10403166lPeerMepConfRowStatus                   RowStatus
    }

sispm10403166lPeerMepConfIndex OBJECT-TYPE
   SYNTAX      Integer32(1..65535)
   MAX-ACCESS  not-accessible
   STATUS      current
   DESCRIPTION
       "Index"
   ::= { sispm10403166lPeerMepConfEntry 1 }

sispm10403166lPeerMepConfPeerMEPID OBJECT-TYPE
   SYNTAX      Integer32
   MAX-ACCESS  read-create
   STATUS      current
   DESCRIPTION
       "Peer MEP ID"
   ::= {sispm10403166lPeerMepConfEntry 2 }

sispm10403166lPeerMepConfUnicastPeerMAC OBJECT-TYPE
   SYNTAX      DisplayString
   MAX-ACCESS  read-create
   STATUS      current
   DESCRIPTION
       ""
   ::= {sispm10403166lPeerMepConfEntry 3 }

sispm10403166lPeerMepConfcLOC OBJECT-TYPE
   SYNTAX      DisplayString
   MAX-ACCESS  read-create
   STATUS      current
   DESCRIPTION
       ""
   ::= {sispm10403166lPeerMepConfEntry 4 }

sispm10403166lPeerMepConfcRDI OBJECT-TYPE
   SYNTAX      DisplayString
   MAX-ACCESS  read-create
   STATUS      current
   DESCRIPTION
       ""
   ::= {sispm10403166lPeerMepConfEntry 5 }

sispm10403166lPeerMepConfcPeriod OBJECT-TYPE
   SYNTAX      DisplayString
   MAX-ACCESS  read-create
   STATUS      current
   DESCRIPTION
       ""
   ::= {sispm10403166lPeerMepConfEntry 6 }

sispm10403166lPeerMepConfcPriority OBJECT-TYPE
   SYNTAX      DisplayString
   MAX-ACCESS  read-create
   STATUS      current
   DESCRIPTION
       ""
   ::= {sispm10403166lPeerMepConfEntry 7 }

sispm10403166lPeerMepConfRowStatus OBJECT-TYPE
   SYNTAX      RowStatus
   MAX-ACCESS  read-create
   STATUS      current
   DESCRIPTION
       "Peer Mep Conf Row Status."
   ::= {sispm10403166lPeerMepConfEntry 8 }

sispm10403166lFunctionalConf    OBJECT IDENTIFIER ::= { sispm10403166lMEP 5 }

sispm10403166lFunctionalConfContinuityCheckEnable OBJECT-TYPE
   SYNTAX      Integer32
   MAX-ACCESS  read-write
   STATUS      current
   DESCRIPTION
       "0:disable
	   1:enable"
   ::= {sispm10403166lFunctionalConf 2 }

sispm10403166lFunctionalConfContinuityCheckPriority OBJECT-TYPE
   SYNTAX      Integer32
   MAX-ACCESS  read-write
   STATUS      current
   DESCRIPTION
       "range:0-7"
   ::= {sispm10403166lFunctionalConf 3 }

sispm10403166lFunctionalConfContinuityCheckFrameRate OBJECT-TYPE
   SYNTAX      Integer32
   MAX-ACCESS  read-write
   STATUS      current
   DESCRIPTION
       "range:1-7
	   1: 300 f/sec
	   2: 100 f/sec
	   3: 10 f/sec
	   4: 1 f/sec
	   5: 6 f/min
	   6: 1 f/min
	   7: 6 f/hour"
   ::= {sispm10403166lFunctionalConf 4 }

sispm10403166lFunctionalConfContinuityCheckTLV OBJECT-TYPE
   SYNTAX      Integer32
   MAX-ACCESS  read-write
   STATUS      current
   DESCRIPTION
       "0:disable
	   1:enable"
   ::= {sispm10403166lFunctionalConf 5 }

sispm10403166lFunctionalConfAPSProtocolEnable OBJECT-TYPE
   SYNTAX      Integer32
   MAX-ACCESS  read-write
   STATUS      current
   DESCRIPTION
       "0:disable
	   1:enable"
   ::= {sispm10403166lFunctionalConf 6 }

sispm10403166lFunctionalConfAPSProtocolPriority OBJECT-TYPE
   SYNTAX      Integer32
   MAX-ACCESS  read-write
   STATUS      current
   DESCRIPTION
       "range:0-7"
   ::= {sispm10403166lFunctionalConf 7 }

sispm10403166lFunctionalConfAPSProtocolCast OBJECT-TYPE
   SYNTAX      Integer32
   MAX-ACCESS  read-write
   STATUS      current
   DESCRIPTION
       "0: Unicast destination address
	   1: Multicast destination address"
   ::= {sispm10403166lFunctionalConf 8 }

sispm10403166lFunctionalConfAPSProtocolType OBJECT-TYPE
   SYNTAX      Integer32
   MAX-ACCESS  read-write
   STATUS      current
   DESCRIPTION
       "1: Linear protection APS
	   2: Ring protection APS"
   ::= {sispm10403166lFunctionalConf 9 }

sispm10403166lFunctionalConfAPSProtocolLastOctet OBJECT-TYPE
   SYNTAX      Integer32
   MAX-ACCESS  read-write
   STATUS      current
   DESCRIPTION
       "range:0-255"
   ::= {sispm10403166lFunctionalConf 10 }

sispm10403166lTLVConf    OBJECT IDENTIFIER ::= { sispm10403166lMEP 6 }

sispm10403166lTLVConfOUIFirst OBJECT-TYPE
   SYNTAX      Integer32
   MAX-ACCESS  read-write
   STATUS      current
   DESCRIPTION
       "range:0-255"
   ::= {sispm10403166lTLVConf 2 }

sispm10403166lTLVConfOUISecond OBJECT-TYPE
   SYNTAX      Integer32
   MAX-ACCESS  read-write
   STATUS      current
   DESCRIPTION
       "range:0-255"
   ::= {sispm10403166lTLVConf 3 }

sispm10403166lTLVConfOUIThird OBJECT-TYPE
   SYNTAX      Integer32
   MAX-ACCESS  read-write
   STATUS      current
   DESCRIPTION
       "range:0-255"
   ::= {sispm10403166lTLVConf 4 }

sispm10403166lTLVConfSubType OBJECT-TYPE
   SYNTAX      Integer32
   MAX-ACCESS  read-write
   STATUS      current
   DESCRIPTION
       "range:0-255"
   ::= {sispm10403166lTLVConf 5 }

sispm10403166lTLVConfValue OBJECT-TYPE
   SYNTAX      Integer32
   MAX-ACCESS  read-write
   STATUS      current
   DESCRIPTION
       "range:0-255"
   ::= {sispm10403166lTLVConf 6 }


sispm10403166lTLVConfStateTable OBJECT-TYPE
   SYNTAX      SEQUENCE OF SISPM10403166LTLVConfStateEntry
   MAX-ACCESS  not-accessible
   STATUS      current
   DESCRIPTION
       "TLV Conf State Table"
   ::= { sispm10403166lMEP 7 }

sispm10403166lTLVConfStateEntry OBJECT-TYPE
   SYNTAX      SISPM10403166LTLVConfStateEntry
   MAX-ACCESS  not-accessible
   STATUS      current
   DESCRIPTION
       "TLV Conf State Entry"
   INDEX    { sispm10403166lTLVConfStateIndex  }
   ::= { sispm10403166lTLVConfStateTable 1 }

SISPM10403166LTLVConfStateEntry ::= SEQUENCE {
   sispm10403166lTLVConfStateIndex                                Integer32,
   sispm10403166lTLVConfStatePeerMEPID                            Integer32,
   sispm10403166lTLVConfStateCCOrganizationSpecificOUIFirst       Integer32,
   sispm10403166lTLVConfStateCCOrganizationSpecificOUISecond      Integer32,
   sispm10403166lTLVConfStateCCOrganizationSpecificOUIThird       Integer32,
   sispm10403166lTLVConfStateCCOrganizationSpecificSubType        Integer32,
   sispm10403166lTLVConfStateCCOrganizationSpecificValue          Integer32,
   sispm10403166lTLVConfStateCCOrganizationSpecificLastRX         DisplayString,
   sispm10403166lTLVConfStateCCPortStatusValue                    Integer32,
   sispm10403166lTLVConfStateCCPortStatusLastRX                   DisplayString,
   sispm10403166lTLVConfStateCCInterfaceStatusValue               Integer32,
   sispm10403166lTLVConfStateCCInterfaceStatusLastRX              DisplayString
}

sispm10403166lTLVConfStateIndex OBJECT-TYPE
   SYNTAX      Integer32(1..65535)
   MAX-ACCESS  not-accessible
   STATUS      current
   DESCRIPTION
       "Index"
   ::= { sispm10403166lTLVConfStateEntry 1 }

sispm10403166lTLVConfStatePeerMEPID OBJECT-TYPE
   SYNTAX      Integer32
   MAX-ACCESS  read-only
   STATUS      current
   DESCRIPTION
       "Peer MEP ID"
   ::= { sispm10403166lTLVConfStateEntry 2 }

sispm10403166lTLVConfStateCCOrganizationSpecificOUIFirst OBJECT-TYPE
   SYNTAX      Integer32
   MAX-ACCESS  read-only
   STATUS      current
   DESCRIPTION
       "The last received first value in the OUI field."
   ::= { sispm10403166lTLVConfStateEntry 3 }

sispm10403166lTLVConfStateCCOrganizationSpecificOUISecond OBJECT-TYPE
   SYNTAX      Integer32
   MAX-ACCESS  read-only
   STATUS      current
   DESCRIPTION
       "The last received second value in the OS TLV OUI field."
   ::= { sispm10403166lTLVConfStateEntry 4 }

sispm10403166lTLVConfStateCCOrganizationSpecificOUIThird OBJECT-TYPE
   SYNTAX      Integer32
   MAX-ACCESS  read-only
   STATUS      current
   DESCRIPTION
       "The last received third value in the OS TLV OUI field."
   ::= { sispm10403166lTLVConfStateEntry 5 }

sispm10403166lTLVConfStateCCOrganizationSpecificSubType OBJECT-TYPE
   SYNTAX      Integer32
   MAX-ACCESS  read-only
   STATUS      current
   DESCRIPTION
       "The last received value in the OS TLV Sub-Type field."
   ::= { sispm10403166lTLVConfStateEntry 6 }

sispm10403166lTLVConfStateCCOrganizationSpecificValue OBJECT-TYPE
   SYNTAX      Integer32
   MAX-ACCESS  read-only
   STATUS      current
   DESCRIPTION
       "The last received value in the OS TLV Value field."
   ::= { sispm10403166lTLVConfStateEntry 7 }

sispm10403166lTLVConfStateCCOrganizationSpecificLastRX OBJECT-TYPE
   SYNTAX      DisplayString
   MAX-ACCESS  read-only
   STATUS      current
   DESCRIPTION
       "OS TLV was received in the last received CCM PDU."
   ::= { sispm10403166lTLVConfStateEntry 8 }

sispm10403166lTLVConfStateCCPortStatusValue OBJECT-TYPE
   SYNTAX      Integer32
   MAX-ACCESS  read-only
   STATUS      current
   DESCRIPTION
       "The last received value in the PS TLV Value field."
   ::= { sispm10403166lTLVConfStateEntry 9 }

sispm10403166lTLVConfStateCCPortStatusLastRX OBJECT-TYPE
   SYNTAX      DisplayString
   MAX-ACCESS  read-only
   STATUS      current
   DESCRIPTION
       "PS TLV was received in the last received CCM PDU."
   ::= { sispm10403166lTLVConfStateEntry 10 }

sispm10403166lTLVConfStateCCInterfaceStatusValue OBJECT-TYPE
   SYNTAX      Integer32
   MAX-ACCESS  read-only
   STATUS      current
   DESCRIPTION
       "The last received value in the IS TLV Value field."
   ::= { sispm10403166lTLVConfStateEntry 11 }

sispm10403166lTLVConfStateCCInterfaceStatusLastRX OBJECT-TYPE
   SYNTAX      DisplayString
   MAX-ACCESS  read-only
   STATUS      current
   DESCRIPTION
       "IS TLV was received in the last received CCM PDU."
   ::= { sispm10403166lTLVConfStateEntry 12 }

sispm10403166lLinkStateTracking OBJECT-TYPE
   SYNTAX      Integer32
   MAX-ACCESS  read-write
   STATUS      current
   DESCRIPTION
       "0:disable
	   1:enable"
   ::= { sispm10403166lMEP 8 }


sispm10403166lFaultManagement    OBJECT IDENTIFIER ::= { sispm10403166lMEP 9 }

sispm10403166lFaultMgmtLoopBackConfEnable OBJECT-TYPE
   SYNTAX      Integer32
   MAX-ACCESS  read-write
   STATUS      current
   DESCRIPTION
       "0:disable
	   1:enable"
   ::= { sispm10403166lFaultManagement 2 }

sispm10403166lFaultMgmtLoopBackConfDEI OBJECT-TYPE
   SYNTAX      Integer32
   MAX-ACCESS  read-write
   STATUS      current
   DESCRIPTION
       "0:disable
	   1:enable"
   ::= { sispm10403166lFaultManagement 3 }

sispm10403166lFaultMgmtLoopBackConfPriority OBJECT-TYPE
   SYNTAX      Integer32
   MAX-ACCESS  read-write
   STATUS      current
   DESCRIPTION
       "range:0-7"
   ::= { sispm10403166lFaultManagement 4 }

sispm10403166lFaultMgmtLoopBackConfCast OBJECT-TYPE
   SYNTAX      Integer32
   MAX-ACCESS  read-write
   STATUS      current
   DESCRIPTION
       "0:Unicast destination address
	   1:Multicast destination address"
   ::= { sispm10403166lFaultManagement 5 }

sispm10403166lFaultMgmtLoopBackConfPeerMEP OBJECT-TYPE
   SYNTAX      Integer32
   MAX-ACCESS  read-write
   STATUS      current
   DESCRIPTION
       "This is only used if the 'Unicast MAC' is configured to all zero.
	   The LBM unicast MAC will be taken from the 'Unicast Peer MAC' configuration of this peer."
   ::= { sispm10403166lFaultManagement 6 }

sispm10403166lFaultMgmtLoopBackConfUnicastMAC OBJECT-TYPE
   SYNTAX      DisplayString
   MAX-ACCESS  read-write
   STATUS      current
   DESCRIPTION
       "This is only used if NOT configured to all zero.
	   This will be used as the LBM PDU unicast MAC.
	   This is the only way to configure Loop Back to-wards a MIP. "
   ::= { sispm10403166lFaultManagement 7 }

sispm10403166lFaultMgmtLoopBackConfToSend OBJECT-TYPE
   SYNTAX      Integer32
   MAX-ACCESS  read-write
   STATUS      current
   DESCRIPTION
       "The number of LBM PDU to send in one loop test.
	   The value 0 indicate infinite transmission (test behaviour).
	   This is HW based LBM/LBR and Requires VOE."
   ::= { sispm10403166lFaultManagement 8 }

sispm10403166lFaultMgmtLoopBackConfSize OBJECT-TYPE
   SYNTAX      Integer32
   MAX-ACCESS  read-write
   STATUS      current
   DESCRIPTION
       "The LBM frame size."
   ::= { sispm10403166lFaultManagement 9 }

sispm10403166lFaultMgmtLoopBackConfInterval OBJECT-TYPE
   SYNTAX      Integer32
   MAX-ACCESS  read-write
   STATUS      current
   DESCRIPTION
       "The interval between transmitting LBM PDU."
   ::= { sispm10403166lFaultManagement 10 }


sispm10403166lFaultManagementState    OBJECT IDENTIFIER ::= { sispm10403166lMEP 10 }


sispm10403166lFaultMgmtStateTransactionID OBJECT-TYPE
   SYNTAX      Integer32
   MAX-ACCESS  read-only
   STATUS      current
   DESCRIPTION
       "The transaction id of the first LBM transmitted.
	   For each LBM transmitted the transaction id in the PDU is incremented."
   ::= { sispm10403166lFaultManagementState 1 }


sispm10403166lFaultMgmtStateTransmitted OBJECT-TYPE
   SYNTAX      Integer32
   MAX-ACCESS  read-only
   STATUS      current
   DESCRIPTION
       "The total number of LBM PDU transmitted."
   ::= { sispm10403166lFaultManagementState 2 }


sispm10403166lFaultMgmtStateTable OBJECT-TYPE
   SYNTAX      SEQUENCE OF SISPM10403166LFaultMgmtStateEntry
   MAX-ACCESS  not-accessible
   STATUS      current
   DESCRIPTION
       " "
   ::= { sispm10403166lFaultManagementState 3 }

sispm10403166lFaultMgmtStateEntry OBJECT-TYPE
   SYNTAX      SISPM10403166LFaultMgmtStateEntry
   MAX-ACCESS  not-accessible
   STATUS      current
   DESCRIPTION
       " "
   INDEX    { sispm10403166lFaultMgmtStateIndex  }
   ::= { sispm10403166lFaultMgmtStateTable 1 }

SISPM10403166LFaultMgmtStateEntry ::= SEQUENCE {
   sispm10403166lFaultMgmtStateIndex               Integer32,
   sispm10403166lFaultMgmtStateReplyMAC            DisplayString,
   sispm10403166lFaultMgmtStateReceived            Integer32,
   sispm10403166lFaultMgmtStateOutOfOrder          Integer32
}

sispm10403166lFaultMgmtStateIndex OBJECT-TYPE
   SYNTAX      Integer32(1..65535)
   MAX-ACCESS  not-accessible
   STATUS      current
   DESCRIPTION
       "Index"
   ::= { sispm10403166lFaultMgmtStateEntry 1 }

sispm10403166lFaultMgmtStateReplyMAC OBJECT-TYPE
   SYNTAX      DisplayString
   MAX-ACCESS  read-only
   STATUS      current
   DESCRIPTION
       "The MAC of the replying MEP/MIP.
	   In case of multi-cast LBM, replies can be received from all peer MEP in the group.
	   This MAC is not shown in case of 'To Send' == 0."
   ::= { sispm10403166lFaultMgmtStateEntry 2 }

sispm10403166lFaultMgmtStateReceived OBJECT-TYPE
   SYNTAX      Integer32
   MAX-ACCESS  read-only
   STATUS      current
   DESCRIPTION
       "The total number of LBR PDU received from this 'Reply MAC'."
   ::= { sispm10403166lFaultMgmtStateEntry 3 }

sispm10403166lFaultMgmtStateOutOfOrder OBJECT-TYPE
   SYNTAX      Integer32
   MAX-ACCESS  read-only
   STATUS      current
   DESCRIPTION
       "The number of LBR PDU received from this 'Reply MAC' with incorrect 'Transaction ID'."
   ::= { sispm10403166lFaultMgmtStateEntry 4 }

sispm10403166lFaultMgmtTestSignal    OBJECT IDENTIFIER ::= { sispm10403166lMEP 11 }

sispm10403166lFaultMgmtTestSignalTx OBJECT-TYPE
   SYNTAX      Integer32
   MAX-ACCESS  read-write
   STATUS      current
   DESCRIPTION
       "Test Signal based on transmitting TST PDU can be enabled/disabled.
	   0:disable
	   1:enable"
   ::= { sispm10403166lFaultMgmtTestSignal 2 }

sispm10403166lFaultMgmtTestSignalRx OBJECT-TYPE
   SYNTAX      Integer32
   MAX-ACCESS  read-write
   STATUS      current
   DESCRIPTION
       "Test Signal based on transmitting TST PDU can be enabled/disabled.
	   0:disable
	   1:enable"
   ::= { sispm10403166lFaultMgmtTestSignal 3 }

sispm10403166lFaultMgmtTestSignalDEI OBJECT-TYPE
   SYNTAX      Integer32
   MAX-ACCESS  read-write
   STATUS      current
   DESCRIPTION
       "The DEI to be inserted as PCP bits in TAG (if any).
	   0:disable
	   1:enable"
   ::= { sispm10403166lFaultMgmtTestSignal 4 }

sispm10403166lFaultMgmtTestSignalPriority OBJECT-TYPE
   SYNTAX      Integer32
   MAX-ACCESS  read-write
   STATUS      current
   DESCRIPTION
       "The priority to be inserted as PCP bits in TAG (if any).
       Range:0-7"
   ::= { sispm10403166lFaultMgmtTestSignal 5 }

sispm10403166lFaultMgmtTestSignalPeerMEP OBJECT-TYPE
   SYNTAX      Integer32
   MAX-ACCESS  read-write
   STATUS      current
   DESCRIPTION
       "The TST frame destination MAC will be taken from the 'Unicast Peer MAC' configuration of this peer."
   ::= { sispm10403166lFaultMgmtTestSignal 6 }

sispm10403166lFaultMgmtTestSignalRate OBJECT-TYPE
   SYNTAX      Integer32
   MAX-ACCESS  read-write
   STATUS      current
   DESCRIPTION
       "The TST frame transmission bit rate - in Mega bits pr. second.
	   Limit is 400 Mbps. This is the bit rate of a standard frame without any encapsulation.
	   If 1 Mbps rate is selected in a EVC MEP, the added tag will give a higher bitrate on the wire."
   ::= { sispm10403166lFaultMgmtTestSignal 7 }

sispm10403166lFaultMgmtTestSignalSize OBJECT-TYPE
   SYNTAX      Integer32
   MAX-ACCESS  read-write
   STATUS      current
   DESCRIPTION
       "The TST frame size. This is entered as the wanted size (in bytes) of a un-tagged frame containing TST OAM PDU - including CRC (four bytes)."
   ::= { sispm10403166lFaultMgmtTestSignal 8 }

sispm10403166lFaultMgmtTestSignalPattern OBJECT-TYPE
   SYNTAX      Integer32
   MAX-ACCESS  read-write
   STATUS      current
   DESCRIPTION
       "The 'empty' TST PDU has the size of 12 bytes.
	   In order to achieve the configured frame size a data TLV will be added with a pattern.
	   0:All Zero
	   1:All One
	   2:10101010"
   ::= { sispm10403166lFaultMgmtTestSignal 9 }

sispm10403166lFaultMgmtTestSignalSequenceNumber OBJECT-TYPE
   SYNTAX      Integer32
   MAX-ACCESS  read-write
   STATUS      current
   DESCRIPTION
       "0:disable
	   1:enable"
   ::= { sispm10403166lFaultMgmtTestSignal 10 }

sispm10403166lFaultMgmtTestSignalState    OBJECT IDENTIFIER ::= { sispm10403166lMEP 12 }

sispm10403166lFaultMgmtTestSignalStateTXFrameCount OBJECT-TYPE
   SYNTAX      Integer32
   MAX-ACCESS  read-only
   STATUS      current
   DESCRIPTION
       "The number of transmitted TST frames since last 'Clear'."
   ::= { sispm10403166lFaultMgmtTestSignalState 2 }

sispm10403166lFaultMgmtTestSignalStateRXFrameCount OBJECT-TYPE
   SYNTAX      Integer32
   MAX-ACCESS  read-only
   STATUS      current
   DESCRIPTION
       "The number of received TST frames since last 'Clear'."
   ::= { sispm10403166lFaultMgmtTestSignalState 3 }

sispm10403166lFaultMgmtTestSignalStateRXRate OBJECT-TYPE
   SYNTAX      Integer32
   MAX-ACCESS  read-only
   STATUS      current
   DESCRIPTION
       "The current received TST frame bit rate in Kbps.
	   This is calculated on a 1 s. basis, starting when first TST frame is received after 'Clear'.
	   The frame size used for this calculation is the first received after 'Clear'"
   ::= { sispm10403166lFaultMgmtTestSignalState 4 }

sispm10403166lFaultMgmtTestSignalStateTestTime OBJECT-TYPE
   SYNTAX      Integer32
   MAX-ACCESS  read-only
   STATUS      current
   DESCRIPTION
       "The number of seconds passed since first TST frame received after last 'Clear'."
   ::= { sispm10403166lFaultMgmtTestSignalState 5 }


sispm10403166lFaultMgmtTestSignalStateClear OBJECT-TYPE
   SYNTAX      Integer32
   MAX-ACCESS  read-write
   STATUS      current
   DESCRIPTION
       "This will clear all Test Signal State.
	   Transmission of TST frame will be restarted.
	   Calculation of 'Rx frame count', 'RX rate' and 'Test time' will be started when receiving first TST frame."
   ::= { sispm10403166lFaultMgmtTestSignalState 6 }


sispm10403166lFaultMgmtClientConfigFlow    OBJECT IDENTIFIER ::= { sispm10403166lMEP 13 }

sispm10403166lFaultMgmtClientConfigFlowTable OBJECT-TYPE
   SYNTAX      SEQUENCE OF SISPM10403166LFaultMgmtClientConfigFlowEntry
   MAX-ACCESS  not-accessible
   STATUS      current
   DESCRIPTION
       " "
   ::= { sispm10403166lFaultMgmtClientConfigFlow 1 }

sispm10403166lFaultMgmtClientConfigFlowEntry OBJECT-TYPE
   SYNTAX      SISPM10403166LFaultMgmtClientConfigFlowEntry
   MAX-ACCESS  not-accessible
   STATUS      current
   DESCRIPTION
       " "
   INDEX    { sispm10403166lFaultMgmtClientConfigFlowIndex  }
   ::= { sispm10403166lFaultMgmtClientConfigFlowTable 1 }

SISPM10403166LFaultMgmtClientConfigFlowEntry ::= SEQUENCE {
   sispm10403166lFaultMgmtClientConfigFlowIndex     Integer32,
   sispm10403166lFaultMgmtClientConfigFlowDomain    Integer32,
   sispm10403166lFaultMgmtClientConfigFlowInstance  Integer32,
   sispm10403166lFaultMgmtClientConfigFlowLevel     Integer32,
   sispm10403166lFaultMgmtClientConfigFlowAISprio   Integer32,
   sispm10403166lFaultMgmtClientConfigFlowLCKprio   Integer32,
   sispm10403166lFaultMgmtClientConfigFlowRowStatus RowStatus
}

sispm10403166lFaultMgmtClientConfigFlowIndex OBJECT-TYPE
   SYNTAX      Integer32(1..65535)
   MAX-ACCESS  not-accessible
   STATUS      current
   DESCRIPTION
       "Index"
   ::= { sispm10403166lFaultMgmtClientConfigFlowEntry 1 }

sispm10403166lFaultMgmtClientConfigFlowDomain OBJECT-TYPE
   SYNTAX      Integer32
   MAX-ACCESS  read-create
   STATUS      current
   DESCRIPTION
       "The domain of the client layer flow.
	   Ranfew:0-6
	   0:Port
	   1:EVC
	   2:VLAN
	   3:MPLS_LINK
	   4:MPLS_TUNNEL
	   5:MPLS_PW
	   6:MPLS_LSP"
   ::= { sispm10403166lFaultMgmtClientConfigFlowEntry 2 }

sispm10403166lFaultMgmtClientConfigFlowInstance OBJECT-TYPE
   SYNTAX      Integer32
   MAX-ACCESS  read-create
   STATUS      current
   DESCRIPTION
       "Client layer flow instance numbers."
   ::= { sispm10403166lFaultMgmtClientConfigFlowEntry 3 }

sispm10403166lFaultMgmtClientConfigFlowLevel OBJECT-TYPE
   SYNTAX      Integer32
   MAX-ACCESS  read-create
   STATUS      current
   DESCRIPTION
       "Client layer level - AIS and LCK PDU transmitted in this client layer flow will be on this level."
   ::= { sispm10403166lFaultMgmtClientConfigFlowEntry 4 }

sispm10403166lFaultMgmtClientConfigFlowAISprio OBJECT-TYPE
   SYNTAX      Integer32
   MAX-ACCESS  read-create
   STATUS      current
   DESCRIPTION
       "The priority to be used when transmitting AIS in each client flow.
	   Priority resulting in highest possible PCP can be selected.
	   Range:0-7. 255 indicate highest possible is requested"
   ::= { sispm10403166lFaultMgmtClientConfigFlowEntry 5 }

sispm10403166lFaultMgmtClientConfigFlowLCKprio OBJECT-TYPE
   SYNTAX      Integer32
   MAX-ACCESS  read-create
   STATUS      current
   DESCRIPTION
       "The priority to be used when transmitting LCK in each client flow.
	   Priority resulting in highest possible PCP can be selected.
	   Range:0-7. 255 indicate highest possible is requested"
   ::= { sispm10403166lFaultMgmtClientConfigFlowEntry 6 }

sispm10403166lFaultMgmtClientConfigFlowRowStatus OBJECT-TYPE
   SYNTAX      RowStatus
   MAX-ACCESS  read-create
   STATUS      current
   DESCRIPTION
       "FaultMgmtClientConfigFlow Row Status."
   ::= {sispm10403166lFaultMgmtClientConfigFlowEntry 7 }


sispm10403166lFaultMgmtAISLOCK    OBJECT IDENTIFIER ::= { sispm10403166lMEP 14 }

sispm10403166lFaultMgmtAISEnable OBJECT-TYPE
   SYNTAX      Integer32
   MAX-ACCESS  read-write
   STATUS      current
   DESCRIPTION
       "Insertion of AIS signal (AIS PDU transmission) in client layer flows, can be enable/disabled.
	   0:disable
	   1:enable"
   ::= { sispm10403166lFaultMgmtAISLOCK 2 }

sispm10403166lFaultMgmtAISFrameRate OBJECT-TYPE
   SYNTAX      Integer32
   MAX-ACCESS  read-write
   STATUS      current
   DESCRIPTION
       "Selecting the frame rate of AIS PDU.
	   This is the inverse of transmission period as described in Y.1731.
       1: 300 frames per second
	   2: 100 frames per second
	   3: 10 frames per second
	   4: 1 frames per second
	   5: 6 frames per minute
	   6: 1 frames per minute
	   7: 6 frames per hour"
   ::= { sispm10403166lFaultMgmtAISLOCK 3 }

sispm10403166lFaultMgmtAISProtection OBJECT-TYPE
   SYNTAX      Integer32
   MAX-ACCESS  read-write
   STATUS      current
   DESCRIPTION
       "Selecting this means that the first 3 AIS PDU is transmitted as fast as possible - in case of using this for protection in the end point.
	   0:disable
	   1:enable"
   ::= { sispm10403166lFaultMgmtAISLOCK 4 }


sispm10403166lFaultMgmtLOCKEnable OBJECT-TYPE
   SYNTAX      Integer32
   MAX-ACCESS  read-write
   STATUS      current
   DESCRIPTION
       "Insertion of LOCK signal (LCK PDU transmission) in client layer flows, can be enable/disabled.
	   0:disable
	   1:enable"
   ::= { sispm10403166lFaultMgmtAISLOCK 5 }

sispm10403166lFaultMgmtLOCKFrameRate OBJECT-TYPE
   SYNTAX      Integer32
   MAX-ACCESS  read-write
   STATUS      current
   DESCRIPTION
       "Selecting the frame rate of LCK PDU. This is the inverse of transmission period as described in Y.1731.
       1: 300 frames per second
	   2: 100 frames per second
	   3: 10 frames per second
	   4: 1 frames per second
	   5: 6 frames per minute
	   6: 1 frames per minute
	   7: 6 frames per hour"
   ::= { sispm10403166lFaultMgmtAISLOCK 6 }

sispm10403166lPerformanceMonitor  OBJECT IDENTIFIER ::= { sispm10403166lMEP 15 }

sispm10403166lDataSetEnable OBJECT-TYPE
   SYNTAX      Integer32
   MAX-ACCESS  read-write
   STATUS      current
   DESCRIPTION
       "
	   When enabled this MEP instance will contribute to the 'PM Data Set' gathered by the PM Session.
	   0:disable
	   1:enable"
   ::= { sispm10403166lPerformanceMonitor 2 }

sispm10403166lLossMeasureEnable OBJECT-TYPE
   SYNTAX      Integer32
   MAX-ACCESS  read-write
   STATUS      current
   DESCRIPTION
       "
	   Loss Measurement based on transmitting/receiving CCM or LMM/LMR PDU can be enabled/disabled - see 'Ended'.
	   This is only valid with one Peer MEP configured.
	   0:disable
	   1:enable"
   ::= { sispm10403166lPerformanceMonitor 3 }

sispm10403166lLossMeasurePriority OBJECT-TYPE
   SYNTAX      Integer32
   MAX-ACCESS  read-write
   STATUS      current
   DESCRIPTION
       "
	   The priority to be inserted as PCP bits in TAG (if any).
	   In case of enable of Continuity Check and Loss Measurement both implemented on SW based CCM, 'Priority' has to be the same.
	   range:0-7"
   ::= { sispm10403166lPerformanceMonitor 4 }

sispm10403166lLossMeasureFrameRate OBJECT-TYPE
   SYNTAX      Integer32
   MAX-ACCESS  read-write
   STATUS      current
   DESCRIPTION
       "
	   1: 300 frames per second
	   2: 100 frames per second
	   3: 10 frames per second
	   4: 1 frames per second
	   5: 6 frames per minute
	   6: 1 frames per minute
	   7: 6 frames per hour"
   ::= { sispm10403166lPerformanceMonitor 5 }

sispm10403166lLossMeasureCast OBJECT-TYPE
   SYNTAX      Integer32
   MAX-ACCESS  read-write
   STATUS      current
   DESCRIPTION
       "
	   0: Unicast destination address
	   1: Multicast destination address
	   "
   ::= { sispm10403166lPerformanceMonitor 6 }

sispm10403166lLossMeasureEnded OBJECT-TYPE
   SYNTAX      Integer32
   MAX-ACCESS  read-write
   STATUS      current
   DESCRIPTION
       "
	   0: Single ended LM based on LMM/LMR or DM based on DMM/DMR
	   1: Dual ended LM based on CCM or DM based on 1DM
	   "
   ::= { sispm10403166lPerformanceMonitor 7 }

sispm10403166lLossMeasureFLRInterval OBJECT-TYPE
   SYNTAX      Integer32
   MAX-ACCESS  read-write
   STATUS      current
   DESCRIPTION
       "
       This is the interval in seconds where the Frame Loss Ratio is calculated.
	   "
   ::= { sispm10403166lPerformanceMonitor 8 }

sispm10403166lLossMeasureLossThreshold OBJECT-TYPE
   SYNTAX      Integer32
   MAX-ACCESS  read-write
   STATUS      current
   DESCRIPTION
       "
       Far end loss threshold count is incremented if a loss measurement is above this threshold.
	   "
   ::= { sispm10403166lPerformanceMonitor 9 }

sispm10403166lLossMeasureStateTx OBJECT-TYPE
   SYNTAX      Integer32
   MAX-ACCESS  read-only
   STATUS      current
   DESCRIPTION
       "
	   "
   ::= { sispm10403166lPerformanceMonitor 10 }

sispm10403166lLossMeasureStateRx OBJECT-TYPE
   SYNTAX      Integer32
   MAX-ACCESS  read-only
   STATUS      current
   DESCRIPTION
       "
	   "
   ::= { sispm10403166lPerformanceMonitor 11 }

sispm10403166lLossMeasureStateNearEndLossCount OBJECT-TYPE
   SYNTAX      Integer32
   MAX-ACCESS  read-only
   STATUS      current
   DESCRIPTION
       "The accumulated near end frame loss count - since last 'clear'.
	   "
   ::= { sispm10403166lPerformanceMonitor 12 }

sispm10403166lLossMeasureStateFarEndLossCount OBJECT-TYPE
   SYNTAX      Integer32
   MAX-ACCESS  read-only
   STATUS      current
   DESCRIPTION
       "The accumulated far end frame loss count - since last 'clear'.
	   "
   ::= { sispm10403166lPerformanceMonitor 13 }

sispm10403166lLossMeasureStateNearEndLossRatio OBJECT-TYPE
   SYNTAX      Integer32
   MAX-ACCESS  read-only
   STATUS      current
   DESCRIPTION
       "The near end frame loss ratio calculated based on the near end frame loss count and far end frame transmitted - in the latest 'FLR Interval'.
	   The result is given in percent.
	   "
   ::= { sispm10403166lPerformanceMonitor 14 }

sispm10403166lLossMeasureStateFarEndLossRatio OBJECT-TYPE
   SYNTAX      Integer32
   MAX-ACCESS  read-only
   STATUS      current
   DESCRIPTION
       "The far end frame loss ratio calculated based on the far end frame loss count and near end frame transmitted - in the latest 'FLR Interval'.
	   The result is given in percent.
	   "
   ::= { sispm10403166lPerformanceMonitor 15 }

sispm10403166lLossMeasureStateClear OBJECT-TYPE
   SYNTAX      Integer32
   MAX-ACCESS  read-write
   STATUS      current
   DESCRIPTION
       "Set of this check and save will clear the accumulated counters and restart ratio calculation.
	   "
   ::= { sispm10403166lPerformanceMonitor 16 }

sispm10403166lLossMeasureAvailabilityEnable OBJECT-TYPE
   SYNTAX      Integer32
   MAX-ACCESS  read-write
   STATUS      current
   DESCRIPTION
       "Enable/disable of loss measurement availability.
	   0:disable
	   1:enable
	   "
   ::= { sispm10403166lPerformanceMonitor 17 }

sispm10403166lLossMeasureAvailabilityInterval OBJECT-TYPE
   SYNTAX      Integer32
   MAX-ACCESS  read-write
   STATUS      current
   DESCRIPTION
       "Availability interval - number of measurements with same availability in order to change availability state.

	   "
   ::= { sispm10403166lPerformanceMonitor 18 }

sispm10403166lLossMeasureAvailabilityFLRThreshold OBJECT-TYPE
   SYNTAX      Integer32
   MAX-ACCESS  read-write
   STATUS      current
   DESCRIPTION
       "Availability frame loss ratio threshold in per mille.
	   "
   ::= { sispm10403166lPerformanceMonitor 19 }

sispm10403166lLossMeasureAvailabilityMaintenance OBJECT-TYPE
   SYNTAX      Integer32
   MAX-ACCESS  read-write
   STATUS      current
   DESCRIPTION
       "Enable/disable of loss measurement availability maintenance.
	   "
   ::= { sispm10403166lPerformanceMonitor 20 }


sispm10403166lLossMeasureAvailabilityStateNearAvailabilityCount OBJECT-TYPE
   SYNTAX      Integer32
   MAX-ACCESS  read-only
   STATUS      current
   DESCRIPTION
       "Near end availability count.
	   "
   ::= { sispm10403166lPerformanceMonitor 21 }

sispm10403166lLossMeasureAvailabilityStateFarAvailabilityCount OBJECT-TYPE
   SYNTAX      Integer32
   MAX-ACCESS  read-only
   STATUS      current
   DESCRIPTION
       "Far end availability count.
	   "
   ::= { sispm10403166lPerformanceMonitor 22 }

sispm10403166lLossMeasureAvailStateNearUnavailabilityCount OBJECT-TYPE
   SYNTAX      Integer32
   MAX-ACCESS  read-only
   STATUS      current
   DESCRIPTION
       "Near end unavailability count.
	   "
   ::= { sispm10403166lPerformanceMonitor 23 }

sispm10403166lLossMeasureAvailabilityStateFarUnavailabilityCount OBJECT-TYPE
   SYNTAX      Integer32
   MAX-ACCESS  read-only
   STATUS      current
   DESCRIPTION
       "Far end unavailability count.
	   "
   ::= { sispm10403166lPerformanceMonitor 24 }

sispm10403166lLossMeasureAvailabilityStateNearState OBJECT-TYPE
   SYNTAX      Integer32
   MAX-ACCESS  read-only
   STATUS      current
   DESCRIPTION
       "Near end availability state.
	   "
   ::= { sispm10403166lPerformanceMonitor 25 }

sispm10403166lLossMeasureAvailabilityStateFarState OBJECT-TYPE
   SYNTAX      Integer32
   MAX-ACCESS  read-only
   STATUS      current
   DESCRIPTION
       "Far end availability state.
	   "
   ::= { sispm10403166lPerformanceMonitor 26 }

sispm10403166lLossMeasureHighLossIntervalEnable OBJECT-TYPE
   SYNTAX      Integer32
   MAX-ACCESS  read-write
   STATUS      current
   DESCRIPTION
       "Enable/disable of loss measurement high loss interval.
	   0:disable
	   1:enable
	   "
   ::= { sispm10403166lPerformanceMonitor 27 }

sispm10403166lLossMeasureHighLossIntervalFLRThreshold OBJECT-TYPE
   SYNTAX      Integer32
   MAX-ACCESS  read-write
   STATUS      current
   DESCRIPTION
       "High Loss Interval frame loss ratio threshold in per mille.
	   "
   ::= { sispm10403166lPerformanceMonitor 28 }

sispm10403166lLossMeasureHighLossIntervalConsecutiveInterval OBJECT-TYPE
   SYNTAX      Integer32
   MAX-ACCESS  read-write
   STATUS      current
   DESCRIPTION
       "High Loss Interval consecutive interval (number of measurements).
	   "
   ::= { sispm10403166lPerformanceMonitor 29 }

sispm10403166lLossMeasureHighLossIntervalStateNearCount OBJECT-TYPE
   SYNTAX      Integer32
   MAX-ACCESS  read-only
   STATUS      current
   DESCRIPTION
       "Near end high loss interval count (number of measurements where availability state is available and FLR is above high loss interval FLR threshold.
	   "
   ::= { sispm10403166lPerformanceMonitor 30 }

sispm10403166lLossMeasureHighLossIntervalStateFarCount OBJECT-TYPE
   SYNTAX      Integer32
   MAX-ACCESS  read-only
   STATUS      current
   DESCRIPTION
       "Far end high loss interval count (number of measurements where availability state is available and FLR is above high loss interval FLR threshold.
	   "
   ::= { sispm10403166lPerformanceMonitor 31 }

sispm10403166lLossMeasureIntervalStateNearConsecutiveCount OBJECT-TYPE
   SYNTAX      Integer32
   MAX-ACCESS  read-only
   STATUS      current
   DESCRIPTION
       "Near end high loss interval consecutive count.
	   "
   ::= { sispm10403166lPerformanceMonitor 32 }

sispm10403166lLossMeasureIntervalStateFarConsecutiveCount OBJECT-TYPE
   SYNTAX      Integer32
   MAX-ACCESS  read-only
   STATUS      current
   DESCRIPTION
       "Far end high loss interval consecutive count.
	   "
   ::= { sispm10403166lPerformanceMonitor 33 }

sispm10403166lLossMeasureSignalDegradeEnable OBJECT-TYPE
   SYNTAX      Integer32
   MAX-ACCESS  read-write
   STATUS      current
   DESCRIPTION
       "Enable/disable of loss measurement signal degrade.
	   0:disable
	   1:enable
	   "
   ::= { sispm10403166lPerformanceMonitor 34 }

sispm10403166lLossMeasureSignalDegradeTXMinimum OBJECT-TYPE
   SYNTAX      Integer32
   MAX-ACCESS  read-write
   STATUS      current
   DESCRIPTION
       "Minimum number of frames that must be transmitted in a measurement before frame loss ratio is tested against loss ratio threshold.

	   "
   ::= { sispm10403166lPerformanceMonitor 35 }

sispm10403166lLossMeasureSignalDegradeFLRThreshold OBJECT-TYPE
   SYNTAX      Integer32
   MAX-ACCESS  read-write
   STATUS      current
   DESCRIPTION
       "Signal Degraded frame loss ratio threshold in per mille.
	   "
   ::= { sispm10403166lPerformanceMonitor 36 }

sispm10403166lLossMeasureSignalDegradeBadThreshold OBJECT-TYPE
   SYNTAX      Integer32
   MAX-ACCESS  read-write
   STATUS      current
   DESCRIPTION
       "Number of consecutive bad interval measurements required to set degrade state.
	   "
   ::= { sispm10403166lPerformanceMonitor 37 }

sispm10403166lLossMeasureSignalDegradeGoodThreshold OBJECT-TYPE
   SYNTAX      Integer32
   MAX-ACCESS  read-write
   STATUS      current
   DESCRIPTION
       "Number of consecutive good interval measurements required to clear degrade state.
	   "
   ::= { sispm10403166lPerformanceMonitor 38 }

sispm10403166lDelayMeasureEnable OBJECT-TYPE
   SYNTAX      Integer32
   MAX-ACCESS  read-write
   STATUS      current
   DESCRIPTION
       "Delay Measurement based on transmitting 1DM/DMM PDU can be enabled/disabled.
	   Delay Measurement based on receiving and handling 1DM/DMR PDU is always enabled.
	   0:disable
	   1:enable
	   "
   ::= { sispm10403166lPerformanceMonitor 39 }

sispm10403166lDelayMeasurePriority OBJECT-TYPE
   SYNTAX      Integer32
   MAX-ACCESS  read-write
   STATUS      current
   DESCRIPTION
       "The priority to be inserted as PCP bits in TAG (if any).
       Range:0-7
	   "
   ::= { sispm10403166lPerformanceMonitor 40 }

sispm10403166lDelayMeasureCast OBJECT-TYPE
   SYNTAX      Integer32
   MAX-ACCESS  read-write
   STATUS      current
   DESCRIPTION
       "Selection of 1DM/DMM PDU transmitted unicast or multicast.
	   The unicast MAC will be configured through 'Peer MEP'.
	   0: Unicast destination address
	   1: Multicast destination address
	   "
   ::= { sispm10403166lPerformanceMonitor 41 }

sispm10403166lDelayMeasurePeerMEP OBJECT-TYPE
   SYNTAX      Integer32
   MAX-ACCESS  read-write
   STATUS      current
   DESCRIPTION
       "This is only used if the 'Cast' is configured to Uni.
	   The 1DM/DMR unicast MAC will be taken from the 'Unicast Peer MAC' configuration of this peer.
	   "
   ::= { sispm10403166lPerformanceMonitor 42 }

sispm10403166lDelayMeasureEnded OBJECT-TYPE
   SYNTAX      Integer32
   MAX-ACCESS  read-write
   STATUS      current
   DESCRIPTION
       "0:One-Way: One-Way Delay Measurement implemented on 1DM.
        1:Two-Way: Two-Way Delay Measurement implemented on DMM/DMR.
	   "
   ::= { sispm10403166lPerformanceMonitor 43 }

sispm10403166lDelayMeasureTxMode OBJECT-TYPE
   SYNTAX      Integer32
   MAX-ACCESS  read-write
   STATUS      current
   DESCRIPTION
       "0:Standardize: Y.1731 standardize way to transmit 1DM/DMR.
        1:Proprietary: Vitesse proprietary way with follow-up packets to transmit 1DM/DMR.
	   "
   ::= { sispm10403166lPerformanceMonitor 44 }

sispm10403166lDelayMeasureCalc OBJECT-TYPE
   SYNTAX      Integer32
   MAX-ACCESS  read-write
   STATUS      current
   DESCRIPTION
       "This is only used if the 'Way' is configured to Two-way.
        0:Round trip: The frame delay calculated by the transmitting and receiving timestamps of initiators.
		    Frame Delay = RxTimeb-TxTimeStampf
        1:Flow: The frame delay calculated by the transmitting and receiving timestamps of initiators and remotes.
		    Frame Delay = (RxTimeb-TxTimeStampf)-(TxTimeStampb-RxTimeStampf)
	   "
   ::= { sispm10403166lPerformanceMonitor 45 }

sispm10403166lDelayMeasureGap OBJECT-TYPE
   SYNTAX      Integer32
   MAX-ACCESS  read-write
   STATUS      current
   DESCRIPTION
       "The gap between transmitting 1DM/DMM PDU in 10ms. The range is 10 to 65535.
	   "
   ::= { sispm10403166lPerformanceMonitor 46 }

sispm10403166lDelayMeasureCount OBJECT-TYPE
   SYNTAX      Integer32
   MAX-ACCESS  read-write
   STATUS      current
   DESCRIPTION
       "The number of last records to calculate. The range is 10 to 2000.
	   "
   ::= { sispm10403166lPerformanceMonitor 47 }

sispm10403166lDelayMeasureUnit OBJECT-TYPE
   SYNTAX      Integer32
   MAX-ACCESS  read-write
   STATUS      current
   DESCRIPTION
       "The time resolution.
	   0:us
	   1:ns
	   "
   ::= { sispm10403166lPerformanceMonitor 48 }

sispm10403166lDelayMeasureD2forD1 OBJECT-TYPE
   SYNTAX      Integer32
   MAX-ACCESS  read-write
   STATUS      current
   DESCRIPTION
       "Enable to use DMM/DMR packet to calculate one-way DM.
	   0:disable
	   1:enable
	   "
   ::= { sispm10403166lPerformanceMonitor 49 }

sispm10403166lDelayMeasureCounterOverflowAction OBJECT-TYPE
   SYNTAX      Integer32
   MAX-ACCESS  read-write
   STATUS      current
   DESCRIPTION
       "The action to counter when overflow happens.
	   0: Keep:When internal total delay counter overflow, DM is disabled automatically
	   1: Reset:When internal total delay counter overflow, counter is reset and DM continues running
	   "
   ::= { sispm10403166lPerformanceMonitor 50 }

sispm10403166lDelayMeasureStateOnewayTx OBJECT-TYPE
   SYNTAX      DisplayString
   MAX-ACCESS  read-only
   STATUS      current
   DESCRIPTION
       "The accumulated transmit count - since last 'clear'.
	   "
   ::= { sispm10403166lPerformanceMonitor 51 }

sispm10403166lDelayMeasureStateOnewayRx OBJECT-TYPE
   SYNTAX      DisplayString
   MAX-ACCESS  read-only
   STATUS      current
   DESCRIPTION
       "The accumulated receive count - since last 'clear'.
	   "
   ::= { sispm10403166lPerformanceMonitor 52 }

sispm10403166lDelayMeasureStateOnewayRxTimeout OBJECT-TYPE
   SYNTAX      DisplayString
   MAX-ACCESS  read-only
   STATUS      current
   DESCRIPTION
       "The accumulated receive timeout count for two-way only - since last 'clear'.
	   "
   ::= { sispm10403166lPerformanceMonitor 53 }

sispm10403166lDelayMeasureStateOnewayRxError OBJECT-TYPE
   SYNTAX      DisplayString
   MAX-ACCESS  read-only
   STATUS      current
   DESCRIPTION
       "The accumulated receive error count - since last 'clear'.
	   This is counting if the frame delay is larger than 1 second or if far end residence time is larger than the round trip time.
	   "
   ::= { sispm10403166lPerformanceMonitor 54 }

sispm10403166lDelayMeasureStateOnewayAvDelayTot OBJECT-TYPE
   SYNTAX      DisplayString
   MAX-ACCESS  read-only
   STATUS      current
   DESCRIPTION
       "The average total delay - since last 'clear'.
	   "
   ::= { sispm10403166lPerformanceMonitor 55 }

sispm10403166lDelayMeasureStateOnewayAvDelaylastN OBJECT-TYPE
   SYNTAX      DisplayString
   MAX-ACCESS  read-only
   STATUS      current
   DESCRIPTION
       "The average delay of the last n packets - since last 'clear'.
	   "
   ::= { sispm10403166lPerformanceMonitor 56 }

sispm10403166lDelayMeasureStateOnewayDelayMin OBJECT-TYPE
   SYNTAX      DisplayString
   MAX-ACCESS  read-only
   STATUS      current
   DESCRIPTION
       "The minimum delay - since last 'clear'.
	   "
   ::= { sispm10403166lPerformanceMonitor 57 }

sispm10403166lDelayMeasureStateOnewayDelayMax OBJECT-TYPE
   SYNTAX      DisplayString
   MAX-ACCESS  read-only
   STATUS      current
   DESCRIPTION
       "The maximum delay - since last 'clear'.
	   "
   ::= { sispm10403166lPerformanceMonitor 58 }

sispm10403166lDelayMeasureStateOnewayAvDelayVarTot OBJECT-TYPE
   SYNTAX      DisplayString
   MAX-ACCESS  read-only
   STATUS      current
   DESCRIPTION
       "The average total delay variation - since last 'clear'.
	   "
   ::= { sispm10403166lPerformanceMonitor 59 }

sispm10403166lDelayMeasureStateOnewayAvDelayVarlastN OBJECT-TYPE
   SYNTAX      DisplayString
   MAX-ACCESS  read-only
   STATUS      current
   DESCRIPTION
       "The average delay variation of the last n packets - since last 'clear'.
	   "
   ::= { sispm10403166lPerformanceMonitor 60 }

sispm10403166lDelayMeasureStateOnewayDelayVarMin OBJECT-TYPE
   SYNTAX      DisplayString
   MAX-ACCESS  read-only
   STATUS      current
   DESCRIPTION
       "The minimum delay variation - since last 'clear'.
	   "
   ::= { sispm10403166lPerformanceMonitor 61 }

sispm10403166lDelayMeasureStateOnewayDelayVarMax OBJECT-TYPE
   SYNTAX      DisplayString
   MAX-ACCESS  read-only
   STATUS      current
   DESCRIPTION
       "The maximum delay variation - since last 'clear'.
	   "
   ::= { sispm10403166lPerformanceMonitor 62 }

sispm10403166lDelayMeasureStateOnewayOverflow OBJECT-TYPE
   SYNTAX      DisplayString
   MAX-ACCESS  read-only
   STATUS      current
   DESCRIPTION
       "The number of counter overflow - since last 'clear'.
	   "
   ::= { sispm10403166lPerformanceMonitor 63 }

sispm10403166lDelayMeasureStateFtoNTx OBJECT-TYPE
   SYNTAX      Integer32
   MAX-ACCESS  read-only
   STATUS      current
   DESCRIPTION
       "The accumulated transmit count - since last 'clear'.
	   "
   ::= { sispm10403166lPerformanceMonitor 64 }

sispm10403166lDelayMeasureStateFtoNRx OBJECT-TYPE
   SYNTAX      Integer32
   MAX-ACCESS  read-only
   STATUS      current
   DESCRIPTION
       "The accumulated receive count - since last 'clear'.
	   "
   ::= { sispm10403166lPerformanceMonitor 65 }

sispm10403166lDelayMeasureStateFtoNRxTimeout OBJECT-TYPE
   SYNTAX      Integer32
   MAX-ACCESS  read-only
   STATUS      current
   DESCRIPTION
       "The accumulated receive timeout count for two-way only - since last 'clear'.
	   "
   ::= { sispm10403166lPerformanceMonitor 66 }

sispm10403166lDelayMeasureStateFtoNRxError OBJECT-TYPE
   SYNTAX      Integer32
   MAX-ACCESS  read-only
   STATUS      current
   DESCRIPTION
       "The accumulated receive error count - since last 'clear'.
	   This is counting if the frame delay is larger than 1 second or if far end residence time is larger than the round trip time.
	   "
   ::= { sispm10403166lPerformanceMonitor 67 }

sispm10403166lDelayMeasureStateFtoNAvDelayTot OBJECT-TYPE
   SYNTAX      Integer32
   MAX-ACCESS  read-only
   STATUS      current
   DESCRIPTION
       "The average total delay - since last 'clear'.
	   "
   ::= { sispm10403166lPerformanceMonitor 68 }

sispm10403166lDelayMeasureStateFtoNAvDelaylastN OBJECT-TYPE
   SYNTAX      Integer32
   MAX-ACCESS  read-only
   STATUS      current
   DESCRIPTION
       "The average delay of the last n packets - since last 'clear'.
	   "
   ::= { sispm10403166lPerformanceMonitor 69 }

sispm10403166lDelayMeasureStateFtoNDelayMin OBJECT-TYPE
   SYNTAX      Integer32
   MAX-ACCESS  read-only
   STATUS      current
   DESCRIPTION
       "The minimum delay - since last 'clear'.
	   "
   ::= { sispm10403166lPerformanceMonitor 70 }

sispm10403166lDelayMeasureStateFtoNDelayMax OBJECT-TYPE
   SYNTAX      Integer32
   MAX-ACCESS  read-only
   STATUS      current
   DESCRIPTION
       "The maximum delay - since last 'clear'.
	   "
   ::= { sispm10403166lPerformanceMonitor 71 }

sispm10403166lDelayMeasureStateFtoNAvDelayVarTot OBJECT-TYPE
   SYNTAX      Integer32
   MAX-ACCESS  read-only
   STATUS      current
   DESCRIPTION
       "The average total delay variation - since last 'clear'.
	   "
   ::= { sispm10403166lPerformanceMonitor 72 }

sispm10403166lDelayMeasureStateFtoNAvDelayVarlastN OBJECT-TYPE
   SYNTAX      Integer32
   MAX-ACCESS  read-only
   STATUS      current
   DESCRIPTION
       "The average delay variation of the last n packets - since last 'clear'.
	   "
   ::= { sispm10403166lPerformanceMonitor 73 }

sispm10403166lDelayMeasureStateFtoNDelayVarMin OBJECT-TYPE
   SYNTAX      Integer32
   MAX-ACCESS  read-only
   STATUS      current
   DESCRIPTION
       "The minimum delay variation - since last 'clear'.
	   "
   ::= { sispm10403166lPerformanceMonitor 74 }

sispm10403166lDelayMeasureStateFtoNDelayVarMax OBJECT-TYPE
   SYNTAX      Integer32
   MAX-ACCESS  read-only
   STATUS      current
   DESCRIPTION
       "The maximum delay variation - since last 'clear'.
	   "
   ::= { sispm10403166lPerformanceMonitor 75 }

sispm10403166lDelayMeasureStateFtoNOverflow OBJECT-TYPE
   SYNTAX      Integer32
   MAX-ACCESS  read-only
   STATUS      current
   DESCRIPTION
       "The number of counter overflow - since last 'clear'.
	   "
   ::= { sispm10403166lPerformanceMonitor 76 }

sispm10403166lDelayMeasureStateNtoFTx OBJECT-TYPE
   SYNTAX      Integer32
   MAX-ACCESS  read-only
   STATUS      current
   DESCRIPTION
       "The accumulated transmit count - since last 'clear'.
	   "
   ::= { sispm10403166lPerformanceMonitor 77 }

sispm10403166lDelayMeasureStateNtoFRx OBJECT-TYPE
   SYNTAX      Integer32
   MAX-ACCESS  read-only
   STATUS      current
   DESCRIPTION
       "The accumulated receive count - since last 'clear'.
	   "
   ::= { sispm10403166lPerformanceMonitor 78 }

sispm10403166lDelayMeasureStateNtoFRxTimeout OBJECT-TYPE
   SYNTAX      Integer32
   MAX-ACCESS  read-only
   STATUS      current
   DESCRIPTION
       "The accumulated receive timeout count for two-way only - since last 'clear'.
	   "
   ::= { sispm10403166lPerformanceMonitor 79 }

sispm10403166lDelayMeasureStateNtoFRxError OBJECT-TYPE
   SYNTAX      Integer32
   MAX-ACCESS  read-only
   STATUS      current
   DESCRIPTION
       "The accumulated receive error count - since last 'clear'.
	   This is counting if the frame delay is larger than 1 second or if far end residence time is larger than the round trip time.
	   "
   ::= { sispm10403166lPerformanceMonitor 80 }

sispm10403166lDelayMeasureStateNtoFAvDelayTot OBJECT-TYPE
   SYNTAX      Integer32
   MAX-ACCESS  read-only
   STATUS      current
   DESCRIPTION
       "The average total delay - since last 'clear'.
	   "
   ::= { sispm10403166lPerformanceMonitor 81 }

sispm10403166lDelayMeasureStateNtoFAvDelaylastN OBJECT-TYPE
   SYNTAX      Integer32
   MAX-ACCESS  read-only
   STATUS      current
   DESCRIPTION
       "The average delay of the last n packets - since last 'clear'.
	   "
   ::= { sispm10403166lPerformanceMonitor 82 }

sispm10403166lDelayMeasureStateNtoFDelayMin OBJECT-TYPE
   SYNTAX      Integer32
   MAX-ACCESS  read-only
   STATUS      current
   DESCRIPTION
       "The minimum delay - since last 'clear'.
	   "
   ::= { sispm10403166lPerformanceMonitor 83 }

sispm10403166lDelayMeasureStateNtoFDelayMax OBJECT-TYPE
   SYNTAX      Integer32
   MAX-ACCESS  read-only
   STATUS      current
   DESCRIPTION
       "The maximum delay - since last 'clear'.
	   "
   ::= { sispm10403166lPerformanceMonitor 84 }

sispm10403166lDelayMeasureStateNtoFAvDelayVarTot OBJECT-TYPE
   SYNTAX      Integer32
   MAX-ACCESS  read-only
   STATUS      current
   DESCRIPTION
       "The average total delay variation - since last 'clear'.
	   "
   ::= { sispm10403166lPerformanceMonitor 85 }

sispm10403166lDelayMeasureStateNtoFAvDelayVarlastN OBJECT-TYPE
   SYNTAX      Integer32
   MAX-ACCESS  read-only
   STATUS      current
   DESCRIPTION
       "The average delay variation of the last n packets - since last 'clear'.
	   "
   ::= { sispm10403166lPerformanceMonitor 86 }

sispm10403166lDelayMeasureStateNtoFDelayVarMin OBJECT-TYPE
   SYNTAX      Integer32
   MAX-ACCESS  read-only
   STATUS      current
   DESCRIPTION
       "The minimum delay variation - since last 'clear'.
	   "
   ::= { sispm10403166lPerformanceMonitor 87 }

sispm10403166lDelayMeasureStateNtoFDelayVarMax OBJECT-TYPE
   SYNTAX      Integer32
   MAX-ACCESS  read-only
   STATUS      current
   DESCRIPTION
       "The maximum delay variation - since last 'clear'.
	   "
   ::= { sispm10403166lPerformanceMonitor 88 }

sispm10403166lDelayMeasureStateNtoFOverflow OBJECT-TYPE
   SYNTAX      Integer32
   MAX-ACCESS  read-only
   STATUS      current
   DESCRIPTION
       "The number of counter overflow - since last 'clear'.
	   "
   ::= { sispm10403166lPerformanceMonitor 89 }

sispm10403166lDelayMeasureStateTwowayTx OBJECT-TYPE
   SYNTAX      Integer32
   MAX-ACCESS  read-only
   STATUS      current
   DESCRIPTION
       "The accumulated transmit count - since last 'clear'.
	   "
   ::= { sispm10403166lPerformanceMonitor 90 }

sispm10403166lDelayMeasureStateTwowayRx OBJECT-TYPE
   SYNTAX      Integer32
   MAX-ACCESS  read-only
   STATUS      current
   DESCRIPTION
       "The accumulated receive count - since last 'clear'.
	   "
   ::= { sispm10403166lPerformanceMonitor 91 }

sispm10403166lDelayMeasureStateTwowayRxTimeout OBJECT-TYPE
   SYNTAX      Integer32
   MAX-ACCESS  read-only
   STATUS      current
   DESCRIPTION
       "The accumulated receive timeout count for two-way only - since last 'clear'.
	   "
   ::= { sispm10403166lPerformanceMonitor 92 }

sispm10403166lDelayMeasureStateTwowayRxError OBJECT-TYPE
   SYNTAX      Integer32
   MAX-ACCESS  read-only
   STATUS      current
   DESCRIPTION
       "The accumulated receive error count - since last 'clear'.
	   This is counting if the frame delay is larger than 1 second or if far end residence time is larger than the round trip time.
	   "
   ::= { sispm10403166lPerformanceMonitor 93 }

sispm10403166lDelayMeasureStateTwowayAvDelayTot OBJECT-TYPE
   SYNTAX      Integer32
   MAX-ACCESS  read-only
   STATUS      current
   DESCRIPTION
       "The average total delay - since last 'clear'.
	   "
   ::= { sispm10403166lPerformanceMonitor 94 }

sispm10403166lDelayMeasureStateTwowayAvDelaylastN OBJECT-TYPE
   SYNTAX      Integer32
   MAX-ACCESS  read-only
   STATUS      current
   DESCRIPTION
       "The average delay of the last n packets - since last 'clear'.
	   "
   ::= { sispm10403166lPerformanceMonitor 95 }

sispm10403166lDelayMeasureStateTwowayDelayMin OBJECT-TYPE
   SYNTAX      Integer32
   MAX-ACCESS  read-only
   STATUS      current
   DESCRIPTION
       "The minimum delay - since last 'clear'.
	   "
   ::= { sispm10403166lPerformanceMonitor 96 }

sispm10403166lDelayMeasureStateTwowayDelayMax OBJECT-TYPE
   SYNTAX      Integer32
   MAX-ACCESS  read-only
   STATUS      current
   DESCRIPTION
       "The maximum delay - since last 'clear'.
	   "
   ::= { sispm10403166lPerformanceMonitor 97 }

sispm10403166lDelayMeasureStateTwowayAvDelayVarTot OBJECT-TYPE
   SYNTAX      Integer32
   MAX-ACCESS  read-only
   STATUS      current
   DESCRIPTION
       "The average total delay variation - since last 'clear'.
	   "
   ::= { sispm10403166lPerformanceMonitor 98 }

sispm10403166lDelayMeasureStateTwowayAvDelayVarlastN OBJECT-TYPE
   SYNTAX      Integer32
   MAX-ACCESS  read-only
   STATUS      current
   DESCRIPTION
       "The average delay variation of the last n packets - since last 'clear'.
	   "
   ::= { sispm10403166lPerformanceMonitor 99 }

sispm10403166lDelayMeasureStateTwowayDelayVarMin OBJECT-TYPE
   SYNTAX      Integer32
   MAX-ACCESS  read-only
   STATUS      current
   DESCRIPTION
       "The minimum delay variation - since last 'clear'.
	   "
   ::= { sispm10403166lPerformanceMonitor 100 }

sispm10403166lDelayMeasureStateTwowayDelayVarMax OBJECT-TYPE
   SYNTAX      Integer32
   MAX-ACCESS  read-only
   STATUS      current
   DESCRIPTION
       "The maximum delay variation - since last 'clear'.
	   "
   ::= { sispm10403166lPerformanceMonitor 101 }

sispm10403166lDelayMeasureStateTwowayOverflow OBJECT-TYPE
   SYNTAX      Integer32
   MAX-ACCESS  read-only
   STATUS      current
   DESCRIPTION
       "The number of counter overflow - since last 'clear'.
	   "
   ::= { sispm10403166lPerformanceMonitor 102 }

sispm10403166lDelayMeasureStateClear OBJECT-TYPE
   SYNTAX      Integer32
   MAX-ACCESS  read-write
   STATUS      current
   DESCRIPTION
       "Set of this check and save will clear the accumulated counters.
	   1:clear
	   "
   ::= { sispm10403166lPerformanceMonitor 103 }

sispm10403166lDelayMeasureBinsMeasurementBinsforFD OBJECT-TYPE
   SYNTAX      Integer32
   MAX-ACCESS  read-write
   STATUS      current
   DESCRIPTION
       "Configurable number of Frame Delay Measurement Bins per Measurement Interval.
	   range: 2-10
	   "
   ::= { sispm10403166lPerformanceMonitor 104 }

sispm10403166lDelayMeasureBinsMeasurementBinsforIFDV OBJECT-TYPE
   SYNTAX      Integer32
   MAX-ACCESS  read-write
   STATUS      current
   DESCRIPTION
       "Configurable number of Inter-Frame Delay Variation Measurement Bins per Measurement Interval.
	   range: 2-10
	   "
   ::= { sispm10403166lPerformanceMonitor 105 }

sispm10403166lDelayMeasureBinsMeasurementThreshold OBJECT-TYPE
   SYNTAX      Integer32
   MAX-ACCESS  read-write
   STATUS      current
   DESCRIPTION
       "Configurable the Measurement Threshold for each Measurement Bin.
	   "
   ::= { sispm10403166lPerformanceMonitor 106 }




sispm10403166lPerformanceMonitorDelayMeasurementBinsforFDTable OBJECT-TYPE
   SYNTAX      SEQUENCE OF SISPM10403166LPerformanceMonitorDelayMeasurementBinsforFDEntry
   MAX-ACCESS  not-accessible
   STATUS      current
   DESCRIPTION
       " "
   ::= { sispm10403166lMEP 16 }

sispm10403166lPerformanceMonitorDelayMeasurementBinsforFDEntry OBJECT-TYPE
   SYNTAX      SISPM10403166LPerformanceMonitorDelayMeasurementBinsforFDEntry
   MAX-ACCESS  not-accessible
   STATUS      current
   DESCRIPTION
       " "
   INDEX    { sispm10403166lPerformanceMonitorDelayMeasurementBinsforFDIndex  }
   ::= { sispm10403166lPerformanceMonitorDelayMeasurementBinsforFDTable 1 }

SISPM10403166LPerformanceMonitorDelayMeasurementBinsforFDEntry ::= SEQUENCE {
   sispm10403166lPerformanceMonitorDelayMeasurementBinsforFDIndex    Integer32,
   sispm10403166lPerformanceMonitorDelayMeasurementBinsforFDOneway   Integer32,
   sispm10403166lPerformanceMonitorDelayMeasurementBinsforFDFtoN     Integer32,
   sispm10403166lPerformanceMonitorDelayMeasurementBinsforFDNtoF     Integer32,
   sispm10403166lPerformanceMonitorDelayMeasurementBinsforFDTwoway   Integer32

}

sispm10403166lPerformanceMonitorDelayMeasurementBinsforFDIndex OBJECT-TYPE
   SYNTAX      Integer32(1..65535)
   MAX-ACCESS  not-accessible
   STATUS      current
   DESCRIPTION
       "Index"
   ::= { sispm10403166lPerformanceMonitorDelayMeasurementBinsforFDEntry 1 }

sispm10403166lPerformanceMonitorDelayMeasurementBinsforFDOneway OBJECT-TYPE
   SYNTAX      Integer32
   MAX-ACCESS  read-only
   STATUS      current
   DESCRIPTION
       " "
   ::= { sispm10403166lPerformanceMonitorDelayMeasurementBinsforFDEntry 2 }

sispm10403166lPerformanceMonitorDelayMeasurementBinsforFDFtoN OBJECT-TYPE
   SYNTAX      Integer32
   MAX-ACCESS  read-only
   STATUS      current
   DESCRIPTION
       " "
   ::= { sispm10403166lPerformanceMonitorDelayMeasurementBinsforFDEntry 3 }

sispm10403166lPerformanceMonitorDelayMeasurementBinsforFDNtoF OBJECT-TYPE
   SYNTAX      Integer32
   MAX-ACCESS  read-only
   STATUS      current
   DESCRIPTION
       " "
   ::= { sispm10403166lPerformanceMonitorDelayMeasurementBinsforFDEntry 4 }

sispm10403166lPerformanceMonitorDelayMeasurementBinsforFDTwoway OBJECT-TYPE
   SYNTAX      Integer32
   MAX-ACCESS  read-only
   STATUS      current
   DESCRIPTION
       " "
   ::= { sispm10403166lPerformanceMonitorDelayMeasurementBinsforFDEntry 5 }




sispm10403166lPerformanceMonitorDelayMeasurementBinsforIFDVTable OBJECT-TYPE
   SYNTAX      SEQUENCE OF SISPM10403166LPerformanceMonitorDelayMeasurementBinsforIFDVEntry
   MAX-ACCESS  not-accessible
   STATUS      current
   DESCRIPTION
       " "
   ::= { sispm10403166lMEP 17 }

sispm10403166lPerformanceMonitorDelayMeasurementBinsforIFDVEntry OBJECT-TYPE
   SYNTAX      SISPM10403166LPerformanceMonitorDelayMeasurementBinsforIFDVEntry
   MAX-ACCESS  not-accessible
   STATUS      current
   DESCRIPTION
       " "
   INDEX    { sispm10403166lPerformanceMonitorDelayMeasureBinsforIFDVIndex  }
   ::= { sispm10403166lPerformanceMonitorDelayMeasurementBinsforIFDVTable 1 }

SISPM10403166LPerformanceMonitorDelayMeasurementBinsforIFDVEntry ::= SEQUENCE {
   sispm10403166lPerformanceMonitorDelayMeasureBinsforIFDVIndex    Integer32,
   sispm10403166lPerformanceMonitorDelayMeasureBinsforIFDVOneway   Integer32,
   sispm10403166lPerformanceMonitorDelayMeasureBinsforIFDVFtoN     Integer32,
   sispm10403166lPerformanceMonitorDelayMeasureBinsforIFDVNtoF     Integer32,
   sispm10403166lPerformanceMonitorDelayMeasureBinsforIFDVTwoway   Integer32

}

sispm10403166lPerformanceMonitorDelayMeasureBinsforIFDVIndex OBJECT-TYPE
   SYNTAX      Integer32(1..65535)
   MAX-ACCESS  not-accessible
   STATUS      current
   DESCRIPTION
       "Index"
   ::= { sispm10403166lPerformanceMonitorDelayMeasurementBinsforIFDVEntry 1 }

sispm10403166lPerformanceMonitorDelayMeasureBinsforIFDVOneway OBJECT-TYPE
   SYNTAX      Integer32
   MAX-ACCESS  read-only
   STATUS      current
   DESCRIPTION
       " "
   ::= { sispm10403166lPerformanceMonitorDelayMeasurementBinsforIFDVEntry 2 }

sispm10403166lPerformanceMonitorDelayMeasureBinsforIFDVFtoN OBJECT-TYPE
   SYNTAX      Integer32
   MAX-ACCESS  read-only
   STATUS      current
   DESCRIPTION
       " "
   ::= { sispm10403166lPerformanceMonitorDelayMeasurementBinsforIFDVEntry 3 }

sispm10403166lPerformanceMonitorDelayMeasureBinsforIFDVNtoF OBJECT-TYPE
   SYNTAX      Integer32
   MAX-ACCESS  read-only
   STATUS      current
   DESCRIPTION
       " "
   ::= { sispm10403166lPerformanceMonitorDelayMeasurementBinsforIFDVEntry 4 }

sispm10403166lPerformanceMonitorDelayMeasureBinsforIFDVTwoway OBJECT-TYPE
   SYNTAX      Integer32
   MAX-ACCESS  read-only
   STATUS      current
   DESCRIPTION
       " "
   ::= { sispm10403166lPerformanceMonitorDelayMeasurementBinsforIFDVEntry 5 }
-- =============================================================================================================
sispm10403166lPTP    OBJECT IDENTIFIER ::= { sispm10403166lConfiguration 28 }

sispm10403166lPTPExternalEnable OBJECT-TYPE
   SYNTAX      Integer32
   MAX-ACCESS  read-write
   STATUS      current
   DESCRIPTION
       "This Selection box will allow you to configure the External Clock output.
		The following values are possible:
		1. True : Enable the external clock output
		0. False : Disable the external clock output
		"
   ::= { sispm10403166lPTP 1 }

sispm10403166lPTPAdjustMethod OBJECT-TYPE
   SYNTAX      Integer32
   MAX-ACCESS  read-write
   STATUS      current
   DESCRIPTION
       "This Selection box will allow you to configure the Frequency adjustment configuration.
		0: LTC frequency : Select Local Time Counter (LTC) frequency control
		1: SyncE-DPLL : Select SyncE DPLL frequency control, if allowed by SyncE
		2: Oscillator : Select an oscillator independent of SyncE for frequency control, if supported by the HW
		3: LTC phase : Select Local Time Counter (LTC) phase control (assumes that the frequency is locked by means of SyncE)
		"
   ::= { sispm10403166lPTP 2 }

sispm10403166lPTPClockFrequency OBJECT-TYPE
   SYNTAX      Integer32
   MAX-ACCESS  read-write
   STATUS      current
   DESCRIPTION
       "This will allow to set the Clock Frequency.
        The possible range of values are 1 - 25000000 (1 - 25MHz)
	   "
   ::= { sispm10403166lPTP 3 }



sispm10403166lPTPClockConfTable  OBJECT-TYPE
   SYNTAX      SEQUENCE OF SISPM10403166LPTPClockConfEntry
   MAX-ACCESS  not-accessible
   STATUS      current
   DESCRIPTION
       "A table of PTP Clock Conf."
 ::= { sispm10403166lPTP 5 }

sispm10403166lPTPClockConfEntry OBJECT-TYPE
    SYNTAX        SISPM10403166LPTPClockConfEntry
    MAX-ACCESS    not-accessible
    STATUS        current
    DESCRIPTION
        "An entry in the PTP Clock Conf table."
    INDEX        { sispm10403166lPTPClockConfIndex }
    ::= { sispm10403166lPTPClockConfTable 1 }

SISPM10403166LPTPClockConfEntry ::=
    SEQUENCE {
        sispm10403166lPTPClockConfIndex                    Integer32,
        sispm10403166lPTPClockConfClockInstance            Integer32,
        sispm10403166lPTPClockConfDeviceType               Integer32,
		sispm10403166lPTPClockConfProfile                  Integer32,
        sispm10403166lPTPClockConfRowStatus                RowStatus
    }

sispm10403166lPTPClockConfIndex OBJECT-TYPE
   SYNTAX      Integer32(1..65535)
   MAX-ACCESS  not-accessible
   STATUS      current
   DESCRIPTION
       "PTP Clock Conf index."
   ::= {sispm10403166lPTPClockConfEntry 1 }

sispm10403166lPTPClockConfClockInstance OBJECT-TYPE
   SYNTAX      Integer32
   MAX-ACCESS  read-create
   STATUS      current
   DESCRIPTION
       "Indicates the Instance of a particular Clock Instance [0..3]."
   ::= {sispm10403166lPTPClockConfEntry 2 }

sispm10403166lPTPClockConfDeviceType OBJECT-TYPE
   SYNTAX      Integer32
   MAX-ACCESS  read-create
   STATUS      current
   DESCRIPTION
       "Indicates the Type of the Clock Instance. There are five Device Types.
	    0: Inactive - passive clock instance
		1: Ord-Bound - clock's Device Type is Ordinary-Boundary Clock.
		2: P2p Transp - clock's Device Type is Peer to Peer Transparent Clock.
		3: E2e Transp - clock's Device Type is End to End Transparent Clock.
		4: Master Only - clock's Device Type is Master Only.
		5: Slave Only - clock's Device Type is Slave Only.
		6: Boundary Clock frontend clock instance, only 1-step, 1-way is supported."
   ::= {sispm10403166lPTPClockConfEntry 3 }

sispm10403166lPTPClockConfProfile OBJECT-TYPE
   SYNTAX      Integer32
   MAX-ACCESS  read-create
   STATUS      current
   DESCRIPTION
       "0:No profile
	   1:1588
	   2:G8265.1
	   3:G8275.1
	   "
   ::= {sispm10403166lPTPClockConfEntry 4 }

sispm10403166lPTPClockConfRowStatus OBJECT-TYPE
   SYNTAX      RowStatus
   MAX-ACCESS  read-create
   STATUS      current
   DESCRIPTION
       "PTP Clock Conf Row Status."
   ::= {sispm10403166lPTPClockConfEntry 5 }

sispm10403166lPTPClockInstance OBJECT-TYPE
   SYNTAX      Integer32
   MAX-ACCESS  read-write
   STATUS      current
   DESCRIPTION
       "Specify the PTP clock instance for the following item used [0..3]."
   ::= {sispm10403166lPTP 6 }


sispm10403166lPTPClockConfAndStatus    OBJECT IDENTIFIER ::= { sispm10403166lPTP 7 }

sispm10403166lEntryClockInstance OBJECT-TYPE
   SYNTAX      Integer32
   MAX-ACCESS  read-only
   STATUS      current
   DESCRIPTION
       ""
   ::= {sispm10403166lPTPClockConfAndStatus 2 }

sispm10403166lEntryDeviceType OBJECT-TYPE
   SYNTAX      DisplayString
   MAX-ACCESS  read-only
   STATUS      current
   DESCRIPTION
       ""
   ::= {sispm10403166lPTPClockConfAndStatus 3 }

sispm10403166lEntryProfile OBJECT-TYPE
   SYNTAX      DisplayString
   MAX-ACCESS  read-only
   STATUS      current
   DESCRIPTION
       ""
   ::= {sispm10403166lPTPClockConfAndStatus 4 }

sispm10403166lEntryApplyProfileDefaults OBJECT-TYPE
   SYNTAX      Integer32
   MAX-ACCESS  read-write
   STATUS      current
   DESCRIPTION
       "-1:n/a
	   0:normal state
	   1:apply profile default"
   ::= {sispm10403166lPTPClockConfAndStatus 5 }

sispm10403166lEntryPTPTime OBJECT-TYPE
   SYNTAX      DisplayString
   MAX-ACCESS  read-only
   STATUS      current
   DESCRIPTION
       "Shows the actual PTP time with nanosecond resolution."
   ::= {sispm10403166lPTPClockConfAndStatus 6 }

sispm10403166lEntryClockAdjustmentMethod OBJECT-TYPE
   SYNTAX      DisplayString
   MAX-ACCESS  read-only
   STATUS      current
   DESCRIPTION
       "Shows the actual clock adjustment method. The method depends on the available hardware."
   ::= {sispm10403166lPTPClockConfAndStatus 7 }

sispm10403166lEntrySynchronizeToSystemClock OBJECT-TYPE
   SYNTAX      Integer32
   MAX-ACCESS  read-write
   STATUS      current
   DESCRIPTION
       "Activate this button to synchronize the System Clock to PTP Time.
	   1:Synchronize to system clock."
   ::= {sispm10403166lPTPClockConfAndStatus 8 }

sispm10403166lEntryClockCurrentDataSetstpRm OBJECT-TYPE
   SYNTAX      Integer32
   MAX-ACCESS  read-only
   STATUS      current
   DESCRIPTION
       "Steps Removed : It is the number of PTP clocks traversed from the grandmaster to the local slave clock."
   ::= {sispm10403166lPTPClockConfAndStatus 9 }

sispm10403166lEntryClockCurrentDataSetOffsetFromMaster OBJECT-TYPE
   SYNTAX      DisplayString
   MAX-ACCESS  read-only
   STATUS      current
   DESCRIPTION
       "Time difference between the master clock and the local slave clock, measured in ns."
   ::= {sispm10403166lPTPClockConfAndStatus 10 }

sispm10403166lEntryClockCurrentDataSetMeanPathDelay OBJECT-TYPE
   SYNTAX      DisplayString
   MAX-ACCESS  read-only
   STATUS      current
   DESCRIPTION
       "The mean propagation time for the link between the master and the local slave."
   ::= {sispm10403166lPTPClockConfAndStatus 11 }

sispm10403166lEntryClockCurrentDataSetSlavePort OBJECT-TYPE
   SYNTAX      Integer32
   MAX-ACCESS  read-only
   STATUS      current
   DESCRIPTION
       "Shows which port is in slave mode. The value is 0 if no ports are in slave mode."
   ::= {sispm10403166lPTPClockConfAndStatus 12 }

sispm10403166lEntryClockCurrentDataSetSlaveState OBJECT-TYPE
   SYNTAX      DisplayString
   MAX-ACCESS  read-only
   STATUS      current
   DESCRIPTION
       "Shows synchronization state of the slave."
   ::= {sispm10403166lPTPClockConfAndStatus 13 }

sispm10403166lEntryClockCurrentDataSetHoldover OBJECT-TYPE
   SYNTAX      DisplayString
   MAX-ACCESS  read-only
   STATUS      current
   DESCRIPTION
       "After the slave has been in Locked mode during the stabilization period,
	   this value shows the actual clock offset between the freerun and the actual holdover frequency,
	   the value is shown in parts pr billion (ppb).
	   During the stabilization period, the value is shown as N.A.
	   The stabilization period is 60 sec as default, it can be changed from the CLI interface."
   ::= {sispm10403166lPTPClockConfAndStatus 14 }

sispm10403166lEntryClockParentDataSetParentPortID OBJECT-TYPE
   SYNTAX      DisplayString
   MAX-ACCESS  read-only
   STATUS      current
   DESCRIPTION
       "Clock identity for the parent clock, if the local clock is not a slave, the value is the clocks own id."
   ::= {sispm10403166lPTPClockConfAndStatus 15 }

sispm10403166lEntryClockParentDataSetPort OBJECT-TYPE
   SYNTAX      Integer32
   MAX-ACCESS  read-only
   STATUS      current
   DESCRIPTION
       "Port Id for the parent master port"
   ::= {sispm10403166lPTPClockConfAndStatus 16 }

sispm10403166lEntryClockParentDataSetPStat OBJECT-TYPE
   SYNTAX      DisplayString
   MAX-ACCESS  read-only
   STATUS      current
   DESCRIPTION
       "Parents Stats (always false)."
   ::= {sispm10403166lPTPClockConfAndStatus 17 }

sispm10403166lEntryClockParentDataSetVar OBJECT-TYPE
   SYNTAX      Integer32
   MAX-ACCESS  read-only
   STATUS      current
   DESCRIPTION
       "It is observed parent offset scaled log variance"
   ::= {sispm10403166lPTPClockConfAndStatus 18 }

sispm10403166lEntryClockParentDataSetRate OBJECT-TYPE
   SYNTAX      Integer32
   MAX-ACCESS  read-only
   STATUS      current
   DESCRIPTION
       "Observed Parent Clock Phase Change Rate. i.e. the slave clocks rate offset compared to the master.
	   (unit = ns per s)."
   ::= {sispm10403166lPTPClockConfAndStatus 19 }

sispm10403166lEntryClockParentDataSetGrandMasterID OBJECT-TYPE
   SYNTAX      DisplayString
   MAX-ACCESS  read-only
   STATUS      current
   DESCRIPTION
       "Clock identity for the grand master clock, if the local clock is not a slave, the value is the clocks own id."
   ::= {sispm10403166lPTPClockConfAndStatus 20 }

sispm10403166lParentDataSetGrandMasterClockQuality OBJECT-TYPE
   SYNTAX      DisplayString
   MAX-ACCESS  read-only
   STATUS      current
   DESCRIPTION
       "The clock quality announced by the grand master (See description of Clock Default DataSet:Clock Quality)"
   ::= {sispm10403166lPTPClockConfAndStatus 21 }

sispm10403166lEntryClockParentDataSetPri1 OBJECT-TYPE
   SYNTAX      Integer32
   MAX-ACCESS  read-only
   STATUS      current
   DESCRIPTION
       "Clock priority 1 announced by the grand master"
   ::= {sispm10403166lPTPClockConfAndStatus 22 }

sispm10403166lEntryClockParentDataSetPri2 OBJECT-TYPE
   SYNTAX      Integer32
   MAX-ACCESS  read-only
   STATUS      current
   DESCRIPTION
       "Clock priority 2 announced by the grand master."
   ::= {sispm10403166lPTPClockConfAndStatus 23 }

sispm10403166lEntryClockDefaultDataSetClockID OBJECT-TYPE
   SYNTAX      Integer32
   MAX-ACCESS  read-only
   STATUS      current
   DESCRIPTION
       "An internal instance id (0..3)"
   ::= {sispm10403166lPTPClockConfAndStatus 24 }

sispm10403166lEntryClockDefaultDataSetDeviceType OBJECT-TYPE
   SYNTAX      DisplayString
   MAX-ACCESS  read-only
   STATUS      current
   DESCRIPTION
       "Indicates the Type of the Clock Instance. There are five Device Types.
		1. Ord-Bound - Clock's Device Type is Ordinary-Boundary Clock.
		2. P2p Transp - Clock's Device Type is Peer to Peer Transparent Clock.
		3. E2e Transp - Clock's Device Type is End to End Transparent Clock.
		4. Master Only - Clock's Device Type is Master Only.
		5. Slave Only - Clock's Device Type is Slave Only."
   ::= {sispm10403166lPTPClockConfAndStatus 25 }

sispm10403166lEntryClockDefaultDataSet2StepFlag OBJECT-TYPE
   SYNTAX      Integer32
   MAX-ACCESS  read-write
   STATUS      current
   DESCRIPTION
       "True if two-step Sync events and Pdelay_Resp events are used
	   0:false
	   1:true"
   ::= {sispm10403166lPTPClockConfAndStatus 26 }

sispm10403166lEntryClockDefaultDataSetPorts OBJECT-TYPE
   SYNTAX      Integer32
   MAX-ACCESS  read-only
   STATUS      current
   DESCRIPTION
       "The total number of physical ports in the node"
   ::= {sispm10403166lPTPClockConfAndStatus 27 }

sispm10403166lEntryClockDefaultDataSetClockIdentity OBJECT-TYPE
   SYNTAX      DisplayString
   MAX-ACCESS  read-only
   STATUS      current
   DESCRIPTION
       "It shows unique clock identifier"
   ::= {sispm10403166lPTPClockConfAndStatus 28 }

sispm10403166lEntryClockDefaultDataSetDom OBJECT-TYPE
   SYNTAX      Integer32
   MAX-ACCESS  read-write
   STATUS      current
   DESCRIPTION
       "Clock domain [0..127]."
   ::= {sispm10403166lPTPClockConfAndStatus 29 }

sispm10403166lEntryClockDefaultDataSetClockQuality OBJECT-TYPE
   SYNTAX      DisplayString
   MAX-ACCESS  read-only
   STATUS      current
   DESCRIPTION
       "The clock quality is determined by the system, and holds 3 parts: Clock Class, Clock Accuracy and OffsetScaledLog Variance as defined in IEEE1588.
The Clock Accuracy values are defined in IEEE1588 table 6 (Currently the clock Accuracy is set to 'Unknown' as default)."
   ::= {sispm10403166lPTPClockConfAndStatus 30 }

sispm10403166lEntryClockDefaultDataSetPri1 OBJECT-TYPE
   SYNTAX      Integer32
   MAX-ACCESS  read-write
   STATUS      current
   DESCRIPTION
       "Clock priority 1 [0..255] used by the BMC master select algorithm."
   ::= {sispm10403166lPTPClockConfAndStatus 31 }

sispm10403166lEntryClockDefaultDataSetPri2 OBJECT-TYPE
   SYNTAX      Integer32
   MAX-ACCESS  read-write
   STATUS      current
   DESCRIPTION
       "Clock priority 2 [0..255] used by the BMC master select algorithm."
   ::= {sispm10403166lPTPClockConfAndStatus 32 }

sispm10403166lEntryClockDefaultDataSetProtocol OBJECT-TYPE
   SYNTAX      Integer32
   MAX-ACCESS  read-write
   STATUS      current
   DESCRIPTION
       "0:Ethernet
	   1:Ethernet Mixed
	   2:IP4Multi
	   3:IP4Mixed
	   4:IP4Uni
	   5:OAM"
   ::= {sispm10403166lPTPClockConfAndStatus 33 }

sispm10403166lEntryClockDefaultDataSetOneWay OBJECT-TYPE
   SYNTAX      Integer32
   MAX-ACCESS  read-write
   STATUS      current
   DESCRIPTION
       "If true, one way measurements are used.
	   This parameter applies only to a slave.
	   In one-way mode no delay measurements are performed, i.e. this is applicable only if frequency synchronization is needed.
	   The master always responds to delay requests.
	   0:false
	   1:true"
   ::= {sispm10403166lPTPClockConfAndStatus 34 }

sispm10403166lEntryClockDefaultDataSetVLANTagEnable OBJECT-TYPE
   SYNTAX      Integer32
   MAX-ACCESS  read-write
   STATUS      current
   DESCRIPTION
       "The VLAN Tag Enable parameter is ignored, because the tagging is controlled by the VLAN configuration.
	   0:false
	   1:true"
   ::= {sispm10403166lPTPClockConfAndStatus 35 }

sispm10403166lEntryClockDefaultDataSetVID OBJECT-TYPE
   SYNTAX      Integer32
   MAX-ACCESS  read-write
   STATUS      current
   DESCRIPTION
       "TVLAN Identifier used for tagging the VLAN packets.
	   range:1-4095"
   ::= {sispm10403166lPTPClockConfAndStatus 36 }

sispm10403166lEntryClockDefaultDataSetPCP OBJECT-TYPE
   SYNTAX      Integer32
   MAX-ACCESS  read-write
   STATUS      current
   DESCRIPTION
       "Priority Code Point value used for PTP frames. range:0-7"
   ::= {sispm10403166lPTPClockConfAndStatus 37 }

sispm10403166lEntryClockDefaultDataSetDSCP OBJECT-TYPE
   SYNTAX      Integer32
   MAX-ACCESS  read-write
   STATUS      current
   DESCRIPTION
       ""
   ::= {sispm10403166lPTPClockConfAndStatus 38 }

sispm10403166lEntryClockTimePropertiesDataSetUtcOffset OBJECT-TYPE
   SYNTAX      Integer32
   MAX-ACCESS  read-write
   STATUS      current
   DESCRIPTION
       "range: 0-10000"
   ::= {sispm10403166lPTPClockConfAndStatus 39 }

sispm10403166lEntryClockTimePropertiesDataSetValid OBJECT-TYPE
   SYNTAX      Integer32
   MAX-ACCESS  read-write
   STATUS      current
   DESCRIPTION
       "0:false
	   1:true"
   ::= {sispm10403166lPTPClockConfAndStatus 40 }

sispm10403166lEntryClockTimePropertiesDataSetLeap59 OBJECT-TYPE
   SYNTAX      Integer32
   MAX-ACCESS  read-write
   STATUS      current
   DESCRIPTION
       "0:false
	   1:true"
   ::= {sispm10403166lPTPClockConfAndStatus 41 }

sispm10403166lEntryClockTimePropertiesDataSetLeap61 OBJECT-TYPE
   SYNTAX      Integer32
   MAX-ACCESS  read-write
   STATUS      current
   DESCRIPTION
       "0:false
	   1:true"
   ::= {sispm10403166lPTPClockConfAndStatus 42 }

sispm10403166lEntryClockTimePropertiesDataSetTimeTrac OBJECT-TYPE
   SYNTAX      Integer32
   MAX-ACCESS  read-write
   STATUS      current
   DESCRIPTION
       "0:false
	   1:true"
   ::= {sispm10403166lPTPClockConfAndStatus 43 }

sispm10403166lEntryClockTimePropertiesDataSetFreqTrac OBJECT-TYPE
   SYNTAX      Integer32
   MAX-ACCESS  read-write
   STATUS      current
   DESCRIPTION
       "0:false
	   1:true"
   ::= {sispm10403166lPTPClockConfAndStatus 44 }

sispm10403166lTimePropertiesDataSetPTPTimeScale OBJECT-TYPE
   SYNTAX      Integer32
   MAX-ACCESS  read-write
   STATUS      current
   DESCRIPTION
       "0:false
	   1:true"
   ::= {sispm10403166lPTPClockConfAndStatus 45 }

sispm10403166lEntryClockTimePropertiesDataSetTimeSource OBJECT-TYPE
   SYNTAX      Integer32
   MAX-ACCESS  read-write
   STATUS      current
   DESCRIPTION
       "range: 0-255"
   ::= {sispm10403166lPTPClockConfAndStatus 46 }

sispm10403166lEntryFilterParametersFilterType OBJECT-TYPE
   SYNTAX      Integer32
   MAX-ACCESS  read-write
   STATUS      current
   DESCRIPTION
       "Shows the filter type used which can be either the basic filter or an advanced filter that can be configured to use only a fraction of the packets received
	   (i.e. the packets that have experienced the least latency).
	   0:BASIC"
   ::= {sispm10403166lPTPClockConfAndStatus 47 }

sispm10403166lEntryFilterParametersDelayFilter OBJECT-TYPE
   SYNTAX      Integer32
   MAX-ACCESS  read-write
   STATUS      current
   DESCRIPTION
       "range:0-6"
   ::= {sispm10403166lPTPClockConfAndStatus 48 }

sispm10403166lEntryFilterParametersPeriod OBJECT-TYPE
   SYNTAX      Integer32
   MAX-ACCESS  read-write
   STATUS      current
   DESCRIPTION
       "range:1-10000"
   ::= {sispm10403166lPTPClockConfAndStatus 49 }

sispm10403166lEntryFilterParametersDist OBJECT-TYPE
   SYNTAX      Integer32
   MAX-ACCESS  read-write
   STATUS      current
   DESCRIPTION
       "range:1-10"
   ::= {sispm10403166lPTPClockConfAndStatus 50 }

sispm10403166lEntryServoParametersDisplay OBJECT-TYPE
   SYNTAX      Integer32
   MAX-ACCESS  read-write
   STATUS      current
   DESCRIPTION
       "If true then Offset From Master, MeanPathDelay and clockAdjustment are logged on the debug terminal
	   0:false
	   1:true"
   ::= {sispm10403166lPTPClockConfAndStatus 51 }

sispm10403166lEntryServoParametersPEnable OBJECT-TYPE
   SYNTAX      Integer32
   MAX-ACCESS  read-write
   STATUS      current
   DESCRIPTION
       "If true the P part of the algorithm is included
	   0:false
	   1:true"
   ::= {sispm10403166lPTPClockConfAndStatus 52 }

sispm10403166lEntryServoParametersIEnable OBJECT-TYPE
   SYNTAX      Integer32
   MAX-ACCESS  read-write
   STATUS      current
   DESCRIPTION
       "If true the I part of the algorithm is included
	   0:false
	   1:true"
   ::= {sispm10403166lPTPClockConfAndStatus 53 }

sispm10403166lEntryServoParametersDEnable OBJECT-TYPE
   SYNTAX      Integer32
   MAX-ACCESS  read-write
   STATUS      current
   DESCRIPTION
       "If true the D part of the algorithm is included
	   0:false
	   1:true"
   ::= {sispm10403166lPTPClockConfAndStatus 54 }

sispm10403166lEntryServoParametersPConstant OBJECT-TYPE
   SYNTAX      Integer32
   MAX-ACCESS  read-write
   STATUS      current
   DESCRIPTION
       "range:0-1000"
   ::= {sispm10403166lPTPClockConfAndStatus 55 }

sispm10403166lEntryServoParametersIConstant OBJECT-TYPE
   SYNTAX      Integer32
   MAX-ACCESS  read-write
   STATUS      current
   DESCRIPTION
       "range:0-10000"
   ::= {sispm10403166lPTPClockConfAndStatus 56 }

sispm10403166lEntryServoParametersDConstant OBJECT-TYPE
   SYNTAX      Integer32
   MAX-ACCESS  read-write
   STATUS      current
   DESCRIPTION
       "range:0-1000"
   ::= {sispm10403166lPTPClockConfAndStatus 57 }


sispm10403166lPTPClockPortDataSetConfTable OBJECT-TYPE
   SYNTAX      SEQUENCE OF SISPM10403166LPTPClockPortDataSetConfEntry
   MAX-ACCESS  not-accessible
   STATUS      current
   DESCRIPTION
       " "
   ::= { sispm10403166lPTP 8 }

sispm10403166lPTPClockPortDataSetConfEntry OBJECT-TYPE
   SYNTAX      SISPM10403166LPTPClockPortDataSetConfEntry
   MAX-ACCESS  not-accessible
   STATUS      current
   DESCRIPTION
       " "
   INDEX    { sispm10403166lPTPClockPortDataSetConfPort  }
   ::= { sispm10403166lPTPClockPortDataSetConfTable 1 }

SISPM10403166LPTPClockPortDataSetConfEntry ::= SEQUENCE {
   sispm10403166lPTPClockPortDataSetConfPort               Integer32,
   sispm10403166lPTPClockConfEntryPortConfEnable           Integer32,
   sispm10403166lPTPClockConfEntryPortConfStat             DisplayString,
   sispm10403166lPTPClockConfEntryPortConfMDR              Integer32,
   sispm10403166lPTPClockConfEntryPortConfPeerMeanPathDel  DisplayString,
   sispm10403166lPTPClockConfEntryPortConfAnv              Integer32,
   sispm10403166lPTPClockConfEntryPortConfATo              Integer32,
   sispm10403166lPTPClockConfEntryPortConfSyv              Integer32,
   sispm10403166lPTPClockConfEntryPortConfDlm              Integer32,
   sispm10403166lPTPClockConfEntryPortConfMPR              Integer32,
   sispm10403166lPTPClockConfEntryPortConfDelayAsymmetry   Integer32,
   sispm10403166lPTPClockConfEntryPortConfIngressLatency   Integer32,
   sispm10403166lPTPClockConfEntryPortConfEgressLatency    Integer32,
   sispm10403166lPTPClockConfEntryPortConfVersion          Integer32
}

sispm10403166lPTPClockPortDataSetConfPort OBJECT-TYPE
   SYNTAX      Integer32(1..65535)
   MAX-ACCESS  not-accessible
   STATUS      current
   DESCRIPTION
       "Index"
   ::= { sispm10403166lPTPClockPortDataSetConfEntry 1 }

sispm10403166lPTPClockConfEntryPortConfEnable OBJECT-TYPE
   SYNTAX      Integer32
   MAX-ACCESS  read-write
   STATUS      current
   DESCRIPTION
       "0:false
	   1:true"
   ::= { sispm10403166lPTPClockPortDataSetConfEntry 2 }

sispm10403166lPTPClockConfEntryPortConfStat OBJECT-TYPE
   SYNTAX      DisplayString
   MAX-ACCESS  read-only
   STATUS      current
   DESCRIPTION
       "Dynamic member portState: Current state of the port."
   ::= { sispm10403166lPTPClockPortDataSetConfEntry 3 }

sispm10403166lPTPClockConfEntryPortConfMDR OBJECT-TYPE
   SYNTAX      Integer32
   MAX-ACCESS  read-only
   STATUS      current
   DESCRIPTION
       "Dynamic member log Min Delay Req Interval: The delay request interval announced by the master."
   ::= { sispm10403166lPTPClockPortDataSetConfEntry 4 }

sispm10403166lPTPClockConfEntryPortConfPeerMeanPathDel OBJECT-TYPE
   SYNTAX      DisplayString
   MAX-ACCESS  read-only
   STATUS      current
   DESCRIPTION
       "The path delay measured by the port in P2P mode. In E2E mode this value is 0"
   ::= { sispm10403166lPTPClockPortDataSetConfEntry 5 }



sispm10403166lPTPClockConfEntryPortConfAnv OBJECT-TYPE
   SYNTAX      Integer32
   MAX-ACCESS  read-write
   STATUS      current
   DESCRIPTION
       "The interval for issuing announce messages in master state. Range is -3 to 4."
   ::= { sispm10403166lPTPClockPortDataSetConfEntry 6 }

sispm10403166lPTPClockConfEntryPortConfATo OBJECT-TYPE
   SYNTAX      Integer32
   MAX-ACCESS  read-write
   STATUS      current
   DESCRIPTION
       "The timeout for receiving announce messages on the port. Range is 1 to 10."
   ::= { sispm10403166lPTPClockPortDataSetConfEntry 7 }

sispm10403166lPTPClockConfEntryPortConfSyv OBJECT-TYPE
   SYNTAX      Integer32
   MAX-ACCESS  read-write
   STATUS      current
   DESCRIPTION
       "The interval for issuing sync messages in master. Range is -7 to 4."
   ::= { sispm10403166lPTPClockPortDataSetConfEntry 8 }

sispm10403166lPTPClockConfEntryPortConfDlm OBJECT-TYPE
   SYNTAX      Integer32
   MAX-ACCESS  read-write
   STATUS      current
   DESCRIPTION
       "Configurable member delayMechanism: The delay mechanism used for the port:
		e2e	End to end delay measurement
		p2p	Peer to peer delay measurement.
		Can be defined per port in an Ordinary/Boundary clock.
		In a transparent clock all ports use the same delay mechanism, determined by the clock type.
		1:e2e
		2:p2p"
   ::= { sispm10403166lPTPClockPortDataSetConfEntry 9 }

sispm10403166lPTPClockConfEntryPortConfMPR OBJECT-TYPE
   SYNTAX      Integer32
   MAX-ACCESS  read-write
   STATUS      current
   DESCRIPTION
       "The interval for issuing Delay_Req messages for the port in E2e mode. This value is announced from the master to the slave in an announce message. The value is reflected in the MDR field in the Slave
The interval for issuing Pdelay_Req messages for the port in P2P mode
Note: The interpretation of this parameter has changed from release 2.40. In earlier versions the value was interpreted relative to the Sync interval, this was a violation of the standard, so now the value is interpreted as an interval. I.e. MPR = 0 => 1 Delay_Req pr sec, independent of the Sync rate.
Range is -7 to 5."
   ::= { sispm10403166lPTPClockPortDataSetConfEntry 10 }

sispm10403166lPTPClockConfEntryPortConfDelayAsymmetry OBJECT-TYPE
   SYNTAX      Integer32
   MAX-ACCESS  read-write
   STATUS      current
   DESCRIPTION
       "If the transmission delay for a link in not symmetric, the asymmetry can be configured here, see IEEE 1588 Section 7.4.2 Communication path asymmetry
Range is -100000 to 100000."
   ::= { sispm10403166lPTPClockPortDataSetConfEntry 11 }

sispm10403166lPTPClockConfEntryPortConfIngressLatency OBJECT-TYPE
   SYNTAX      Integer32
   MAX-ACCESS  read-write
   STATUS      current
   DESCRIPTION
       "Ingress latency measured in ns, as defined in IEEE 1588 Section 7.3.4.2.
Range is -100000 to 100000."
   ::= { sispm10403166lPTPClockPortDataSetConfEntry 12 }

sispm10403166lPTPClockConfEntryPortConfEgressLatency OBJECT-TYPE
   SYNTAX      Integer32
   MAX-ACCESS  read-write
   STATUS      current
   DESCRIPTION
       "Egress latency measured in ns, as defined in IEEE 1588 Section 7.3.4.2.
Range is -100000 to 100000."
   ::= { sispm10403166lPTPClockPortDataSetConfEntry 13 }

sispm10403166lPTPClockConfEntryPortConfVersion OBJECT-TYPE
   SYNTAX      Integer32
   MAX-ACCESS  read-only
   STATUS      current
   DESCRIPTION
       "The current implementation only supports PTP version 2"
   ::= { sispm10403166lPTPClockPortDataSetConfEntry 14 }


sispm10403166lPTPClockUnicastSlaveConfTable OBJECT-TYPE
   SYNTAX      SEQUENCE OF SISPM10403166LPTPClockUnicastSlaveConfEntry
   MAX-ACCESS  not-accessible
   STATUS      current
   DESCRIPTION
       " "
   ::= { sispm10403166lPTP 9 }

sispm10403166lPTPClockUnicastSlaveConfEntry OBJECT-TYPE
   SYNTAX      SISPM10403166LPTPClockUnicastSlaveConfEntry
   MAX-ACCESS  not-accessible
   STATUS      current
   DESCRIPTION
       " "
   INDEX    { sispm10403166lPTPClockConfEntryUnicastSlaveConfIndex  }
   ::= { sispm10403166lPTPClockUnicastSlaveConfTable 1 }

SISPM10403166LPTPClockUnicastSlaveConfEntry ::= SEQUENCE {
   sispm10403166lPTPClockConfEntryUnicastSlaveConfIndex              Integer32,
   sispm10403166lPTPClockConfEntryUnicastSlaveConfDuration           Integer32,
   sispm10403166lPTPClockConfEntryUnicastSlaveConfIPAddress          IpAddress,
   sispm10403166lPTPClockConfEntryUnicastSlaveConfGrant              Integer32,
   sispm10403166lPTPClockConfEntryUnicastSlaveConfCommState          DisplayString
}

sispm10403166lPTPClockConfEntryUnicastSlaveConfIndex OBJECT-TYPE
   SYNTAX      Integer32(1..65535)
   MAX-ACCESS  not-accessible
   STATUS      current
   DESCRIPTION
       "Index"
   ::= { sispm10403166lPTPClockUnicastSlaveConfEntry 1 }

sispm10403166lPTPClockConfEntryUnicastSlaveConfDuration OBJECT-TYPE
   SYNTAX      Integer32
   MAX-ACCESS  read-write
   STATUS      current
   DESCRIPTION
       "The number of seconds a master is requested to send Announce/Sync messages.
	   The request is repeated from the slave each Duration/4 seconds.
	   range:10-1000"
   ::= { sispm10403166lPTPClockUnicastSlaveConfEntry 2 }

sispm10403166lPTPClockConfEntryUnicastSlaveConfIPAddress OBJECT-TYPE
   SYNTAX      IpAddress
   MAX-ACCESS  read-write
   STATUS      current
   DESCRIPTION
       "IPv4 Address of the Master clock"
   ::= { sispm10403166lPTPClockUnicastSlaveConfEntry 3 }

sispm10403166lPTPClockConfEntryUnicastSlaveConfGrant OBJECT-TYPE
   SYNTAX      Integer32
   MAX-ACCESS  read-only
   STATUS      current
   DESCRIPTION
       "The granted repetition period for the sync message"
   ::= { sispm10403166lPTPClockUnicastSlaveConfEntry 4 }

sispm10403166lPTPClockConfEntryUnicastSlaveConfCommState OBJECT-TYPE
   SYNTAX      DisplayString
   MAX-ACCESS  read-only
   STATUS      current
   DESCRIPTION
       "The state of the communication with the master, possible values are:
		IDLE : The entry is not in use.
		INIT : Announce is sent to the master (Waiting for a response).
		CONN : The master has responded.
		SELL : The assigned master is selected as current master.
		SYNC : The master is sending Sync messages."
   ::= { sispm10403166lPTPClockUnicastSlaveConfEntry 5 }
-- =======================================================================================================================
sispm10403166lETHLINKOAM    OBJECT IDENTIFIER ::= { sispm10403166lConfiguration 29 }

sispm10403166lEthLinkOAMPortConfTable OBJECT-TYPE
   SYNTAX      SEQUENCE OF SISPM10403166LEthLinkOAMPortConfEntry
   MAX-ACCESS  not-accessible
   STATUS      current
   DESCRIPTION
       " "
   ::= { sispm10403166lETHLINKOAM 1 }

sispm10403166lEthLinkOAMPortConfEntry OBJECT-TYPE
   SYNTAX      SISPM10403166LEthLinkOAMPortConfEntry
   MAX-ACCESS  not-accessible
   STATUS      current
   DESCRIPTION
       " "
   INDEX    { sispm10403166lEthLinkOAMPortConfIndex  }
   ::= { sispm10403166lEthLinkOAMPortConfTable 1 }

SISPM10403166LEthLinkOAMPortConfEntry ::= SEQUENCE {
   sispm10403166lEthLinkOAMPortConfIndex               Integer32,
   sispm10403166lEthLinkOAMPortConfOAMEnable           Integer32,
   sispm10403166lEthLinkOAMPortConfOAMMode             Integer32,
   sispm10403166lEthLinkOAMPortConfLoopbackSupport     Integer32,
   sispm10403166lEthLinkOAMPortConfLinkMonitorSupport  Integer32,
   sispm10403166lEthLinkOAMPortConfMIBRetrievalSupport Integer32,
   sispm10403166lEthLinkOAMPortConfLoopbackOperation   Integer32
}

sispm10403166lEthLinkOAMPortConfIndex OBJECT-TYPE
   SYNTAX      Integer32(1..65535)
   MAX-ACCESS  not-accessible
   STATUS      current
   DESCRIPTION
       "Index"
   ::= { sispm10403166lEthLinkOAMPortConfEntry 1 }

sispm10403166lEthLinkOAMPortConfOAMEnable OBJECT-TYPE
   SYNTAX      Integer32
   MAX-ACCESS  read-write
   STATUS      current
   DESCRIPTION
       "Controls whether Link OAM is enabled on this switch port.
	   Enabling Link OAM provides the network operators the ability to monitor the health of the network and
	   quickly determine the location of failing links or fault conditions.
	   0:disable
	   1:enable"
   ::= { sispm10403166lEthLinkOAMPortConfEntry 2 }

sispm10403166lEthLinkOAMPortConfOAMMode OBJECT-TYPE
   SYNTAX      Integer32
   MAX-ACCESS  read-write
   STATUS      current
   DESCRIPTION
       "Configures the OAM Mode as Active or Passive. The default mode is Passive.
	   0:Passive mode
	   1:Active mode"
   ::= { sispm10403166lEthLinkOAMPortConfEntry 3 }

sispm10403166lEthLinkOAMPortConfLoopbackSupport OBJECT-TYPE
   SYNTAX      Integer32
   MAX-ACCESS  read-write
   STATUS      current
   DESCRIPTION
       "Controls whether the loopback support is enabled for the switch port.
	   0:disable
	   1:enable"
   ::= { sispm10403166lEthLinkOAMPortConfEntry 4 }

sispm10403166lEthLinkOAMPortConfLinkMonitorSupport OBJECT-TYPE
   SYNTAX      Integer32
   MAX-ACCESS  read-write
   STATUS      current
   DESCRIPTION
       "Controls whether the Link Monitor support is enabled for the switch port.
	   0:disable
	   1:enable"
   ::= { sispm10403166lEthLinkOAMPortConfEntry 5 }

sispm10403166lEthLinkOAMPortConfMIBRetrievalSupport OBJECT-TYPE
   SYNTAX      Integer32
   MAX-ACCESS  read-write
   STATUS      current
   DESCRIPTION
       "Controls whether the MIB Retrieval Support is enabled for the switch port.
	   0:disable
	   1:enable"
   ::= { sispm10403166lEthLinkOAMPortConfEntry 6 }

sispm10403166lEthLinkOAMPortConfLoopbackOperation OBJECT-TYPE
   SYNTAX      Integer32
   MAX-ACCESS  read-write
   STATUS      current
   DESCRIPTION
       "If the Loopback support is enabled, enabling this field will start a loopback operation for the port.
	   0:disable
	   1:enable"
   ::= { sispm10403166lEthLinkOAMPortConfEntry 7 }



sispm10403166lEthLinkOAMPortDetailStatusTable OBJECT-TYPE
   SYNTAX      SEQUENCE OF SISPM10403166LEthLinkOAMPortDetailStatusEntry
   MAX-ACCESS  not-accessible
   STATUS      current
   DESCRIPTION
       "Eth Link OAM Port Detail Status table"
   ::= { sispm10403166lETHLINKOAM 2 }

sispm10403166lEthLinkOAMPortDetailStatusEntry OBJECT-TYPE
   SYNTAX      SISPM10403166LEthLinkOAMPortDetailStatusEntry
   MAX-ACCESS  not-accessible
   STATUS      current
   DESCRIPTION
       "Eth Link OAM Port Detail Status entry"
   INDEX    { sispm10403166lEthLinkOAMPortDetailStatusIndex  }
   ::= { sispm10403166lEthLinkOAMPortDetailStatusTable 1 }

SISPM10403166LEthLinkOAMPortDetailStatusEntry ::= SEQUENCE {
   sispm10403166lEthLinkOAMPortDetailStatusIndex                       Integer32,
   sispm10403166lEthLinkOAMPortPDUPermission                           DisplayString,
   sispm10403166lEthLinkOAMPortDiscoveryState                          DisplayString,
   sispm10403166lEthLinkOAMPortPeerMACAddress                          DisplayString,
   sispm10403166lEthLinkOAMPortLocalMode                               DisplayString,
   sispm10403166lEthLinkOAMPortLocalUnidirectionalOperationSupport     DisplayString,
   sispm10403166lEthLinkOAMPortLocalRemoteLoopbackSupport              DisplayString,
   sispm10403166lEthLinkOAMPortLocalLinkMonitoringSupport              DisplayString,
   sispm10403166lEthLinkOAMPortLocalMIBRetrievalSupport                DisplayString,
   sispm10403166lEthLinkOAMPortLocalMTUSize                            Integer32,
   sispm10403166lEthLinkOAMPortLocalMultiplexerState                   DisplayString,
   sispm10403166lEthLinkOAMPortLocalParserState                        DisplayString,
   sispm10403166lEthLinkOAMPortLocalOrganizationalUniqueIdent          DisplayString,
   sispm10403166lEthLinkOAMPortLocalPDURevision                        Integer32,
   sispm10403166lEthLinkOAMPortPeerMode                                DisplayString,
   sispm10403166lEthLinkOAMPortPeerUnidirectionalOperationSupport      DisplayString,
   sispm10403166lEthLinkOAMPortPeerRemoteLoopbackSupport               DisplayString,
   sispm10403166lEthLinkOAMPortPeerLinkMonitoringSupport               DisplayString,
   sispm10403166lEthLinkOAMPortPeerMIBRetrievalSupport                 DisplayString,
   sispm10403166lEthLinkOAMPortPeerMTUSize                             DisplayString,
   sispm10403166lEthLinkOAMPortPeerMultiplexerState                    DisplayString,
   sispm10403166lEthLinkOAMPortPeerParserState                         DisplayString,
   sispm10403166lEthLinkOAMPortPeerOrganizationalUniqueIdent           DisplayString,
   sispm10403166lEthLinkOAMPortPDURevision                             DisplayString
}

sispm10403166lEthLinkOAMPortDetailStatusIndex OBJECT-TYPE
   SYNTAX      Integer32(1..65535)
   MAX-ACCESS  not-accessible
   STATUS      current
   DESCRIPTION
       "Index"
   ::= { sispm10403166lEthLinkOAMPortDetailStatusEntry 1 }

sispm10403166lEthLinkOAMPortPDUPermission OBJECT-TYPE
   SYNTAX      DisplayString
   MAX-ACCESS  read-only
   STATUS      current
   DESCRIPTION
       "This field is available only for the Local DTE.
	   It displays the current permission rules set for the local DTE.
	   Possible values are Link fault, Receive only, Information exchange only, ANY."
   ::= { sispm10403166lEthLinkOAMPortDetailStatusEntry 2 }

sispm10403166lEthLinkOAMPortDiscoveryState OBJECT-TYPE
   SYNTAX      DisplayString
   MAX-ACCESS  read-only
   STATUS      current
   DESCRIPTION
       "Displays the current state of the discovery process.
	   Possible states are Fault state, Active state, Passive state,
	   SEND_LOCAL_REMOTE_STATE, SEND_LOCAL_REMOTE_OK_STATE, SEND_ANY_STATE."
   ::= { sispm10403166lEthLinkOAMPortDetailStatusEntry 3 }

sispm10403166lEthLinkOAMPortPeerMACAddress OBJECT-TYPE
   SYNTAX      DisplayString
   MAX-ACCESS  read-only
   STATUS      current
   DESCRIPTION
       " "
   ::= { sispm10403166lEthLinkOAMPortDetailStatusEntry 4 }

sispm10403166lEthLinkOAMPortLocalMode OBJECT-TYPE
   SYNTAX      DisplayString
   MAX-ACCESS  read-only
   STATUS      current
   DESCRIPTION
       "The Mode in which the Link OAM is operating, Active or Passive."
   ::= { sispm10403166lEthLinkOAMPortDetailStatusEntry 5 }

sispm10403166lEthLinkOAMPortLocalUnidirectionalOperationSupport OBJECT-TYPE
   SYNTAX      DisplayString
   MAX-ACCESS  read-only
   STATUS      current
   DESCRIPTION
       "This feature is not available to be configured by the user. The status of this configuration is retrieved from the PHY."
   ::= { sispm10403166lEthLinkOAMPortDetailStatusEntry 6 }

sispm10403166lEthLinkOAMPortLocalRemoteLoopbackSupport OBJECT-TYPE
   SYNTAX      DisplayString
   MAX-ACCESS  read-only
   STATUS      current
   DESCRIPTION
       "If status is enabled, DTE is capable of OAM remote loopback mode."
   ::= { sispm10403166lEthLinkOAMPortDetailStatusEntry 7 }

sispm10403166lEthLinkOAMPortLocalLinkMonitoringSupport OBJECT-TYPE
   SYNTAX      DisplayString
   MAX-ACCESS  read-only
   STATUS      current
   DESCRIPTION
       "If status is enabled, DTE supports interpreting Link Events."
   ::= { sispm10403166lEthLinkOAMPortDetailStatusEntry 8 }

sispm10403166lEthLinkOAMPortLocalMIBRetrievalSupport OBJECT-TYPE
   SYNTAX      DisplayString
   MAX-ACCESS  read-only
   STATUS      current
   DESCRIPTION
       "If status ie enabled DTE supports sending Variable Response OAMPDUs."
   ::= { sispm10403166lEthLinkOAMPortDetailStatusEntry 9 }

sispm10403166lEthLinkOAMPortLocalMTUSize OBJECT-TYPE
   SYNTAX      Integer32
   MAX-ACCESS  read-only
   STATUS      current
   DESCRIPTION
       "It represents the largest OAMPDU, in octets, supported by the DTE.
	   This value is compared to the remotes Maximum PDU Size and the smaller of the two is used."
   ::= { sispm10403166lEthLinkOAMPortDetailStatusEntry 10 }

sispm10403166lEthLinkOAMPortLocalMultiplexerState OBJECT-TYPE
   SYNTAX      DisplayString
   MAX-ACCESS  read-only
   STATUS      current
   DESCRIPTION
       "When in forwarding state, the Device is forwarding non-OAMPDUs to the lower sublayer.
	   Incase of discarding, the device discards all the non-OAMPDU's."
   ::= { sispm10403166lEthLinkOAMPortDetailStatusEntry 11 }

sispm10403166lEthLinkOAMPortLocalParserState OBJECT-TYPE
   SYNTAX      DisplayString
   MAX-ACCESS  read-only
   STATUS      current
   DESCRIPTION
       "When in forwarding state, Device is forwarding non-OAMPDUs to higher sublayer.
	   When in loopback, Device is looping back non-OAMPDUs to the lower sublayer.
	   When in discarding state, Device is discarding non-OAMPDUs."
   ::= { sispm10403166lEthLinkOAMPortDetailStatusEntry 12 }

sispm10403166lEthLinkOAMPortLocalOrganizationalUniqueIdent OBJECT-TYPE
   SYNTAX      DisplayString
   MAX-ACCESS  read-only
   STATUS      current
   DESCRIPTION
       "24-bit Organizationally Unique Identifier of the vendor."
   ::= { sispm10403166lEthLinkOAMPortDetailStatusEntry 13 }

sispm10403166lEthLinkOAMPortLocalPDURevision OBJECT-TYPE
   SYNTAX      Integer32
   MAX-ACCESS  read-only
   STATUS      current
   DESCRIPTION
       "It indicates the current revision of the Information TLV.
	   The value of this field shall start at zero and be incremented each time something in the Information TLV changes.
	   Upon reception of an Information TLV from a peer, an OAM client may use this field to decide if it needs to be processed
	   (an Information TLV that is identical to the previous Information TLV doesn't need to be parsed as nothing in it has changed)."
   ::= { sispm10403166lEthLinkOAMPortDetailStatusEntry 14 }

sispm10403166lEthLinkOAMPortPeerMode OBJECT-TYPE
   SYNTAX      DisplayString
   MAX-ACCESS  read-only
   STATUS      current
   DESCRIPTION
       "The Mode in which the Link OAM is operating, Active or Passive."
   ::= { sispm10403166lEthLinkOAMPortDetailStatusEntry 15 }

sispm10403166lEthLinkOAMPortPeerUnidirectionalOperationSupport OBJECT-TYPE
   SYNTAX      DisplayString
   MAX-ACCESS  read-only
   STATUS      current
   DESCRIPTION
       "This feature is not available to be configured by the user.
	   The status of this configuration is retrieved from the PHY."
   ::= { sispm10403166lEthLinkOAMPortDetailStatusEntry 16 }

sispm10403166lEthLinkOAMPortPeerRemoteLoopbackSupport OBJECT-TYPE
   SYNTAX      DisplayString
   MAX-ACCESS  read-only
   STATUS      current
   DESCRIPTION
       "If status is enabled, DTE is capable of OAM remote loopback mode."
   ::= { sispm10403166lEthLinkOAMPortDetailStatusEntry 17 }

sispm10403166lEthLinkOAMPortPeerLinkMonitoringSupport OBJECT-TYPE
   SYNTAX      DisplayString
   MAX-ACCESS  read-only
   STATUS      current
   DESCRIPTION
       "If status is enabled, DTE supports interpreting Link Events."
   ::= { sispm10403166lEthLinkOAMPortDetailStatusEntry 18 }

sispm10403166lEthLinkOAMPortPeerMIBRetrievalSupport OBJECT-TYPE
   SYNTAX      DisplayString
   MAX-ACCESS  read-only
   STATUS      current
   DESCRIPTION
       "If status ie enabled DTE supports sending Variable Response OAMPDUs."
   ::= { sispm10403166lEthLinkOAMPortDetailStatusEntry 19 }

sispm10403166lEthLinkOAMPortPeerMTUSize OBJECT-TYPE
   SYNTAX      DisplayString
   MAX-ACCESS  read-only
   STATUS      current
   DESCRIPTION
       "It represents the largest OAMPDU, in octets, supported by the DTE.
	   This value is compared to the remotes Maximum PDU Size and the smaller of the two is used."
   ::= { sispm10403166lEthLinkOAMPortDetailStatusEntry 20 }

sispm10403166lEthLinkOAMPortPeerMultiplexerState OBJECT-TYPE
   SYNTAX      DisplayString
   MAX-ACCESS  read-only
   STATUS      current
   DESCRIPTION
       "When in forwarding state, the Device is forwarding non-OAMPDUs to the lower sublayer.
	   Incase of discarding, the device discards all the non-OAMPDU's."
   ::= { sispm10403166lEthLinkOAMPortDetailStatusEntry 21 }

sispm10403166lEthLinkOAMPortPeerParserState OBJECT-TYPE
   SYNTAX      DisplayString
   MAX-ACCESS  read-only
   STATUS      current
   DESCRIPTION
       "When in forwarding state, Device is forwarding non-OAMPDUs to higher sublayer.
	   When in loopback, Device is looping back non-OAMPDUs to the lower sublayer.
	   When in discarding state, Device is discarding non-OAMPDUs."
   ::= { sispm10403166lEthLinkOAMPortDetailStatusEntry 22 }

sispm10403166lEthLinkOAMPortPeerOrganizationalUniqueIdent OBJECT-TYPE
   SYNTAX      DisplayString
   MAX-ACCESS  read-only
   STATUS      current
   DESCRIPTION
       "24-bit Organizationally Unique Identifier of the vendor."
   ::= { sispm10403166lEthLinkOAMPortDetailStatusEntry 23 }

sispm10403166lEthLinkOAMPortPDURevision                              OBJECT-TYPE
   SYNTAX      DisplayString
   MAX-ACCESS  read-only
   STATUS      current
   DESCRIPTION
       "It indicates the current revision of the Information TLV.
	   The value of this field shall start at zero and be incremented each time something in the Information TLV changes.
	   Upon reception of an Information TLV from a peer, an OAM client may use this field to decide if it needs to be processed
	   (an Information TLV that is identical to the previous Information TLV doesn't need to be parsed as nothing in it has changed)."
   ::= { sispm10403166lEthLinkOAMPortDetailStatusEntry 24 }


sispm10403166lEthLinkOAMPortLinkEventConfTable OBJECT-TYPE
   SYNTAX      SEQUENCE OF SISPM10403166LEthLinkOAMPortLinkEventConfEntry
   MAX-ACCESS  not-accessible
   STATUS      current
   DESCRIPTION
       "Eth Link OAM Port Link Event Conf Table"
   ::= { sispm10403166lETHLINKOAM 3 }

sispm10403166lEthLinkOAMPortLinkEventConfEntry OBJECT-TYPE
   SYNTAX      SISPM10403166LEthLinkOAMPortLinkEventConfEntry
   MAX-ACCESS  not-accessible
   STATUS      current
   DESCRIPTION
       "Eth Link OAM Port Link Event Conf Entry"
   INDEX    { sispm10403166lEventConfIndex  }
   ::= { sispm10403166lEthLinkOAMPortLinkEventConfTable 1 }

SISPM10403166LEthLinkOAMPortLinkEventConfEntry ::= SEQUENCE {
   sispm10403166lEventConfIndex                                 Integer32,
   sispm10403166lEventConfErrorFrameEventErrorWindow            Integer32,
   sispm10403166lEventConfErrorFrameEventErrorThreshold         Integer32,
   sispm10403166lEventConfSymbolPeriodErrorEventErrorWindow     Integer32,
   sispm10403166lEventConfSymbolPeriodErrorEventErrorThreshold  Integer32,
   sispm10403166lEventConfSecondsSummaryEventErrorWindow        Integer32,
   sispm10403166lEventConfSecondsSummaryEventErrorThreshold     Integer32
}

sispm10403166lEventConfIndex OBJECT-TYPE
   SYNTAX      Integer32(1..65535)
   MAX-ACCESS  not-accessible
   STATUS      current
   DESCRIPTION
       "Index"
   ::= { sispm10403166lEthLinkOAMPortLinkEventConfEntry 1 }

sispm10403166lEventConfErrorFrameEventErrorWindow OBJECT-TYPE
   SYNTAX      Integer32
   MAX-ACCESS  read-write
   STATUS      current
   DESCRIPTION
       "The Errored Frame Event counts the number of errored frames detected during the specified period.
	   Represents the window period in the order of 1 sec for the observation of various link events.
	   range: 1-60"
   ::= { sispm10403166lEthLinkOAMPortLinkEventConfEntry 2 }

sispm10403166lEventConfErrorFrameEventErrorThreshold OBJECT-TYPE
   SYNTAX      Integer32
   MAX-ACCESS  read-write
   STATUS      current
   DESCRIPTION
       "The Errored Frame Event counts the number of errored frames detected during the specified period.
	   Represents the threshold value for the window period for the appropriate Link event so as to notify the peer of this error.
	   range:0-0xffffffff"
   ::= { sispm10403166lEthLinkOAMPortLinkEventConfEntry 3 }

sispm10403166lEventConfSymbolPeriodErrorEventErrorWindow OBJECT-TYPE
   SYNTAX      Integer32
   MAX-ACCESS  read-write
   STATUS      current
   DESCRIPTION
       "The Errored Symbol Period Event counts the number of symbol errors that occurred during the specified period.
	   Represents the window period in the order of 1 sec for the observation of various link events.
	   range: 1-60"
   ::= { sispm10403166lEthLinkOAMPortLinkEventConfEntry 4 }

sispm10403166lEventConfSymbolPeriodErrorEventErrorThreshold OBJECT-TYPE
   SYNTAX      Integer32
   MAX-ACCESS  read-write
   STATUS      current
   DESCRIPTION
       "The Errored Symbol Period Event counts the number of symbol errors that occurred during the specified period.
	   Represents the threshold value for the window period for the appropriate Link event so as to notify the peer of this error.
	   range:0-0xffffffff"
   ::= { sispm10403166lEthLinkOAMPortLinkEventConfEntry 5 }

sispm10403166lEventConfSecondsSummaryEventErrorWindow OBJECT-TYPE
   SYNTAX      Integer32
   MAX-ACCESS  read-write
   STATUS      current
   DESCRIPTION
       "The Errored Frame Seconds Summary Event TLV counts the number of errored frame seconds that occurred during the specified period.
	   Represents the window period in the order of 1 sec for the observation of various link events.
	   range: 10-900"
   ::= { sispm10403166lEthLinkOAMPortLinkEventConfEntry 6 }

sispm10403166lEventConfSecondsSummaryEventErrorThreshold OBJECT-TYPE
   SYNTAX      Integer32
   MAX-ACCESS  read-write
   STATUS      current
   DESCRIPTION
       "The Errored Frame Seconds Summary Event TLV counts the number of errored frame seconds that occurred during the specified period.
	   Represents the threshold value for the window period for the appropriate Link event so as to notify the peer of this error.
	   range:0-0xffff"
   ::= { sispm10403166lEthLinkOAMPortLinkEventConfEntry 7 }




sispm10403166lEthLinkOAMPortDetailedStatisticsTable OBJECT-TYPE
   SYNTAX      SEQUENCE OF SISPM10403166LEthLinkOAMPortDetailedStatisticsEntry
   MAX-ACCESS  not-accessible
   STATUS      current
   DESCRIPTION
       "Eth Link OAM Port Detailed Statistics Table"
   ::= { sispm10403166lETHLINKOAM 4 }

sispm10403166lEthLinkOAMPortDetailedStatisticsEntry OBJECT-TYPE
   SYNTAX      SISPM10403166LEthLinkOAMPortDetailedStatisticsEntry
   MAX-ACCESS  not-accessible
   STATUS      current
   DESCRIPTION
       "Eth Link OAM Port Detailed Statistics Entry"
   INDEX    { sispm10403166lStatisticsIndex  }
   ::= { sispm10403166lEthLinkOAMPortDetailedStatisticsTable 1 }

SISPM10403166LEthLinkOAMPortDetailedStatisticsEntry ::= SEQUENCE {
   sispm10403166lStatisticsIndex                             Integer32,
   sispm10403166lStatisticsRxOAMInformationPDUs              Integer32,
   sispm10403166lStatisticsRxUniqueErrorEventNotification    Integer32,
   sispm10403166lStatisticsRxDuplicateErrorEventNotification Integer32,
   sispm10403166lStatisticsRxLoopbackControl                 Integer32,
   sispm10403166lStatisticsRxVariableRequest                 Integer32,
   sispm10403166lStatisticsRxVariableResponse                Integer32,
   sispm10403166lStatisticsRxOrgSpecificPDUs                 Integer32,
   sispm10403166lStatisticsRxUnsupportedCodes                Integer32,
   sispm10403166lStatisticsRxLinkFaultPDUs                   Integer32,
   sispm10403166lStatisticsRxDyingGasp                       Integer32,
   sispm10403166lStatisticsRxCriticalEventPDUs               Integer32,
   sispm10403166lStatisticsTxOAMInformationPDUs              Integer32,
   sispm10403166lStatisticsTxUniqueErrorEventNotification    Integer32,
   sispm10403166lStatisticsTxDuplicateErrorEventNotification Integer32,
   sispm10403166lStatisticsTxLoopbackControl                 Integer32,
   sispm10403166lStatisticsTxVariableRequest                 Integer32,
   sispm10403166lStatisticsTxVariableResponse                Integer32,
   sispm10403166lStatisticsTxOrgSpecificPDUs                 Integer32,
   sispm10403166lStatisticsTxUnsupportedCodes                Integer32,
   sispm10403166lStatisticsTxLinkFaultPDUs                   Integer32,
   sispm10403166lStatisticsTxDyingGasp                       Integer32,
   sispm10403166lStatisticsTxCriticalEventPDUs               Integer32,
   sispm10403166lStatisticsClear                             Integer32
}

sispm10403166lStatisticsIndex OBJECT-TYPE
   SYNTAX      Integer32(1..65535)
   MAX-ACCESS  not-accessible
   STATUS      current
   DESCRIPTION
       "Index"
   ::= { sispm10403166lEthLinkOAMPortDetailedStatisticsEntry 1 }

sispm10403166lStatisticsRxOAMInformationPDUs OBJECT-TYPE
   SYNTAX      Integer32
   MAX-ACCESS  read-only
   STATUS      current
   DESCRIPTION
       "The number of received and transmitted OAM Information PDU's.
	   Discontinuities of this counter can occur at re-initialization of the management system."
   ::= { sispm10403166lEthLinkOAMPortDetailedStatisticsEntry 2 }

sispm10403166lStatisticsRxUniqueErrorEventNotification OBJECT-TYPE
   SYNTAX      Integer32
   MAX-ACCESS  read-only
   STATUS      current
   DESCRIPTION
       "A count of the number of unique Event OAMPDUs received and transmitted on this interface.
	   Event Notifications may be sent in duplicate to increase the probability of successfully being received,
	   given the possibility that a frame may be lost in transit.
	   Duplicate Event Notification transmissions are counted by
	   Duplicate Event Notification counters for Tx and Rx respectively.
	   A unique Event Notification OAMPDU is indicated as an Event Notification OAMPDU with
	   a Sequence Number field that is distinct from the previously transmitted Event Notification OAMPDU Sequence Number."
   ::= { sispm10403166lEthLinkOAMPortDetailedStatisticsEntry 3 }

sispm10403166lStatisticsRxDuplicateErrorEventNotification OBJECT-TYPE
   SYNTAX      Integer32
   MAX-ACCESS  read-only
   STATUS      current
   DESCRIPTION
       "A count of the number of duplicate Event OAMPDUs received and transmitted on this interface.
	   Event Notification OAMPDUs may be sent in duplicate to increase the probability of successfully being received,
	   given the possibility that a frame may be lost in transit.
	   A duplicate Event Notification OAMPDU is indicated as an Event Notification OAMPDU with
	   a Sequence Number field that is identical to the previously transmitted Event Notification OAMPDU Sequence Number."
   ::= { sispm10403166lEthLinkOAMPortDetailedStatisticsEntry 4 }

sispm10403166lStatisticsRxLoopbackControl OBJECT-TYPE
   SYNTAX      Integer32
   MAX-ACCESS  read-only
   STATUS      current
   DESCRIPTION
       "A count of the number of Loopback Control OAMPDUs received and transmitted on this interface."
   ::= { sispm10403166lEthLinkOAMPortDetailedStatisticsEntry 5 }

sispm10403166lStatisticsRxVariableRequest OBJECT-TYPE
   SYNTAX      Integer32
   MAX-ACCESS  read-only
   STATUS      current
   DESCRIPTION
       "A count of the number of Variable Request OAMPDUs received and transmitted on this interface."
   ::= { sispm10403166lEthLinkOAMPortDetailedStatisticsEntry 6 }

sispm10403166lStatisticsRxVariableResponse OBJECT-TYPE
   SYNTAX      Integer32
   MAX-ACCESS  read-only
   STATUS      current
   DESCRIPTION
       "A count of the number of Variable Response OAMPDUs received and transmitted on this interface."
   ::= { sispm10403166lEthLinkOAMPortDetailedStatisticsEntry 7 }

sispm10403166lStatisticsRxOrgSpecificPDUs OBJECT-TYPE
   SYNTAX      Integer32
   MAX-ACCESS  read-only
   STATUS      current
   DESCRIPTION
       "A count of the number of Organization Specific OAMPDUs transmitted on this interface."
   ::= { sispm10403166lEthLinkOAMPortDetailedStatisticsEntry 8 }

sispm10403166lStatisticsRxUnsupportedCodes OBJECT-TYPE
   SYNTAX      Integer32
   MAX-ACCESS  read-only
   STATUS      current
   DESCRIPTION
       "A count of the number of OAMPDUs transmitted on this interface with an unsupported op-code."
   ::= { sispm10403166lEthLinkOAMPortDetailedStatisticsEntry 9 }

sispm10403166lStatisticsRxLinkFaultPDUs OBJECT-TYPE
   SYNTAX      Integer32
   MAX-ACCESS  read-only
   STATUS      current
   DESCRIPTION
       "A count of the number of Link fault PDU's received and transmitted on this interface."
   ::= { sispm10403166lEthLinkOAMPortDetailedStatisticsEntry 10 }

sispm10403166lStatisticsRxDyingGasp OBJECT-TYPE
   SYNTAX      Integer32
   MAX-ACCESS  read-only
   STATUS      current
   DESCRIPTION
       "A count of the number of Dying Gasp events received and transmitted on this interface."
   ::= { sispm10403166lEthLinkOAMPortDetailedStatisticsEntry 11 }

sispm10403166lStatisticsRxCriticalEventPDUs OBJECT-TYPE
   SYNTAX      Integer32
   MAX-ACCESS  read-only
   STATUS      current
   DESCRIPTION
       "A count of the number of Critical event PDU's received and transmitted on this interface."
   ::= { sispm10403166lEthLinkOAMPortDetailedStatisticsEntry 12 }

sispm10403166lStatisticsTxOAMInformationPDUs OBJECT-TYPE
   SYNTAX      Integer32
   MAX-ACCESS  read-only
   STATUS      current
   DESCRIPTION
       "The number of received and transmitted OAM Information PDU's.
	   Discontinuities of this counter can occur at re-initialization of the management system."
   ::= { sispm10403166lEthLinkOAMPortDetailedStatisticsEntry 13 }

sispm10403166lStatisticsTxUniqueErrorEventNotification OBJECT-TYPE
   SYNTAX      Integer32
   MAX-ACCESS  read-only
   STATUS      current
   DESCRIPTION
       "A count of the number of unique Event OAMPDUs received and transmitted on this interface.
	   Event Notifications may be sent in duplicate to increase the probability of successfully being received,
	   given the possibility that a frame may be lost in transit.
	   Duplicate Event Notification transmissions are counted by
	   Duplicate Event Notification counters for Tx and Rx respectively.
	   A unique Event Notification OAMPDU is indicated as an Event Notification OAMPDU with
	   a Sequence Number field that is distinct from the previously transmitted Event Notification OAMPDU Sequence Number."
   ::= { sispm10403166lEthLinkOAMPortDetailedStatisticsEntry 14 }

sispm10403166lStatisticsTxDuplicateErrorEventNotification OBJECT-TYPE
   SYNTAX      Integer32
   MAX-ACCESS  read-only
   STATUS      current
   DESCRIPTION
       "A count of the number of duplicate Event OAMPDUs received and transmitted on this interface.
	   Event Notification OAMPDUs may be sent in duplicate to increase the probability of successfully being received,
	   given the possibility that a frame may be lost in transit.
	   A duplicate Event Notification OAMPDU is indicated as an Event Notification OAMPDU with
	   a Sequence Number field that is identical to the previously transmitted Event Notification OAMPDU Sequence Number."
   ::= { sispm10403166lEthLinkOAMPortDetailedStatisticsEntry 15 }

sispm10403166lStatisticsTxLoopbackControl OBJECT-TYPE
   SYNTAX      Integer32
   MAX-ACCESS  read-only
   STATUS      current
   DESCRIPTION
       "A count of the number of Loopback Control OAMPDUs received and transmitted on this interface."
   ::= { sispm10403166lEthLinkOAMPortDetailedStatisticsEntry 16 }

sispm10403166lStatisticsTxVariableRequest OBJECT-TYPE
   SYNTAX      Integer32
   MAX-ACCESS  read-only
   STATUS      current
   DESCRIPTION
       "A count of the number of Variable Request OAMPDUs received and transmitted on this interface."
   ::= { sispm10403166lEthLinkOAMPortDetailedStatisticsEntry 17 }

sispm10403166lStatisticsTxVariableResponse OBJECT-TYPE
   SYNTAX      Integer32
   MAX-ACCESS  read-only
   STATUS      current
   DESCRIPTION
       "A count of the number of Variable Response OAMPDUs received and transmitted on this interface."
   ::= { sispm10403166lEthLinkOAMPortDetailedStatisticsEntry 18 }

sispm10403166lStatisticsTxOrgSpecificPDUs OBJECT-TYPE
   SYNTAX      Integer32
   MAX-ACCESS  read-only
   STATUS      current
   DESCRIPTION
       "A count of the number of Organization Specific OAMPDUs transmitted on this interface."
   ::= { sispm10403166lEthLinkOAMPortDetailedStatisticsEntry 19 }

sispm10403166lStatisticsTxUnsupportedCodes OBJECT-TYPE
   SYNTAX      Integer32
   MAX-ACCESS  read-only
   STATUS      current
   DESCRIPTION
       "A count of the number of OAMPDUs transmitted on this interface with an unsupported op-code."
   ::= { sispm10403166lEthLinkOAMPortDetailedStatisticsEntry 20 }

sispm10403166lStatisticsTxLinkFaultPDUs OBJECT-TYPE
   SYNTAX      Integer32
   MAX-ACCESS  read-only
   STATUS      current
   DESCRIPTION
       "A count of the number of Link fault PDU's received and transmitted on this interface."
   ::= { sispm10403166lEthLinkOAMPortDetailedStatisticsEntry 21 }

sispm10403166lStatisticsTxDyingGasp OBJECT-TYPE
   SYNTAX      Integer32
   MAX-ACCESS  read-only
   STATUS      current
   DESCRIPTION
       "A count of the number of Dying Gasp events received and transmitted on this interface."
   ::= { sispm10403166lEthLinkOAMPortDetailedStatisticsEntry 22 }

sispm10403166lStatisticsTxCriticalEventPDUs OBJECT-TYPE
   SYNTAX      Integer32
   MAX-ACCESS  read-only
   STATUS      current
   DESCRIPTION
       "A count of the number of Critical event PDU's received and transmitted on this interface."
   ::= { sispm10403166lEthLinkOAMPortDetailedStatisticsEntry 23 }

sispm10403166lStatisticsClear OBJECT-TYPE
   SYNTAX      Integer32
   MAX-ACCESS  read-write
   STATUS      current
   DESCRIPTION
       "Clears the counters for the selected port."
   ::= { sispm10403166lEthLinkOAMPortDetailedStatisticsEntry 24 }


sispm10403166lEthLinkOAMPortEventDetailedStatisticsTable OBJECT-TYPE
   SYNTAX      SEQUENCE OF SISPM10403166LEthLinkOAMPortEventDetailedStatisticsEntry
   MAX-ACCESS  not-accessible
   STATUS      current
   DESCRIPTION
       "Eth Link OAM Port Event Detailed Statistics Table"
   ::= { sispm10403166lETHLINKOAM 5 }

sispm10403166lEthLinkOAMPortEventDetailedStatisticsEntry OBJECT-TYPE
   SYNTAX      SISPM10403166LEthLinkOAMPortEventDetailedStatisticsEntry
   MAX-ACCESS  not-accessible
   STATUS      current
   DESCRIPTION
       "Eth Link OAM Port Event Detailed Statistics Entry"
   INDEX    { sispm10403166lDetailedStatisticsIndex  }
   ::= { sispm10403166lEthLinkOAMPortEventDetailedStatisticsTable 1 }

SISPM10403166LEthLinkOAMPortEventDetailedStatisticsEntry ::= SEQUENCE {
   sispm10403166lDetailedStatisticsIndex                          Integer32,
   sispm10403166lStatisticsLocalSequenceNumber                    Integer32,
   sispm10403166lStatisticsLocalFrameErrorEventTimestamp          Integer32,
   sispm10403166lStatisticsLocalFrameErrorEventWindow             Integer32,
   sispm10403166lStatisticsLocalFrameErrorEventThreshold          Integer32,
   sispm10403166lStatisticsLocalFrameErrors                       Integer32,
   sispm10403166lStatisticsLocalTotalFrameErrors                  Counter64,
   sispm10403166lStatisticsLocalTotalFrameErrorEvents             Integer32,
   sispm10403166lStatisticsLocalFramePeriodErrorEventTimestamp    Integer32,
   sispm10403166lStatisticsLocalFramePeriodErrorEventWindow       Integer32,
   sispm10403166lStatisticsLocalFramePeriodErrorEventThreshold    Integer32,
   sispm10403166lStatisticsLocalFramePeriodErrors                 Integer32,
   sispm10403166lStatisticsLocalTotalFramePeriodErrors            Counter64,
   sispm10403166lStatisticsLocalTotalFramePeriodErrorEvents       Integer32,
   sispm10403166lStatisticsLocalSymbolPeriodErrorEventTimestamp   Integer32,
   sispm10403166lStatisticsLocalSymbolPeriodErrorEventWindow      Counter64,
   sispm10403166lStatisticsLocalSymbolPeriodErrorEventThreshold   Counter64,
   sispm10403166lStatisticsLocalSymbolPeriodErrors                Counter64,
   sispm10403166lStatisticsLocalSymbolFramePeriodErrors           Counter64,
   sispm10403166lStatisticsLocalSymbolFramePeriodErrorEvents      Integer32,
   sispm10403166lStatisticsLocalEventSecondsSummaryTimeStamp      Integer32,
   sispm10403166lStatisticsLocalEventSecondsSummaryWindow         Integer32,
   sispm10403166lStatisticsLocalEventSecondsSummaryThreshold      Integer32,
   sispm10403166lStatisticsLocalEventSecondsSummaryEvents         Integer32,
   sispm10403166lStatisticsLocalEventSecondsSummaryErrorTotal     Integer32,
   sispm10403166lStatisticsLocalEventSecondsSummaryEventTotal     Integer32,
   sispm10403166lStatisticsRemoteFrameErrorEventTimestamp         Integer32,
   sispm10403166lStatisticsRemoteFrameErrorEventWindow            Integer32,
   sispm10403166lStatisticsRemoteFrameErrorEventThreshold         Integer32,
   sispm10403166lStatisticsRemoteFrameErrors                      Integer32,
   sispm10403166lStatisticsRemoteTotalFrameErrors                 Counter64,
   sispm10403166lStatisticsRemoteTotalFrameErrorEvents            Integer32,
   sispm10403166lStatisticsRemoteFramePeriodErrorEventTimestamp   Integer32,
   sispm10403166lStatisticsRemoteFramePeriodErrorEventWindow      Integer32,
   sispm10403166lStatisticsRemoteFramePeriodErrorEventThreshold   Integer32,
   sispm10403166lStatisticsRemoteFramePeriodErrors                Integer32,
   sispm10403166lStatisticsRemoteTotalFramePeriodErrors           Counter64,
   sispm10403166lStatisticsRemoteTotalFramePeriodErrorEvents      Integer32,
   sispm10403166lStatisticsRemoteSymbolPeriodErrorEventTimestamp  Integer32,
   sispm10403166lStatisticsRemoteSymbolPeriodErrorEventWindow     Counter64,
   sispm10403166lStatisticsRemoteSymbolPeriodErrorEventThreshold  Counter64,
   sispm10403166lStatisticsRemoteSymbolPeriodErrors               Counter64,
   sispm10403166lStatisticsRemoteSymbolFramePeriodErrors          Counter64,
   sispm10403166lStatisticsRemoteSymbolFramePeriodErrorEvents     Integer32,
   sispm10403166lStatisticsRemoteEventSecondsSummaryTimeStamp     Integer32,
   sispm10403166lStatisticsRemoteEventSecondsSummaryWindow        Integer32,
   sispm10403166lStatisticsRemoteEventSecondsSummaryThreshold     Integer32,
   sispm10403166lStatisticsRemoteEventSecondsSummaryEvents        Integer32,
   sispm10403166lStatisticsRemoteEventSecondsSummaryErrorTotal    Integer32,
   sispm10403166lStatisticsRemoteEventSecondsSummaryEventTotal    Integer32
}

sispm10403166lDetailedStatisticsIndex OBJECT-TYPE
   SYNTAX      Integer32(1..65535)
   MAX-ACCESS  not-accessible
   STATUS      current
   DESCRIPTION
       "Index"
   ::= { sispm10403166lEthLinkOAMPortEventDetailedStatisticsEntry 1 }

sispm10403166lStatisticsLocalSequenceNumber OBJECT-TYPE
   SYNTAX      Integer32
   MAX-ACCESS  read-only
   STATUS      current
   DESCRIPTION
       "This two-octet field indicates the total number of events occurred at the remote end."
   ::= { sispm10403166lEthLinkOAMPortEventDetailedStatisticsEntry 2 }

sispm10403166lStatisticsLocalFrameErrorEventTimestamp OBJECT-TYPE
   SYNTAX      Integer32
   MAX-ACCESS  read-only
   STATUS      current
   DESCRIPTION
       "This two-octet field indicates the time reference when the event was generated, in terms of 100 ms intervals."
   ::= { sispm10403166lEthLinkOAMPortEventDetailedStatisticsEntry 3 }

sispm10403166lStatisticsLocalFrameErrorEventWindow OBJECT-TYPE
   SYNTAX      Integer32
   MAX-ACCESS  read-only
   STATUS      current
   DESCRIPTION
       "This two-octet field indicates the duration of the period in terms of 100 ms intervals. 1)
	   The default value is one second. 2) The lower bound is one second. 3)
	   The upper bound is one minute."
   ::= { sispm10403166lEthLinkOAMPortEventDetailedStatisticsEntry 4 }

sispm10403166lStatisticsLocalFrameErrorEventThreshold OBJECT-TYPE
   SYNTAX      Integer32
   MAX-ACCESS  read-only
   STATUS      current
   DESCRIPTION
       "This four-octet field indicates the number of detected errored frames in the period is required
	   to be equal to or greater than in order for the event to be generated. 1)
	   The default value is one frame error. 2)
	   The lower bound is zero frame errors. 3)
	   The upper bound is unspecified."
   ::= { sispm10403166lEthLinkOAMPortEventDetailedStatisticsEntry 5 }

sispm10403166lStatisticsLocalFrameErrors OBJECT-TYPE
   SYNTAX      Integer32
   MAX-ACCESS  read-only
   STATUS      current
   DESCRIPTION
       "This four-octet field indicates the number of detected errored frames in the period."
   ::= { sispm10403166lEthLinkOAMPortEventDetailedStatisticsEntry 6 }

sispm10403166lStatisticsLocalTotalFrameErrors OBJECT-TYPE
   SYNTAX      Counter64
   MAX-ACCESS  read-only
   STATUS      current
   DESCRIPTION
       "This eight-octet field indicates the sum of errored frames that have been detected since the OAM sublayer was reset."
   ::= { sispm10403166lEthLinkOAMPortEventDetailedStatisticsEntry 7 }

sispm10403166lStatisticsLocalTotalFrameErrorEvents OBJECT-TYPE
   SYNTAX      Integer32
   MAX-ACCESS  read-only
   STATUS      current
   DESCRIPTION
       "This four-octet field indicates the number of Errored Frame Event TLVs that
	   have been generated since the OAM sublayer was reset."
   ::= { sispm10403166lEthLinkOAMPortEventDetailedStatisticsEntry 8 }

sispm10403166lStatisticsLocalFramePeriodErrorEventTimestamp OBJECT-TYPE
   SYNTAX      Integer32
   MAX-ACCESS  read-only
   STATUS      current
   DESCRIPTION
       "This two-octet field indicates the time reference when the event was generated, in terms of 100 ms intervals."
   ::= { sispm10403166lEthLinkOAMPortEventDetailedStatisticsEntry 9 }

sispm10403166lStatisticsLocalFramePeriodErrorEventWindow OBJECT-TYPE
   SYNTAX      Integer32
   MAX-ACCESS  read-only
   STATUS      current
   DESCRIPTION
       "This four-octet field indicates the duration of period in terms of frames."
   ::= { sispm10403166lEthLinkOAMPortEventDetailedStatisticsEntry 10 }

sispm10403166lStatisticsLocalFramePeriodErrorEventThreshold OBJECT-TYPE
   SYNTAX      Integer32
   MAX-ACCESS  read-only
   STATUS      current
   DESCRIPTION
       "This four-octet field indicates the number of errored frames in the period is required
	   to be equal to or greater than in order for the event to be generated."
   ::= { sispm10403166lEthLinkOAMPortEventDetailedStatisticsEntry 11 }

sispm10403166lStatisticsLocalFramePeriodErrors OBJECT-TYPE
   SYNTAX      Integer32
   MAX-ACCESS  read-only
   STATUS      current
   DESCRIPTION
       "This four-octet field indicates the number of frame errors in the period."
   ::= { sispm10403166lEthLinkOAMPortEventDetailedStatisticsEntry 12 }

sispm10403166lStatisticsLocalTotalFramePeriodErrors OBJECT-TYPE
   SYNTAX      Counter64
   MAX-ACCESS  read-only
   STATUS      current
   DESCRIPTION
       "This eight-octet field indicates the sum of frame errors that have been detected since the OAM sublayer was reset."
   ::= { sispm10403166lEthLinkOAMPortEventDetailedStatisticsEntry 13 }

sispm10403166lStatisticsLocalTotalFramePeriodErrorEvents OBJECT-TYPE
   SYNTAX      Integer32
   MAX-ACCESS  read-only
   STATUS      current
   DESCRIPTION
       "This four-octet field indicates the number of Errored Frame Period Event TLVs
	   that have been generated since the OAM sublayer was reset."
   ::= { sispm10403166lEthLinkOAMPortEventDetailedStatisticsEntry 14 }

sispm10403166lStatisticsLocalSymbolPeriodErrorEventTimestamp OBJECT-TYPE
   SYNTAX      Integer32
   MAX-ACCESS  read-only
   STATUS      current
   DESCRIPTION
       "This two-octet field indicates the time reference when the event was generated, in terms of 100 ms intervals."
   ::= { sispm10403166lEthLinkOAMPortEventDetailedStatisticsEntry 15 }

sispm10403166lStatisticsLocalSymbolPeriodErrorEventWindow OBJECT-TYPE
   SYNTAX      Counter64
   MAX-ACCESS  read-only
   STATUS      current
   DESCRIPTION
       "This eight-octet field indicates the number of symbols in the period."
   ::= { sispm10403166lEthLinkOAMPortEventDetailedStatisticsEntry 16 }

sispm10403166lStatisticsLocalSymbolPeriodErrorEventThreshold OBJECT-TYPE
   SYNTAX      Counter64
   MAX-ACCESS  read-only
   STATUS      current
   DESCRIPTION
       "This eight-octet field indicates the number of errored symbols in the period is required to
	   be equal to or greater than in order for the event to be generated."
   ::= { sispm10403166lEthLinkOAMPortEventDetailedStatisticsEntry 17 }

sispm10403166lStatisticsLocalSymbolPeriodErrors OBJECT-TYPE
   SYNTAX      Counter64
   MAX-ACCESS  read-only
   STATUS      current
   DESCRIPTION
       "This eight-octet field indicates the number of symbol errors in the period."
   ::= { sispm10403166lEthLinkOAMPortEventDetailedStatisticsEntry 18 }

sispm10403166lStatisticsLocalSymbolFramePeriodErrors OBJECT-TYPE
   SYNTAX      Counter64
   MAX-ACCESS  read-only
   STATUS      current
   DESCRIPTION
       "This eight-octet field indicates the sum of symbol errors since the OAM sublayer was reset."
   ::= { sispm10403166lEthLinkOAMPortEventDetailedStatisticsEntry 19 }

sispm10403166lStatisticsLocalSymbolFramePeriodErrorEvents OBJECT-TYPE
   SYNTAX      Integer32
   MAX-ACCESS  read-only
   STATUS      current
   DESCRIPTION
       "This four-octet field indicates the number of Errored Symbol Period Event TLVs that
	   have been generated since the OAM sublayer was reset."
   ::= { sispm10403166lEthLinkOAMPortEventDetailedStatisticsEntry 20 }

sispm10403166lStatisticsLocalEventSecondsSummaryTimeStamp OBJECT-TYPE
   SYNTAX      Integer32
   MAX-ACCESS  read-only
   STATUS      current
   DESCRIPTION
       "This two-octet field indicates the time reference when the event was generated,
	   in terms of 100 ms intervals, encoded as a 16-bit unsigned integer."
   ::= { sispm10403166lEthLinkOAMPortEventDetailedStatisticsEntry 21 }

sispm10403166lStatisticsLocalEventSecondsSummaryWindow OBJECT-TYPE
   SYNTAX      Integer32
   MAX-ACCESS  read-only
   STATUS      current
   DESCRIPTION
       "This two-octet field indicates the duration of the period in terms of 100 ms intervals, encoded as a 16-bit unsigned integer."
   ::= { sispm10403166lEthLinkOAMPortEventDetailedStatisticsEntry 22 }

sispm10403166lStatisticsLocalEventSecondsSummaryThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."
   ::= { sispm10403166lEthLinkOAMPortEventDetailedStatisticsEntry 23 }

sispm10403166lStatisticsLocalEventSecondsSummaryEvents OBJECT-TYPE
   SYNTAX      Integer32
   MAX-ACCESS  read-only
   STATUS      current
   DESCRIPTION
       "This two-octet field indicates the number of errored frame seconds in the period, encoded as a 16-bit unsigned integer."
   ::= { sispm10403166lEthLinkOAMPortEventDetailedStatisticsEntry 24 }

sispm10403166lStatisticsLocalEventSecondsSummaryErrorTotal OBJECT-TYPE
   SYNTAX      Integer32
   MAX-ACCESS  read-only
   STATUS      current
   DESCRIPTION
       "This four-octet field indicates the sum of errored frame seconds that have been detected since the OAM sublayer was reset."
   ::= { sispm10403166lEthLinkOAMPortEventDetailedStatisticsEntry 25 }

sispm10403166lStatisticsLocalEventSecondsSummaryEventTotal OBJECT-TYPE
   SYNTAX      Integer32
   MAX-ACCESS  read-only
   STATUS      current
   DESCRIPTION
       "This four-octet field indicates the number of Errored Frame Seconds Summary Event TLVs that
	   have been generated since the OAM sublayer was reset, encoded as a 32bit unsigned integer."
   ::= { sispm10403166lEthLinkOAMPortEventDetailedStatisticsEntry 26 }

sispm10403166lStatisticsRemoteFrameErrorEventTimestamp OBJECT-TYPE
   SYNTAX      Integer32
   MAX-ACCESS  read-only
   STATUS      current
   DESCRIPTION
       "This two-octet field indicates the time reference when the event was generated, in terms of 100 ms intervals."
   ::= { sispm10403166lEthLinkOAMPortEventDetailedStatisticsEntry 27 }

sispm10403166lStatisticsRemoteFrameErrorEventWindow OBJECT-TYPE
   SYNTAX      Integer32
   MAX-ACCESS  read-only
   STATUS      current
   DESCRIPTION
       "This two-octet field indicates the duration of the period in terms of 100 ms intervals. 1)
	   The default value is one second. 2) The lower bound is one second. 3)
	   The upper bound is one minute."
   ::= { sispm10403166lEthLinkOAMPortEventDetailedStatisticsEntry 28 }

sispm10403166lStatisticsRemoteFrameErrorEventThreshold OBJECT-TYPE
   SYNTAX      Integer32
   MAX-ACCESS  read-only
   STATUS      current
   DESCRIPTION
       "This four-octet field indicates the number of detected errored frames in the period is required
	   to be equal to or greater than in order for the event to be generated. 1)
	   The default value is one frame error. 2)
	   The lower bound is zero frame errors. 3)
	   The upper bound is unspecified."
   ::= { sispm10403166lEthLinkOAMPortEventDetailedStatisticsEntry 29 }

sispm10403166lStatisticsRemoteFrameErrors OBJECT-TYPE
   SYNTAX      Integer32
   MAX-ACCESS  read-only
   STATUS      current
   DESCRIPTION
       "This four-octet field indicates the number of detected errored frames in the period."
   ::= { sispm10403166lEthLinkOAMPortEventDetailedStatisticsEntry 30 }

sispm10403166lStatisticsRemoteTotalFrameErrors OBJECT-TYPE
   SYNTAX      Counter64
   MAX-ACCESS  read-only
   STATUS      current
   DESCRIPTION
       "This eight-octet field indicates the sum of errored frames that have been detected since the OAM sublayer was reset."
   ::= { sispm10403166lEthLinkOAMPortEventDetailedStatisticsEntry 31 }

sispm10403166lStatisticsRemoteTotalFrameErrorEvents OBJECT-TYPE
   SYNTAX      Integer32
   MAX-ACCESS  read-only
   STATUS      current
   DESCRIPTION
       "This four-octet field indicates the number of Errored Frame Event TLVs that
	   have been generated since the OAM sublayer was reset."
   ::= { sispm10403166lEthLinkOAMPortEventDetailedStatisticsEntry 32 }

sispm10403166lStatisticsRemoteFramePeriodErrorEventTimestamp OBJECT-TYPE
   SYNTAX      Integer32
   MAX-ACCESS  read-only
   STATUS      current
   DESCRIPTION
       "This two-octet field indicates the time reference when the event was generated, in terms of 100 ms intervals."
   ::= { sispm10403166lEthLinkOAMPortEventDetailedStatisticsEntry 33 }

sispm10403166lStatisticsRemoteFramePeriodErrorEventWindow OBJECT-TYPE
   SYNTAX      Integer32
   MAX-ACCESS  read-only
   STATUS      current
   DESCRIPTION
       "This four-octet field indicates the duration of period in terms of frames."
   ::= { sispm10403166lEthLinkOAMPortEventDetailedStatisticsEntry 34 }

sispm10403166lStatisticsRemoteFramePeriodErrorEventThreshold OBJECT-TYPE
   SYNTAX      Integer32
   MAX-ACCESS  read-only
   STATUS      current
   DESCRIPTION
       "This four-octet field indicates the number of errored frames in the period is required
	   to be equal to or greater than in order for the event to be generated."
   ::= { sispm10403166lEthLinkOAMPortEventDetailedStatisticsEntry 35 }

sispm10403166lStatisticsRemoteFramePeriodErrors OBJECT-TYPE
   SYNTAX      Integer32
   MAX-ACCESS  read-only
   STATUS      current
   DESCRIPTION
       "This four-octet field indicates the number of frame errors in the period."
   ::= { sispm10403166lEthLinkOAMPortEventDetailedStatisticsEntry 36 }

sispm10403166lStatisticsRemoteTotalFramePeriodErrors OBJECT-TYPE
   SYNTAX      Counter64
   MAX-ACCESS  read-only
   STATUS      current
   DESCRIPTION
       "This eight-octet field indicates the sum of frame errors that have been detected since the OAM sublayer was reset."
   ::= { sispm10403166lEthLinkOAMPortEventDetailedStatisticsEntry 37 }

sispm10403166lStatisticsRemoteTotalFramePeriodErrorEvents OBJECT-TYPE
   SYNTAX      Integer32
   MAX-ACCESS  read-only
   STATUS      current
   DESCRIPTION
       "This four-octet field indicates the number of Errored Frame Period Event TLVs
	   that have been generated since the OAM sublayer was reset."
   ::= { sispm10403166lEthLinkOAMPortEventDetailedStatisticsEntry 38 }

sispm10403166lStatisticsRemoteSymbolPeriodErrorEventTimestamp OBJECT-TYPE
   SYNTAX      Integer32
   MAX-ACCESS  read-only
   STATUS      current
   DESCRIPTION
       "This two-octet field indicates the time reference when the event was generated, in terms of 100 ms intervals."
   ::= { sispm10403166lEthLinkOAMPortEventDetailedStatisticsEntry 39 }

sispm10403166lStatisticsRemoteSymbolPeriodErrorEventWindow OBJECT-TYPE
   SYNTAX      Counter64
   MAX-ACCESS  read-only
   STATUS      current
   DESCRIPTION
       "This eight-octet field indicates the number of symbols in the period."
   ::= { sispm10403166lEthLinkOAMPortEventDetailedStatisticsEntry 40 }

sispm10403166lStatisticsRemoteSymbolPeriodErrorEventThreshold OBJECT-TYPE
   SYNTAX      Counter64
   MAX-ACCESS  read-only
   STATUS      current
   DESCRIPTION
       "This eight-octet field indicates the number of errored symbols in the period is required to
	   be equal to or greater than in order for the event to be generated."
   ::= { sispm10403166lEthLinkOAMPortEventDetailedStatisticsEntry 41 }

sispm10403166lStatisticsRemoteSymbolPeriodErrors OBJECT-TYPE
   SYNTAX      Counter64
   MAX-ACCESS  read-only
   STATUS      current
   DESCRIPTION
       "This eight-octet field indicates the number of symbol errors in the period."
   ::= { sispm10403166lEthLinkOAMPortEventDetailedStatisticsEntry 42 }

sispm10403166lStatisticsRemoteSymbolFramePeriodErrors OBJECT-TYPE
   SYNTAX      Counter64
   MAX-ACCESS  read-only
   STATUS      current
   DESCRIPTION
       "This eight-octet field indicates the sum of symbol errors since the OAM sublayer was reset."
   ::= { sispm10403166lEthLinkOAMPortEventDetailedStatisticsEntry 43 }

sispm10403166lStatisticsRemoteSymbolFramePeriodErrorEvents OBJECT-TYPE
   SYNTAX      Integer32
   MAX-ACCESS  read-only
   STATUS      current
   DESCRIPTION
       "This four-octet field indicates the number of Errored Symbol Period Event TLVs that
	   have been generated since the OAM sublayer was reset."
   ::= { sispm10403166lEthLinkOAMPortEventDetailedStatisticsEntry 44 }

sispm10403166lStatisticsRemoteEventSecondsSummaryTimeStamp OBJECT-TYPE
   SYNTAX      Integer32
   MAX-ACCESS  read-only
   STATUS      current
   DESCRIPTION
       "This two-octet field indicates the time reference when the event was generated,
	   in terms of 100 ms intervals, encoded as a 16-bit unsigned integer."
   ::= { sispm10403166lEthLinkOAMPortEventDetailedStatisticsEntry 45 }

sispm10403166lStatisticsRemoteEventSecondsSummaryWindow OBJECT-TYPE
   SYNTAX      Integer32
   MAX-ACCESS  read-only
   STATUS      current
   DESCRIPTION
       "This two-octet field indicates the duration of the period in terms of 100 ms intervals, encoded as a 16-bit unsigned integer."
   ::= { sispm10403166lEthLinkOAMPortEventDetailedStatisticsEntry 46 }

sispm10403166lStatisticsRemoteEventSecondsSummaryThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."
   ::= { sispm10403166lEthLinkOAMPortEventDetailedStatisticsEntry 47 }

sispm10403166lStatisticsRemoteEventSecondsSummaryEvents OBJECT-TYPE
   SYNTAX      Integer32
   MAX-ACCESS  read-only
   STATUS      current
   DESCRIPTION
       "This two-octet field indicates the number of errored frame seconds in the period, encoded as a 16-bit unsigned integer."
   ::= { sispm10403166lEthLinkOAMPortEventDetailedStatisticsEntry 48 }

sispm10403166lStatisticsRemoteEventSecondsSummaryErrorTotal OBJECT-TYPE
   SYNTAX      Integer32
   MAX-ACCESS  read-only
   STATUS      current
   DESCRIPTION
       "This four-octet field indicates the sum of errored frame seconds that have been detected since the OAM sublayer was reset."
   ::= { sispm10403166lEthLinkOAMPortEventDetailedStatisticsEntry 49 }

sispm10403166lStatisticsRemoteEventSecondsSummaryEventTotal OBJECT-TYPE
   SYNTAX      Integer32
   MAX-ACCESS  read-only
   STATUS      current
   DESCRIPTION
       "This four-octet field indicates the number of Errored Frame Seconds Summary Event TLVs that
	   have been generated since the OAM sublayer was reset, encoded as a 32bit unsigned integer."
   ::= { sispm10403166lEthLinkOAMPortEventDetailedStatisticsEntry 50 }


sispm10403166lIPMC    OBJECT IDENTIFIER ::= { sispm10403166lConfiguration 32 }

sispm10403166lIGMPSnooping    OBJECT IDENTIFIER ::= { sispm10403166lIPMC 1 }

sispm10403166lIGMPSnoopingBasicConfigSnoopingEnabled OBJECT-TYPE
   SYNTAX      Integer32(0|1)
   MAX-ACCESS  read-write
   STATUS      current
   DESCRIPTION
       "Snooping Enabled
       0:Disable
       1:Enable"
   ::= {     sispm10403166lIGMPSnooping 2 }

sispm10403166lIGMPSnoopingUnregisteredIPMCv4FloodingEnabled OBJECT-TYPE
   SYNTAX      Integer32(0|1)
   MAX-ACCESS  read-write
   STATUS      current
   DESCRIPTION
       "Unregistered IPMCv4 Flooding Enabled
       0:Disable
       1:Enable"
   ::= {     sispm10403166lIGMPSnooping 3 }

sispm10403166lIGMPSnoopingBasicConfigIGMPSSMRange OBJECT-TYPE
   SYNTAX      IpAddress
   MAX-ACCESS  read-write
   STATUS      current
   DESCRIPTION
       "IGMP SSM Range
        IPv4 multicast address."
   ::= {     sispm10403166lIGMPSnooping 4 }

sispm10403166lIGMPSnoopingBasicConfigIGMPSSMRangeLength OBJECT-TYPE
   SYNTAX      Integer32(4..32)
   MAX-ACCESS  read-write
   STATUS      current
   DESCRIPTION
       "IGMP SSM Range prefix. "
   ::= {     sispm10403166lIGMPSnooping 5 }

sispm10403166lIGMPSnoopingBasicConfigLeaveProxyEnabled OBJECT-TYPE
   SYNTAX      Integer32(0|1)
   MAX-ACCESS  read-write
   STATUS      current
   DESCRIPTION
       "Leave Proxy Enabled
       0:Disable
       1:Enable"
   ::= {     sispm10403166lIGMPSnooping 6 }

sispm10403166lIGMPSnoopingBasicConfigProxyEnabled OBJECT-TYPE
   SYNTAX      Integer32(0|1)
   MAX-ACCESS  read-write
   STATUS      current
   DESCRIPTION
       "Proxy Enabled
       0:Disable
       1:Enable"
   ::= {     sispm10403166lIGMPSnooping 7 }



sispm10403166lIGMPSnoopingPortRelatedTable OBJECT-TYPE
   SYNTAX      SEQUENCE OF SISPM10403166LIGMPSnoopingPortRelatedEntry
   MAX-ACCESS  not-accessible
   STATUS      current
   DESCRIPTION
       " "
   ::= { sispm10403166lIGMPSnooping 8 }

sispm10403166lIGMPSnoopingPortRelatedEntry OBJECT-TYPE
   SYNTAX      SISPM10403166LIGMPSnoopingPortRelatedEntry
   MAX-ACCESS  not-accessible
   STATUS      current
   DESCRIPTION
       " "
   INDEX    { sispm10403166lIGMPSnoopingPortRelatedPort  }
   ::= { sispm10403166lIGMPSnoopingPortRelatedTable 1 }

SISPM10403166LIGMPSnoopingPortRelatedEntry ::= SEQUENCE {
   sispm10403166lIGMPSnoopingPortRelatedPort       Integer32,
   sispm10403166lIGMPSnoopingPortRouterPort        Integer32,
   sispm10403166lIGMPSnoopingPortFastLeave         Integer32,
   sispm10403166lIGMPSnoopingPortThrottling        Integer32,
   sispm10403166lIGMPSnoopingPortFilteringProfile  DisplayString
}

sispm10403166lIGMPSnoopingPortRelatedPort OBJECT-TYPE
   SYNTAX      Integer32(1..65535)
   MAX-ACCESS  not-accessible
   STATUS      current
   DESCRIPTION
       "Index"
   ::= {     sispm10403166lIGMPSnoopingPortRelatedEntry 1 }

sispm10403166lIGMPSnoopingPortRouterPort OBJECT-TYPE
   SYNTAX      Integer32(0|1)
   MAX-ACCESS  read-write
   STATUS      current
   DESCRIPTION
       "Router Port
       0:Disable
       1:Enable"
   ::= {     sispm10403166lIGMPSnoopingPortRelatedEntry 2 }

sispm10403166lIGMPSnoopingPortFastLeave OBJECT-TYPE
   SYNTAX      Integer32(0|1)
   MAX-ACCESS  read-write
   STATUS      current
   DESCRIPTION
       "Fast Leave
       0:Disable
       1:Enable"
   ::= {     sispm10403166lIGMPSnoopingPortRelatedEntry 3 }

sispm10403166lIGMPSnoopingPortThrottling OBJECT-TYPE
   SYNTAX      Integer32(0..10)
   MAX-ACCESS  read-write
   STATUS      current
   DESCRIPTION
       "Throttling.
       Range: 0:unlimited, 1-10"
   ::= {     sispm10403166lIGMPSnoopingPortRelatedEntry 4 }

sispm10403166lIGMPSnoopingPortFilteringProfile OBJECT-TYPE
   SYNTAX      DisplayString
   MAX-ACCESS  read-write
   STATUS      current
   DESCRIPTION
       "Filtering Profile"
   ::= {     sispm10403166lIGMPSnoopingPortRelatedEntry 5 }

sispm10403166lIGMPSnoopingVLANConfigTable OBJECT-TYPE
   SYNTAX      SEQUENCE OF SISPM10403166LIGMPSnoopingVLANConfigEntry
   MAX-ACCESS  not-accessible
   STATUS      current
   DESCRIPTION
       " "
   ::= { sispm10403166lIGMPSnooping 9 }

sispm10403166lIGMPSnoopingVLANConfigEntry OBJECT-TYPE
   SYNTAX      SISPM10403166LIGMPSnoopingVLANConfigEntry
   MAX-ACCESS  not-accessible
   STATUS      current
   DESCRIPTION
       " "
   INDEX    { sispm10403166lIGMPSnoopingVLANConfigIndex  }
   ::= { sispm10403166lIGMPSnoopingVLANConfigTable 1 }

SISPM10403166LIGMPSnoopingVLANConfigEntry ::= SEQUENCE {
   sispm10403166lIGMPSnoopingVLANConfigIndex            Integer32,
   sispm10403166lIGMPSnoopingVLANConfigVLANID           Integer32,
   sispm10403166lIGMPSnoopingVLANConfigSnoopingEnabled  Integer32,
   sispm10403166lIGMPSnoopingVLANConfigQuerierElection  Integer32,
   sispm10403166lIGMPSnoopingVLANConfigQuerierAddress   IpAddress,
   sispm10403166lIGMPSnoopingVLANConfigCompatibility    Integer32,
   sispm10403166lIGMPSnoopingVLANConfigPRI              Integer32,
   sispm10403166lIGMPSnoopingVLANConfigRV               Integer32,
   sispm10403166lIGMPSnoopingVLANConfigQI               Integer32,
   sispm10403166lIGMPSnoopingVLANConfigQRI              Integer32,
   sispm10403166lIGMPSnoopingVLANConfigLLQI             Integer32,
   sispm10403166lIGMPSnoopingVLANConfigURI              Integer32
}

sispm10403166lIGMPSnoopingVLANConfigIndex OBJECT-TYPE
   SYNTAX      Integer32(1..65535)
   MAX-ACCESS  not-accessible
   STATUS      current
   DESCRIPTION
       "Index"
   ::= {     sispm10403166lIGMPSnoopingVLANConfigEntry 1 }

sispm10403166lIGMPSnoopingVLANConfigVLANID OBJECT-TYPE
   SYNTAX      Integer32
   MAX-ACCESS  read-only
   STATUS      current
   DESCRIPTION
       "VLAN ID"
   ::= {     sispm10403166lIGMPSnoopingVLANConfigEntry 2 }

sispm10403166lIGMPSnoopingVLANConfigSnoopingEnabled OBJECT-TYPE
   SYNTAX      Integer32(0|1)
   MAX-ACCESS  read-write
   STATUS      current
   DESCRIPTION
       "IGMP Snooping Enabled
       0:Disable
       1:Enable"
   ::= {     sispm10403166lIGMPSnoopingVLANConfigEntry 3 }

sispm10403166lIGMPSnoopingVLANConfigQuerierElection OBJECT-TYPE
   SYNTAX      Integer32(0|1)
   MAX-ACCESS  read-write
   STATUS      current
   DESCRIPTION
       "Querier Election
       0:Disable
       1:Enable"
   ::= {     sispm10403166lIGMPSnoopingVLANConfigEntry 4 }

sispm10403166lIGMPSnoopingVLANConfigQuerierAddress OBJECT-TYPE
   SYNTAX      IpAddress
   MAX-ACCESS  read-write
   STATUS      current
   DESCRIPTION
       "Querier Address"
   ::= {     sispm10403166lIGMPSnoopingVLANConfigEntry 5 }

sispm10403166lIGMPSnoopingVLANConfigCompatibility OBJECT-TYPE
   SYNTAX      Integer32(0..3)
   MAX-ACCESS  read-write
   STATUS      current
   DESCRIPTION
       "Compatibility
       0:IGMP-Auto
       1:Forced IGMPv1
       2:Forced IGMPv2
       3:Forced IGMPv3"
   ::= {     sispm10403166lIGMPSnoopingVLANConfigEntry 6 }

sispm10403166lIGMPSnoopingVLANConfigPRI OBJECT-TYPE
   SYNTAX      Integer32(0..7)
   MAX-ACCESS  read-write
   STATUS      current
   DESCRIPTION
       "Priority of Interface.
       "
   ::= {     sispm10403166lIGMPSnoopingVLANConfigEntry 7 }

sispm10403166lIGMPSnoopingVLANConfigRV OBJECT-TYPE
   SYNTAX      Integer32(1..255)
   MAX-ACCESS  read-write
   STATUS      current
   DESCRIPTION
       "Robustness Variable."
   ::= {     sispm10403166lIGMPSnoopingVLANConfigEntry 8 }

sispm10403166lIGMPSnoopingVLANConfigQI OBJECT-TYPE
   SYNTAX      Integer32(1..31744)
   MAX-ACCESS  read-write
   STATUS      current
   DESCRIPTION
       "Query Interval."
   ::= {     sispm10403166lIGMPSnoopingVLANConfigEntry 9 }

sispm10403166lIGMPSnoopingVLANConfigQRI OBJECT-TYPE
   SYNTAX      Integer32(0..31744)
   MAX-ACCESS  read-write
   STATUS      current
   DESCRIPTION
       "Query Response Interval."
   ::= {     sispm10403166lIGMPSnoopingVLANConfigEntry 10 }

sispm10403166lIGMPSnoopingVLANConfigLLQI OBJECT-TYPE
   SYNTAX      Integer32(0..31744)
   MAX-ACCESS  read-write
   STATUS      current
   DESCRIPTION
       "Last Member Query Interval."
   ::= {     sispm10403166lIGMPSnoopingVLANConfigEntry 11 }

sispm10403166lIGMPSnoopingVLANConfigURI OBJECT-TYPE
   SYNTAX      Integer32(0..31744)
   MAX-ACCESS  read-write
   STATUS      current
   DESCRIPTION
       "Unsolicited Report Interval."
   ::= {     sispm10403166lIGMPSnoopingVLANConfigEntry 12 }


sispm10403166lIGMPSnoopingStatusClear OBJECT-TYPE
   SYNTAX      Integer32(0|1)
   MAX-ACCESS  read-write
   STATUS      current
   DESCRIPTION
       "Clears all Statistics counters."
   ::= { sispm10403166lIGMPSnooping 10 }


sispm10403166lIGMPSnoopingStatusTable OBJECT-TYPE
   SYNTAX      SEQUENCE OF SISPM10403166LIGMPSnoopingStatusEntry
   MAX-ACCESS  not-accessible
   STATUS      current
   DESCRIPTION
       " "
   ::= { sispm10403166lIGMPSnooping 11 }

sispm10403166lIGMPSnoopingStatusEntry OBJECT-TYPE
   SYNTAX      SISPM10403166LIGMPSnoopingStatusEntry
   MAX-ACCESS  not-accessible
   STATUS      current
   DESCRIPTION
       " "
   INDEX    { sispm10403166lIGMPSnoopingStatusIndex  }
   ::= { sispm10403166lIGMPSnoopingStatusTable 1 }

SISPM10403166LIGMPSnoopingStatusEntry ::= SEQUENCE {
   sispm10403166lIGMPSnoopingStatusIndex               Integer32,
   sispm10403166lIGMPSnoopingStatusVLANID              Integer32,
   sispm10403166lIGMPSnoopingStatusQuerierVersion      DisplayString,
   sispm10403166lIGMPSnoopingStatusHostVersion         DisplayString,
   sispm10403166lIGMPSnoopingStatusQuerierStatus       Integer32,
   sispm10403166lIGMPSnoopingStatusQueriesTransmitted  Integer32,
   sispm10403166lIGMPSnoopingStatusQueriesReceived     Integer32,
   sispm10403166lIGMPSnoopingStatusV1ReportsReceived   Integer32,
   sispm10403166lIGMPSnoopingStatusV2ReportsReceived   Integer32,
   sispm10403166lIGMPSnoopingStatusV3ReportsReceived   Integer32,
   sispm10403166lIGMPSnoopingStatusV2LeavesReceived    Integer32
}

sispm10403166lIGMPSnoopingStatusIndex OBJECT-TYPE
   SYNTAX      Integer32(1..65535)
   MAX-ACCESS  not-accessible
   STATUS      current
   DESCRIPTION
       "Index"
   ::= {     sispm10403166lIGMPSnoopingStatusEntry 1 }

sispm10403166lIGMPSnoopingStatusVLANID OBJECT-TYPE
   SYNTAX      Integer32
   MAX-ACCESS  read-only
   STATUS      current
   DESCRIPTION
       "VLAN ID"
   ::= {     sispm10403166lIGMPSnoopingStatusEntry 2 }

sispm10403166lIGMPSnoopingStatusQuerierVersion OBJECT-TYPE
   SYNTAX      DisplayString
   MAX-ACCESS  read-only
   STATUS      current
   DESCRIPTION
       "Querier Version"
   ::= {     sispm10403166lIGMPSnoopingStatusEntry 3 }

sispm10403166lIGMPSnoopingStatusHostVersion OBJECT-TYPE
   SYNTAX      DisplayString
   MAX-ACCESS  read-only
   STATUS      current
   DESCRIPTION
       "Host Version"
   ::= {     sispm10403166lIGMPSnoopingStatusEntry 4 }

sispm10403166lIGMPSnoopingStatusQuerierStatus OBJECT-TYPE
   SYNTAX      Integer32
   MAX-ACCESS  read-only
   STATUS      current
   DESCRIPTION
       "Querier Status.
       0:Init
       1:Idle
       2:Active"
   ::= {     sispm10403166lIGMPSnoopingStatusEntry 5 }

sispm10403166lIGMPSnoopingStatusQueriesTransmitted OBJECT-TYPE
   SYNTAX      Integer32
   MAX-ACCESS  read-only
   STATUS      current
   DESCRIPTION
       "Queries Transmitted."
   ::= {     sispm10403166lIGMPSnoopingStatusEntry 6 }

sispm10403166lIGMPSnoopingStatusQueriesReceived OBJECT-TYPE
   SYNTAX      Integer32
   MAX-ACCESS  read-only
   STATUS      current
   DESCRIPTION
       "Queries Received."
   ::= {     sispm10403166lIGMPSnoopingStatusEntry 7 }

sispm10403166lIGMPSnoopingStatusV1ReportsReceived OBJECT-TYPE
   SYNTAX      Integer32
   MAX-ACCESS  read-only
   STATUS      current
   DESCRIPTION
       "V1 Reports Received"
   ::= {     sispm10403166lIGMPSnoopingStatusEntry 8 }

sispm10403166lIGMPSnoopingStatusV2ReportsReceived OBJECT-TYPE
   SYNTAX      Integer32
   MAX-ACCESS  read-only
   STATUS      current
   DESCRIPTION
       "V2 Reports Received"
   ::= {     sispm10403166lIGMPSnoopingStatusEntry 9 }

sispm10403166lIGMPSnoopingStatusV3ReportsReceived OBJECT-TYPE
   SYNTAX      Integer32
   MAX-ACCESS  read-only
   STATUS      current
   DESCRIPTION
       "V3 Reports Received"
   ::= {     sispm10403166lIGMPSnoopingStatusEntry 10 }

sispm10403166lIGMPSnoopingStatusV2LeavesReceived OBJECT-TYPE
   SYNTAX      Integer32
   MAX-ACCESS  read-only
   STATUS      current
   DESCRIPTION
       "V2 Leaves Received"
   ::= {     sispm10403166lIGMPSnoopingStatusEntry 11 }

sispm10403166lIGMPSnoopingStatusRouterPortTable OBJECT-TYPE
   SYNTAX      SEQUENCE OF SISPM10403166LIGMPSnoopingStatusRouterPortEntry
   MAX-ACCESS  not-accessible
   STATUS      current
   DESCRIPTION
       " "
   ::= { sispm10403166lIGMPSnooping 12 }

sispm10403166lIGMPSnoopingStatusRouterPortEntry OBJECT-TYPE
   SYNTAX      SISPM10403166LIGMPSnoopingStatusRouterPortEntry
   MAX-ACCESS  not-accessible
   STATUS      current
   DESCRIPTION
       " "
   INDEX    { sispm10403166lIGMPSnoopingStatusRouterPortIndex  }
   ::= { sispm10403166lIGMPSnoopingStatusRouterPortTable 1 }

SISPM10403166LIGMPSnoopingStatusRouterPortEntry ::= SEQUENCE {
   sispm10403166lIGMPSnoopingStatusRouterPortIndex    Integer32,
   sispm10403166lIGMPSnoopingStatusRouterPortPort     Integer32
}

sispm10403166lIGMPSnoopingStatusRouterPortIndex OBJECT-TYPE
   SYNTAX      Integer32(1..65535)
   MAX-ACCESS  not-accessible
   STATUS      current
   DESCRIPTION
       "Index"
   ::= {     sispm10403166lIGMPSnoopingStatusRouterPortEntry 1 }

sispm10403166lIGMPSnoopingStatusRouterPortPort OBJECT-TYPE
   SYNTAX      Integer32
   MAX-ACCESS  read-only
   STATUS      current
   DESCRIPTION
       "Switch port number.
       0:DISABLE
       1:IDLE
       2:ACTIVE"
   ::= {     sispm10403166lIGMPSnoopingStatusRouterPortEntry 2 }



sispm10403166lIGMPSnoopingGroupInfoTable OBJECT-TYPE
   SYNTAX      SEQUENCE OF SISPM10403166LIGMPSnoopingGroupInfoEntry
   MAX-ACCESS  not-accessible
   STATUS      current
   DESCRIPTION
       " "
   ::= { sispm10403166lIGMPSnooping 13 }

sispm10403166lIGMPSnoopingGroupInfoEntry OBJECT-TYPE
   SYNTAX      SISPM10403166LIGMPSnoopingGroupInfoEntry
   MAX-ACCESS  not-accessible
   STATUS      current
   DESCRIPTION
       " "
   INDEX    { sispm10403166lIGMPSnoopingGroupInfoIndex  }
   ::= { sispm10403166lIGMPSnoopingGroupInfoTable 1 }

SISPM10403166LIGMPSnoopingGroupInfoEntry ::= SEQUENCE {
   sispm10403166lIGMPSnoopingGroupInfoIndex       Integer32,
   sispm10403166lIGMPSnoopingGroupInfoVLANID      Integer32,
   sispm10403166lIGMPSnoopingGroupInfoGroups      IpAddress,
   sispm10403166lIGMPSnoopingGroupInfoPortMembers DisplayString
}

sispm10403166lIGMPSnoopingGroupInfoIndex OBJECT-TYPE
   SYNTAX      Integer32(1..65535)
   MAX-ACCESS  not-accessible
   STATUS      current
   DESCRIPTION
       "Index"
   ::= {     sispm10403166lIGMPSnoopingGroupInfoEntry 1 }

sispm10403166lIGMPSnoopingGroupInfoVLANID OBJECT-TYPE
   SYNTAX      Integer32
   MAX-ACCESS  read-only
   STATUS      current
   DESCRIPTION
       "VLAN ID"
   ::= {     sispm10403166lIGMPSnoopingGroupInfoEntry 2 }

sispm10403166lIGMPSnoopingGroupInfoGroups OBJECT-TYPE
   SYNTAX      IpAddress
   MAX-ACCESS  read-only
   STATUS      current
   DESCRIPTION
       "Groups"
   ::= {     sispm10403166lIGMPSnoopingGroupInfoEntry 3 }

sispm10403166lIGMPSnoopingGroupInfoPortMembers OBJECT-TYPE
   SYNTAX      DisplayString
   MAX-ACCESS  read-only
   STATUS      current
   DESCRIPTION
       "Port Members"
   ::= {     sispm10403166lIGMPSnoopingGroupInfoEntry 4 }



sispm10403166lIGMPSFMInfoTable OBJECT-TYPE
   SYNTAX      SEQUENCE OF SISPM10403166LIGMPSFMInfoEntry
   MAX-ACCESS  not-accessible
   STATUS      current
   DESCRIPTION
       " "
   ::= { sispm10403166lIGMPSnooping 14 }

sispm10403166lIGMPSFMInfoEntry OBJECT-TYPE
   SYNTAX      SISPM10403166LIGMPSFMInfoEntry
   MAX-ACCESS  not-accessible
   STATUS      current
   DESCRIPTION
       " "
   INDEX    { sispm10403166lIGMPSFMInfoIndex  }
   ::= { sispm10403166lIGMPSFMInfoTable 1 }

SISPM10403166LIGMPSFMInfoEntry ::= SEQUENCE {
   sispm10403166lIGMPSFMInfoIndex                Integer32,
   sispm10403166lIGMPSFMInfoVLANID               Integer32,
   sispm10403166lIGMPSFMInfoGroup                IpAddress,
   sispm10403166lIGMPSFMInfoPort                 Integer32,
   sispm10403166lIGMPSFMInfoMode                 Integer32,
   sispm10403166lIGMPSFMInfoSourceAddress        DisplayString,
   sispm10403166lIGMPSFMInfoType                 Integer32,
   sispm10403166lIGMPSFMInfoHardwareFilterSwitch Integer32

}

sispm10403166lIGMPSFMInfoIndex OBJECT-TYPE
   SYNTAX      Integer32(1..65535)
   MAX-ACCESS  not-accessible
   STATUS      current
   DESCRIPTION
       "Index"
   ::= {     sispm10403166lIGMPSFMInfoEntry 1 }

sispm10403166lIGMPSFMInfoVLANID OBJECT-TYPE
   SYNTAX      Integer32
   MAX-ACCESS  read-only
   STATUS      current
   DESCRIPTION
       "VLAN ID"
   ::= {     sispm10403166lIGMPSFMInfoEntry 2 }

sispm10403166lIGMPSFMInfoGroup OBJECT-TYPE
   SYNTAX      IpAddress
   MAX-ACCESS  read-only
   STATUS      current
   DESCRIPTION
       "Group"
   ::= {     sispm10403166lIGMPSFMInfoEntry 3 }

sispm10403166lIGMPSFMInfoPort OBJECT-TYPE
   SYNTAX      Integer32
   MAX-ACCESS  read-only
   STATUS      current
   DESCRIPTION
       "Port"
   ::= {     sispm10403166lIGMPSFMInfoEntry 4 }

sispm10403166lIGMPSFMInfoMode OBJECT-TYPE
   SYNTAX      Integer32
   MAX-ACCESS  read-only
   STATUS      current
   DESCRIPTION
       "Mode
       0:Exclude.
       1:Include"
   ::= {     sispm10403166lIGMPSFMInfoEntry 5 }

sispm10403166lIGMPSFMInfoSourceAddress OBJECT-TYPE
   SYNTAX      DisplayString
   MAX-ACCESS  read-only
   STATUS      current
   DESCRIPTION
       "Source Address"
   ::= {     sispm10403166lIGMPSFMInfoEntry 6 }

sispm10403166lIGMPSFMInfoType OBJECT-TYPE
   SYNTAX      Integer32
   MAX-ACCESS  read-only
   STATUS      current
   DESCRIPTION
       "Type
       0:Deny
       1:Allow"
   ::= {     sispm10403166lIGMPSFMInfoEntry 7 }

sispm10403166lIGMPSFMInfoHardwareFilterSwitch OBJECT-TYPE
   SYNTAX      Integer32
   MAX-ACCESS  read-only
   STATUS      current
   DESCRIPTION
       "Hardware Filter\Switch
       0:No
       1:Yes"
   ::= {     sispm10403166lIGMPSFMInfoEntry 8 }

sispm10403166lMLDSnooping    OBJECT IDENTIFIER ::= { sispm10403166lIPMC 2 }

sispm10403166lMLDSnoopingBasicConfigSnoopingEnabled OBJECT-TYPE
   SYNTAX      Integer32(0|1)
   MAX-ACCESS  read-write
   STATUS      current
   DESCRIPTION
       "Snooping Enabled
       0:Disable
       1:Enable"
   ::= {     sispm10403166lMLDSnooping 2 }

sispm10403166lMLDSnoopingUnregisteredIPMCv6FloodingEnabled OBJECT-TYPE
   SYNTAX      Integer32(0|1)
   MAX-ACCESS  read-write
   STATUS      current
   DESCRIPTION
       "Unregistered IPMCv6 Flooding Enabled
       0:Disable
       1:Enable"
   ::= {     sispm10403166lMLDSnooping 3 }

sispm10403166lMLDSnoopingBasicConfigMLDSSMRange OBJECT-TYPE
   SYNTAX      DisplayString
   MAX-ACCESS  read-write
   STATUS      current
   DESCRIPTION
       "MLD SSM Range
        IPv6 multicast address."
   ::= {     sispm10403166lMLDSnooping 4 }

sispm10403166lMLDSnoopingBasicConfigMLDSSMRangeLength OBJECT-TYPE
   SYNTAX      Integer32(8..128)
   MAX-ACCESS  read-write
   STATUS      current
   DESCRIPTION
       "MLD SSM Range prefix. "
   ::= {     sispm10403166lMLDSnooping 5 }

sispm10403166lMLDSnoopingBasicConfigLeaveProxyEnabled OBJECT-TYPE
   SYNTAX      Integer32(0|1)
   MAX-ACCESS  read-write
   STATUS      current
   DESCRIPTION
       "Leave Proxy Enabled
       0:Disable
       1:Enable"
   ::= {     sispm10403166lMLDSnooping 6 }

sispm10403166lMLDSnoopingBasicConfigProxyEnabled OBJECT-TYPE
   SYNTAX      Integer32(0|1)
   MAX-ACCESS  read-write
   STATUS      current
   DESCRIPTION
       "Proxy Enabled
       0:Disable
       1:Enable"
   ::= {     sispm10403166lMLDSnooping 7 }



sispm10403166lMLDSnoopingPortRelatedTable OBJECT-TYPE
   SYNTAX      SEQUENCE OF SISPM10403166LMLDSnoopingPortRelatedEntry
   MAX-ACCESS  not-accessible
   STATUS      current
   DESCRIPTION
       " "
   ::= { sispm10403166lMLDSnooping 8 }

sispm10403166lMLDSnoopingPortRelatedEntry OBJECT-TYPE
   SYNTAX      SISPM10403166LMLDSnoopingPortRelatedEntry
   MAX-ACCESS  not-accessible
   STATUS      current
   DESCRIPTION
       " "
   INDEX    { sispm10403166lMLDSnoopingPortRelatedPort  }
   ::= { sispm10403166lMLDSnoopingPortRelatedTable 1 }

SISPM10403166LMLDSnoopingPortRelatedEntry ::= SEQUENCE {
   sispm10403166lMLDSnoopingPortRelatedPort       Integer32,
   sispm10403166lMLDSnoopingPortRouterPort        Integer32,
   sispm10403166lMLDSnoopingPortFastLeave         Integer32,
   sispm10403166lMLDSnoopingPortThrottling        Integer32,
   sispm10403166lMLDSnoopingPortFilteringProfile  DisplayString
}

sispm10403166lMLDSnoopingPortRelatedPort OBJECT-TYPE
   SYNTAX      Integer32(1..65535)
   MAX-ACCESS  not-accessible
   STATUS      current
   DESCRIPTION
       "Index"
   ::= {     sispm10403166lMLDSnoopingPortRelatedEntry 1 }

sispm10403166lMLDSnoopingPortRouterPort OBJECT-TYPE
   SYNTAX      Integer32(0|1)
   MAX-ACCESS  read-write
   STATUS      current
   DESCRIPTION
       "Router Port
       0:Disable
       1:Enable"
   ::= {     sispm10403166lMLDSnoopingPortRelatedEntry 2 }

sispm10403166lMLDSnoopingPortFastLeave OBJECT-TYPE
   SYNTAX      Integer32(0|1)
   MAX-ACCESS  read-write
   STATUS      current
   DESCRIPTION
       "Fast Leave
       0:Disable
       1:Enable"
   ::= {     sispm10403166lMLDSnoopingPortRelatedEntry 3 }

sispm10403166lMLDSnoopingPortThrottling OBJECT-TYPE
   SYNTAX      Integer32(0..10)
   MAX-ACCESS  read-write
   STATUS      current
   DESCRIPTION
       "Throttling.
       Range: 0:unlimited, 1-10"
   ::= {     sispm10403166lMLDSnoopingPortRelatedEntry 4 }

sispm10403166lMLDSnoopingPortFilteringProfile OBJECT-TYPE
   SYNTAX      DisplayString
   MAX-ACCESS  read-write
   STATUS      current
   DESCRIPTION
       "Filtering Profile"
   ::= {     sispm10403166lMLDSnoopingPortRelatedEntry 5 }


sispm10403166lMLDSnoopingVLANConfigTable OBJECT-TYPE
   SYNTAX      SEQUENCE OF SISPM10403166LMLDSnoopingVLANConfigEntry
   MAX-ACCESS  not-accessible
   STATUS      current
   DESCRIPTION
       " "
   ::= { sispm10403166lMLDSnooping 9 }

sispm10403166lMLDSnoopingVLANConfigEntry OBJECT-TYPE
   SYNTAX      SISPM10403166LMLDSnoopingVLANConfigEntry
   MAX-ACCESS  not-accessible
   STATUS      current
   DESCRIPTION
       " "
   INDEX    { sispm10403166lMLDSnoopingVLANConfigIndex  }
   ::= { sispm10403166lMLDSnoopingVLANConfigTable 1 }

SISPM10403166LMLDSnoopingVLANConfigEntry ::= SEQUENCE {
   sispm10403166lMLDSnoopingVLANConfigIndex            Integer32,
   sispm10403166lMLDSnoopingVLANConfigVLANID           Integer32,
   sispm10403166lMLDSnoopingVLANConfigSnoopingEnabled  Integer32,
   sispm10403166lMLDSnoopingVLANConfigQuerierElection  Integer32,
   sispm10403166lMLDSnoopingVLANConfigCompatibility    Integer32,
   sispm10403166lMLDSnoopingVLANConfigPRI              Integer32,
   sispm10403166lMLDSnoopingVLANConfigRV               Integer32,
   sispm10403166lMLDSnoopingVLANConfigQI               Integer32,
   sispm10403166lMLDSnoopingVLANConfigQRI              Integer32,
   sispm10403166lMLDSnoopingVLANConfigLLQI             Integer32,
   sispm10403166lMLDSnoopingVLANConfigURI              Integer32
}

sispm10403166lMLDSnoopingVLANConfigIndex OBJECT-TYPE
   SYNTAX      Integer32(1..65535)
   MAX-ACCESS  not-accessible
   STATUS      current
   DESCRIPTION
       "Index"
   ::= {     sispm10403166lMLDSnoopingVLANConfigEntry 1 }

sispm10403166lMLDSnoopingVLANConfigVLANID OBJECT-TYPE
   SYNTAX      Integer32
   MAX-ACCESS  read-only
   STATUS      current
   DESCRIPTION
       "VLAN ID"
   ::= {     sispm10403166lMLDSnoopingVLANConfigEntry 2 }

sispm10403166lMLDSnoopingVLANConfigSnoopingEnabled OBJECT-TYPE
   SYNTAX      Integer32(0|1)
   MAX-ACCESS  read-write
   STATUS      current
   DESCRIPTION
       "IGMP Snooping Enabled
       0:Disable
       1:Enable"
   ::= {     sispm10403166lMLDSnoopingVLANConfigEntry 3 }

sispm10403166lMLDSnoopingVLANConfigQuerierElection OBJECT-TYPE
   SYNTAX      Integer32(0|1)
   MAX-ACCESS  read-write
   STATUS      current
   DESCRIPTION
       "Querier Election
       0:Disable
       1:Enable"
   ::= {     sispm10403166lMLDSnoopingVLANConfigEntry 4 }

sispm10403166lMLDSnoopingVLANConfigCompatibility OBJECT-TYPE
   SYNTAX      Integer32(0..2)
   MAX-ACCESS  read-write
   STATUS      current
   DESCRIPTION
       "Compatibility
       0:MLD-Auto
       1:Forced MLDv1
       2:Forced MLDv2"
   ::= {     sispm10403166lMLDSnoopingVLANConfigEntry 6 }

sispm10403166lMLDSnoopingVLANConfigPRI OBJECT-TYPE
   SYNTAX      Integer32(0..7)
   MAX-ACCESS  read-write
   STATUS      current
   DESCRIPTION
       "Priority of Interface.
       "
   ::= {     sispm10403166lMLDSnoopingVLANConfigEntry 7 }

sispm10403166lMLDSnoopingVLANConfigRV OBJECT-TYPE
   SYNTAX      Integer32(1..255)
   MAX-ACCESS  read-write
   STATUS      current
   DESCRIPTION
       "Robustness Variable."
   ::= {     sispm10403166lMLDSnoopingVLANConfigEntry 8 }

sispm10403166lMLDSnoopingVLANConfigQI OBJECT-TYPE
   SYNTAX      Integer32(1..31744)
   MAX-ACCESS  read-write
   STATUS      current
   DESCRIPTION
       "Query Interval."
   ::= {     sispm10403166lMLDSnoopingVLANConfigEntry 9 }

sispm10403166lMLDSnoopingVLANConfigQRI OBJECT-TYPE
   SYNTAX      Integer32(0..31744)
   MAX-ACCESS  read-write
   STATUS      current
   DESCRIPTION
       "Query Response Interval."
   ::= {     sispm10403166lMLDSnoopingVLANConfigEntry 10 }

sispm10403166lMLDSnoopingVLANConfigLLQI OBJECT-TYPE
   SYNTAX      Integer32(0..31744)
   MAX-ACCESS  read-write
   STATUS      current
   DESCRIPTION
       "Last Member Query Interval."
   ::= {     sispm10403166lMLDSnoopingVLANConfigEntry 11 }

sispm10403166lMLDSnoopingVLANConfigURI OBJECT-TYPE
   SYNTAX      Integer32(0..31744)
   MAX-ACCESS  read-write
   STATUS      current
   DESCRIPTION
       "Unsolicited Report Interval."
   ::= {     sispm10403166lMLDSnoopingVLANConfigEntry 12 }


sispm10403166lMLDSnoopingStatusClear OBJECT-TYPE
   SYNTAX      Integer32(0|1)
   MAX-ACCESS  read-write
   STATUS      current
   DESCRIPTION
       "Clears all Statistics counters."
   ::= { sispm10403166lMLDSnooping 10 }


sispm10403166lMLDSnoopingStatusTable OBJECT-TYPE
   SYNTAX      SEQUENCE OF SISPM10403166LMLDSnoopingStatusEntry
   MAX-ACCESS  not-accessible
   STATUS      current
   DESCRIPTION
       " "
   ::= { sispm10403166lMLDSnooping 11 }

sispm10403166lMLDSnoopingStatusEntry OBJECT-TYPE
   SYNTAX      SISPM10403166LMLDSnoopingStatusEntry
   MAX-ACCESS  not-accessible
   STATUS      current
   DESCRIPTION
       " "
   INDEX    { sispm10403166lMLDSnoopingStatusIndex  }
   ::= { sispm10403166lMLDSnoopingStatusTable 1 }

SISPM10403166LMLDSnoopingStatusEntry ::= SEQUENCE {
   sispm10403166lMLDSnoopingStatusIndex               Integer32,
   sispm10403166lMLDSnoopingStatusVLANID              Integer32,
   sispm10403166lMLDSnoopingStatusQuerierVersion      DisplayString,
   sispm10403166lMLDSnoopingStatusHostVersion         DisplayString,
   sispm10403166lMLDSnoopingStatusQuerierStatus       Integer32,
   sispm10403166lMLDSnoopingStatusQueriesTransmitted  Integer32,
   sispm10403166lMLDSnoopingStatusQueriesReceived     Integer32,
   sispm10403166lMLDSnoopingStatusV1ReportsReceived   Integer32,
   sispm10403166lMLDSnoopingStatusV2ReportsReceived   Integer32,
   sispm10403166lMLDSnoopingStatusV1LeavesReceived    Integer32
}

sispm10403166lMLDSnoopingStatusIndex OBJECT-TYPE
   SYNTAX      Integer32(1..65535)
   MAX-ACCESS  not-accessible
   STATUS      current
   DESCRIPTION
       "Index"
   ::= {     sispm10403166lMLDSnoopingStatusEntry 1 }

sispm10403166lMLDSnoopingStatusVLANID OBJECT-TYPE
   SYNTAX      Integer32
   MAX-ACCESS  read-only
   STATUS      current
   DESCRIPTION
       "VLAN ID"
   ::= {     sispm10403166lMLDSnoopingStatusEntry 2 }

sispm10403166lMLDSnoopingStatusQuerierVersion OBJECT-TYPE
   SYNTAX      DisplayString
   MAX-ACCESS  read-only
   STATUS      current
   DESCRIPTION
       "Querier Version"
   ::= {     sispm10403166lMLDSnoopingStatusEntry 3 }

sispm10403166lMLDSnoopingStatusHostVersion OBJECT-TYPE
   SYNTAX      DisplayString
   MAX-ACCESS  read-only
   STATUS      current
   DESCRIPTION
       "Host Version"
   ::= {     sispm10403166lMLDSnoopingStatusEntry 4 }

sispm10403166lMLDSnoopingStatusQuerierStatus OBJECT-TYPE
   SYNTAX      Integer32
   MAX-ACCESS  read-only
   STATUS      current
   DESCRIPTION
       "Querier Status.
       0:Init
       1:Idle
       2:Active"
   ::= {     sispm10403166lMLDSnoopingStatusEntry 5 }

sispm10403166lMLDSnoopingStatusQueriesTransmitted OBJECT-TYPE
   SYNTAX      Integer32
   MAX-ACCESS  read-only
   STATUS      current
   DESCRIPTION
       "Queries Transmitted."
   ::= {     sispm10403166lMLDSnoopingStatusEntry 6 }

sispm10403166lMLDSnoopingStatusQueriesReceived OBJECT-TYPE
   SYNTAX      Integer32
   MAX-ACCESS  read-only
   STATUS      current
   DESCRIPTION
       "Queries Received."
   ::= {     sispm10403166lMLDSnoopingStatusEntry 7 }

sispm10403166lMLDSnoopingStatusV1ReportsReceived OBJECT-TYPE
   SYNTAX      Integer32
   MAX-ACCESS  read-only
   STATUS      current
   DESCRIPTION
       "V1 Reports Received"
   ::= {     sispm10403166lMLDSnoopingStatusEntry 8 }

sispm10403166lMLDSnoopingStatusV2ReportsReceived OBJECT-TYPE
   SYNTAX      Integer32
   MAX-ACCESS  read-only
   STATUS      current
   DESCRIPTION
       "V2 Reports Received"
   ::= {     sispm10403166lMLDSnoopingStatusEntry 9 }

sispm10403166lMLDSnoopingStatusV1LeavesReceived OBJECT-TYPE
   SYNTAX      Integer32
   MAX-ACCESS  read-only
   STATUS      current
   DESCRIPTION
       "V1 Leaves Received"
   ::= {     sispm10403166lMLDSnoopingStatusEntry 11 }

sispm10403166lMLDSnoopingStatusRouterPortTable OBJECT-TYPE
   SYNTAX      SEQUENCE OF SISPM10403166LMLDSnoopingStatusRouterPortEntry
   MAX-ACCESS  not-accessible
   STATUS      current
   DESCRIPTION
       " "
   ::= { sispm10403166lMLDSnooping 12 }

sispm10403166lMLDSnoopingStatusRouterPortEntry OBJECT-TYPE
   SYNTAX      SISPM10403166LMLDSnoopingStatusRouterPortEntry
   MAX-ACCESS  not-accessible
   STATUS      current
   DESCRIPTION
       " "
   INDEX    { sispm10403166lMLDSnoopingStatusRouterPortIndex  }
   ::= { sispm10403166lMLDSnoopingStatusRouterPortTable 1 }

SISPM10403166LMLDSnoopingStatusRouterPortEntry ::= SEQUENCE {
   sispm10403166lMLDSnoopingStatusRouterPortIndex    Integer32,
   sispm10403166lMLDSnoopingStatusRouterPortPort     Integer32
}

sispm10403166lMLDSnoopingStatusRouterPortIndex OBJECT-TYPE
   SYNTAX      Integer32(1..65535)
   MAX-ACCESS  not-accessible
   STATUS      current
   DESCRIPTION
       "Index"
   ::= {     sispm10403166lMLDSnoopingStatusRouterPortEntry 1 }

sispm10403166lMLDSnoopingStatusRouterPortPort OBJECT-TYPE
   SYNTAX      Integer32
   MAX-ACCESS  read-only
   STATUS      current
   DESCRIPTION
       "Switch port number.
       0:DISABLE
       1:IDLE
       2:ACTIVE"
   ::= {     sispm10403166lMLDSnoopingStatusRouterPortEntry 2 }


sispm10403166lMLDSnoopingGroupInfoTable OBJECT-TYPE
   SYNTAX      SEQUENCE OF SISPM10403166LMLDSnoopingGroupInfoEntry
   MAX-ACCESS  not-accessible
   STATUS      current
   DESCRIPTION
       " "
   ::= { sispm10403166lMLDSnooping 13 }

sispm10403166lMLDSnoopingGroupInfoEntry OBJECT-TYPE
   SYNTAX      SISPM10403166LMLDSnoopingGroupInfoEntry
   MAX-ACCESS  not-accessible
   STATUS      current
   DESCRIPTION
       " "
   INDEX    { sispm10403166lMLDSnoopingGroupInfoIndex  }
   ::= { sispm10403166lMLDSnoopingGroupInfoTable 1 }

SISPM10403166LMLDSnoopingGroupInfoEntry ::= SEQUENCE {
   sispm10403166lMLDSnoopingGroupInfoIndex       Integer32,
   sispm10403166lMLDSnoopingGroupInfoVLANID      Integer32,
   sispm10403166lMLDSnoopingGroupInfoGroups      IpAddress,
   sispm10403166lMLDSnoopingGroupInfoPortMembers DisplayString
}

sispm10403166lMLDSnoopingGroupInfoIndex OBJECT-TYPE
   SYNTAX      Integer32(1..65535)
   MAX-ACCESS  not-accessible
   STATUS      current
   DESCRIPTION
       "Index"
   ::= {     sispm10403166lMLDSnoopingGroupInfoEntry 1 }

sispm10403166lMLDSnoopingGroupInfoVLANID OBJECT-TYPE
   SYNTAX      Integer32
   MAX-ACCESS  read-only
   STATUS      current
   DESCRIPTION
       "VLAN ID"
   ::= {     sispm10403166lMLDSnoopingGroupInfoEntry 2 }

sispm10403166lMLDSnoopingGroupInfoGroups OBJECT-TYPE
   SYNTAX      IpAddress
   MAX-ACCESS  read-only
   STATUS      current
   DESCRIPTION
       "Groups"
   ::= {     sispm10403166lMLDSnoopingGroupInfoEntry 3 }

sispm10403166lMLDSnoopingGroupInfoPortMembers OBJECT-TYPE
   SYNTAX      DisplayString
   MAX-ACCESS  read-only
   STATUS      current
   DESCRIPTION
       "Port Members"
   ::= {     sispm10403166lMLDSnoopingGroupInfoEntry 4 }



sispm10403166lMLDSFMInfoTable OBJECT-TYPE
   SYNTAX      SEQUENCE OF SISPM10403166LMLDSFMInfoEntry
   MAX-ACCESS  not-accessible
   STATUS      current
   DESCRIPTION
       " "
   ::= { sispm10403166lMLDSnooping 14 }

sispm10403166lMLDSFMInfoEntry OBJECT-TYPE
   SYNTAX      SISPM10403166LMLDSFMInfoEntry
   MAX-ACCESS  not-accessible
   STATUS      current
   DESCRIPTION
       " "
   INDEX    { sispm10403166lMLDSFMInfoIndex  }
   ::= { sispm10403166lMLDSFMInfoTable 1 }

SISPM10403166LMLDSFMInfoEntry ::= SEQUENCE {
   sispm10403166lMLDSFMInfoIndex                Integer32,
   sispm10403166lMLDSFMInfoVLANID               Integer32,
   sispm10403166lMLDSFMInfoGroup                IpAddress,
   sispm10403166lMLDSFMInfoPort                 Integer32,
   sispm10403166lMLDSFMInfoMode                 Integer32,
   sispm10403166lMLDSFMInfoSourceAddress        DisplayString,
   sispm10403166lMLDSFMInfoType                 Integer32,
   sispm10403166lMLDSFMInfoHardwareFilterSwitch Integer32

}

sispm10403166lMLDSFMInfoIndex OBJECT-TYPE
   SYNTAX      Integer32(1..65535)
   MAX-ACCESS  not-accessible
   STATUS      current
   DESCRIPTION
       "Index"
   ::= {     sispm10403166lMLDSFMInfoEntry 1 }

sispm10403166lMLDSFMInfoVLANID OBJECT-TYPE
   SYNTAX      Integer32
   MAX-ACCESS  read-only
   STATUS      current
   DESCRIPTION
       "VLAN ID"
   ::= {     sispm10403166lMLDSFMInfoEntry 2 }

sispm10403166lMLDSFMInfoGroup OBJECT-TYPE
   SYNTAX      IpAddress
   MAX-ACCESS  read-only
   STATUS      current
   DESCRIPTION
       "Group"
   ::= {     sispm10403166lMLDSFMInfoEntry 3 }

sispm10403166lMLDSFMInfoPort OBJECT-TYPE
   SYNTAX      Integer32
   MAX-ACCESS  read-only
   STATUS      current
   DESCRIPTION
       "Port"
   ::= {     sispm10403166lMLDSFMInfoEntry 4 }

sispm10403166lMLDSFMInfoMode OBJECT-TYPE
   SYNTAX      Integer32
   MAX-ACCESS  read-only
   STATUS      current
   DESCRIPTION
       "Mode
       0:Exclude.
       1:Include"
   ::= {     sispm10403166lMLDSFMInfoEntry 5 }

sispm10403166lMLDSFMInfoSourceAddress OBJECT-TYPE
   SYNTAX      DisplayString
   MAX-ACCESS  read-only
   STATUS      current
   DESCRIPTION
       "Source Address"
   ::= {     sispm10403166lMLDSFMInfoEntry 6 }

sispm10403166lMLDSFMInfoType OBJECT-TYPE
   SYNTAX      Integer32
   MAX-ACCESS  read-only
   STATUS      current
   DESCRIPTION
       "Type
       0:Deny
       1:Allow"
   ::= {     sispm10403166lMLDSFMInfoEntry 7 }

sispm10403166lMLDSFMInfoHardwareFilterSwitch OBJECT-TYPE
   SYNTAX      Integer32
   MAX-ACCESS  read-only
   STATUS      current
   DESCRIPTION
       "Hardware Filter\Switch
       0:No
       1:Yes"
   ::= {     sispm10403166lMLDSFMInfoEntry 8 }

sispm10403166lMVR    OBJECT IDENTIFIER ::= { sispm10403166lConfiguration 33 }

sispm10403166lMVRConfig    OBJECT IDENTIFIER ::= { sispm10403166lMVR 1 }

sispm10403166lMVRConfigMVRMode OBJECT-TYPE
   SYNTAX      Integer32
   MAX-ACCESS  read-write
   STATUS      current
   DESCRIPTION
       "MVR Mode
       0:Disable
       1:Enable"
   ::= { sispm10403166lMVRConfig 2 }


sispm10403166lVLANInterfaceSettingTable  OBJECT-TYPE
   SYNTAX      SEQUENCE OF SISPM10403166LVLANInterfaceSettingEntry
   MAX-ACCESS  not-accessible
   STATUS      current
   DESCRIPTION
       "MVR Config table"
 ::= { sispm10403166lMVRConfig 3 }

sispm10403166lVLANInterfaceSettingEntry OBJECT-TYPE
    SYNTAX        SISPM10403166LVLANInterfaceSettingEntry
    MAX-ACCESS    not-accessible
    STATUS        current
    DESCRIPTION
        "MVR Config table"
    INDEX        { sispm10403166lVLANInterfaceSettingIndex }
    ::= { sispm10403166lVLANInterfaceSettingTable 1 }

SISPM10403166LVLANInterfaceSettingEntry ::=
    SEQUENCE {
        sispm10403166lVLANInterfaceSettingIndex                    Integer32,
        sispm10403166lVLANInterfaceSettingMVRVID                   Integer32,
        sispm10403166lVLANInterfaceSettingMVRName                  DisplayString,
        sispm10403166lVLANInterfaceSettingIGMPAddress              IpAddress,
        sispm10403166lVLANInterfaceSettingMode                     Integer32,
        sispm10403166lVLANInterfaceSettingTagging                  Integer32,
        sispm10403166lVLANInterfaceSettingPriority                 Integer32,
        sispm10403166lVLANInterfaceSettingLLQI                     Integer32,
        sispm10403166lVLANInterfaceSettingInterfaceChannelProfile  DisplayString,
        sispm10403166lVLANInterfaceSettingRowStatus                RowStatus
    }

sispm10403166lVLANInterfaceSettingIndex OBJECT-TYPE
   SYNTAX      Integer32(1..65535)
   MAX-ACCESS  not-accessible
   STATUS      current
   DESCRIPTION
       "MVR Config index."
   ::= {sispm10403166lVLANInterfaceSettingEntry 1 }

sispm10403166lVLANInterfaceSettingMVRVID OBJECT-TYPE
   SYNTAX      Integer32
   MAX-ACCESS  read-create
   STATUS      current
   DESCRIPTION
       "MVR VLAN ID"
   ::= {sispm10403166lVLANInterfaceSettingEntry 2 }

sispm10403166lVLANInterfaceSettingMVRName OBJECT-TYPE
   SYNTAX      DisplayString
   MAX-ACCESS  read-create
   STATUS      current
   DESCRIPTION
       "MVR Name. Length:0-16"
   ::= {sispm10403166lVLANInterfaceSettingEntry 3 }

sispm10403166lVLANInterfaceSettingIGMPAddress OBJECT-TYPE
   SYNTAX      IpAddress
   MAX-ACCESS  read-create
   STATUS      current
   DESCRIPTION
       "IPv4 IGMP Address"
   ::= {sispm10403166lVLANInterfaceSettingEntry 4 }

sispm10403166lVLANInterfaceSettingMode OBJECT-TYPE
   SYNTAX      Integer32
   MAX-ACCESS  read-create
   STATUS      current
   DESCRIPTION
      "Mode.
       0:Dynamic
       1:Compatible"
   ::= {sispm10403166lVLANInterfaceSettingEntry 5 }

sispm10403166lVLANInterfaceSettingTagging OBJECT-TYPE
   SYNTAX      Integer32
   MAX-ACCESS  read-create
   STATUS      current
   DESCRIPTION
      "Tagging.
       0:Untagged
       1:Tagged"
   ::= {sispm10403166lVLANInterfaceSettingEntry 6 }

sispm10403166lVLANInterfaceSettingPriority OBJECT-TYPE
   SYNTAX      Integer32(0..7)
   MAX-ACCESS  read-create
   STATUS      current
   DESCRIPTION
      "Priority"
   ::= {sispm10403166lVLANInterfaceSettingEntry 7 }

sispm10403166lVLANInterfaceSettingLLQI OBJECT-TYPE
   SYNTAX      Integer32(0..31744)
   MAX-ACCESS  read-create
   STATUS      current
   DESCRIPTION
      "LLQI"
   ::= {sispm10403166lVLANInterfaceSettingEntry 8 }

sispm10403166lVLANInterfaceSettingInterfaceChannelProfile OBJECT-TYPE
   SYNTAX      DisplayString
   MAX-ACCESS  read-create
   STATUS      current
   DESCRIPTION
      "Interface Channel Profile."
   ::= {sispm10403166lVLANInterfaceSettingEntry 9 }


sispm10403166lVLANInterfaceSettingRowStatus OBJECT-TYPE
   SYNTAX      RowStatus
   MAX-ACCESS  read-create
   STATUS      current
   DESCRIPTION
       "Row Status."
   ::= {sispm10403166lVLANInterfaceSettingEntry 10 }

sispm10403166lMVRVIDIndex OBJECT-TYPE
   SYNTAX      Integer32
   MAX-ACCESS  read-write
   STATUS      current
   DESCRIPTION
       "Set VIDIndex before use VLANInterfaceSettingPortRoleTable table."
   ::= { sispm10403166lMVRConfig 4 }

sispm10403166lVLANInterfaceSettingPortRoleTable  OBJECT-TYPE
   SYNTAX      SEQUENCE OF SISPM10403166LVLANInterfaceSettingPortRoleEntry
   MAX-ACCESS  not-accessible
   STATUS      current
   DESCRIPTION
       "VLAN Interface Setting Port Role table"
 ::= { sispm10403166lMVRConfig 5 }

sispm10403166lVLANInterfaceSettingPortRoleEntry OBJECT-TYPE
    SYNTAX        SISPM10403166LVLANInterfaceSettingPortRoleEntry
    MAX-ACCESS    not-accessible
    STATUS        current
    DESCRIPTION
        "VLAN Interface Setting Port Role table"
    INDEX        { sispm10403166lVLANInterfaceSettingPortRoleIndex }
    ::= { sispm10403166lVLANInterfaceSettingPortRoleTable 1 }

SISPM10403166LVLANInterfaceSettingPortRoleEntry ::=
    SEQUENCE {
        sispm10403166lVLANInterfaceSettingPortRoleIndex   Integer32,
        sispm10403166lVLANInterfaceSettingPortRolePort    Integer32
    }

sispm10403166lVLANInterfaceSettingPortRoleIndex OBJECT-TYPE
   SYNTAX      Integer32(1..65535)
   MAX-ACCESS  not-accessible
   STATUS      current
   DESCRIPTION
       "VLAN Interface Setting Port Role index."
   ::= {sispm10403166lVLANInterfaceSettingPortRoleEntry 1 }

sispm10403166lVLANInterfaceSettingPortRolePort OBJECT-TYPE
   SYNTAX      Integer32(0..2)
   MAX-ACCESS  read-write
   STATUS      current
   DESCRIPTION
       "Port Role.
       0:Inactive
       1:Source
       2:Receiver"
   ::= {sispm10403166lVLANInterfaceSettingPortRoleEntry 2 }



sispm10403166lImmediateLeaveSettingTable  OBJECT-TYPE
   SYNTAX      SEQUENCE OF SISPM10403166LImmediateLeaveSettingEntry
   MAX-ACCESS  not-accessible
   STATUS      current
   DESCRIPTION
       "Immediate Leave Setting table"
 ::= { sispm10403166lMVRConfig 6 }

sispm10403166lImmediateLeaveSettingEntry OBJECT-TYPE
    SYNTAX        SISPM10403166LImmediateLeaveSettingEntry
    MAX-ACCESS    not-accessible
    STATUS        current
    DESCRIPTION
        "Immediate Leave Setting table"
    INDEX        { sispm10403166lImmediateLeaveSettingPort }
    ::= { sispm10403166lImmediateLeaveSettingTable 1 }

SISPM10403166LImmediateLeaveSettingEntry ::=
    SEQUENCE {
        sispm10403166lImmediateLeaveSettingPort            Integer32,
        sispm10403166lImmediateLeaveSettingImmediateLeave  Integer32
    }

sispm10403166lImmediateLeaveSettingPort OBJECT-TYPE
   SYNTAX      Integer32(1..65535)
   MAX-ACCESS  not-accessible
   STATUS      current
   DESCRIPTION
       "Immediate Leave Setting index."
   ::= {sispm10403166lImmediateLeaveSettingEntry 1 }

sispm10403166lImmediateLeaveSettingImmediateLeave OBJECT-TYPE
   SYNTAX      Integer32(0|1)
   MAX-ACCESS  read-write
   STATUS      current
   DESCRIPTION
      "Immediate Leave
       0:Disable
       1:Enable"
   ::= {sispm10403166lImmediateLeaveSettingEntry 2 }


sispm10403166lStatistics    OBJECT IDENTIFIER ::= { sispm10403166lMVR 2 }

sispm10403166lMVRStatisticsClear OBJECT-TYPE
   SYNTAX      Integer32
   MAX-ACCESS  read-write
   STATUS      current
   DESCRIPTION
       "Statistics Clear.
       1:Clear"
   ::= { sispm10403166lStatistics 2 }

sispm10403166lMVRStatisticsTable OBJECT-TYPE
   SYNTAX      SEQUENCE OF SISPM10403166LMVRStatisticsEntry
   MAX-ACCESS  not-accessible
   STATUS      current
   DESCRIPTION
       " "
   ::= { sispm10403166lStatistics 3 }

sispm10403166lMVRStatisticsEntry OBJECT-TYPE
   SYNTAX      SISPM10403166LMVRStatisticsEntry
   MAX-ACCESS  not-accessible
   STATUS      current
   DESCRIPTION
       " "
   INDEX    { sispm10403166lMVRStatisticsIndex  }
   ::= { sispm10403166lMVRStatisticsTable 1 }

SISPM10403166LMVRStatisticsEntry ::= SEQUENCE {
   sispm10403166lMVRStatisticsIndex                       Integer32,
   sispm10403166lMVRStatisticsVLANID                      Integer32,
   sispm10403166lMVRStatisticsIGMPMLDQueriesReceived      DisplayString,
   sispm10403166lMVRStatisticsIGMPMLDQueriesTransmitted   DisplayString,
   sispm10403166lMVRStatisticsIGMPv1JoinsReceived         DisplayString,
   sispm10403166lMVRStatisticsIGMPv2MLDv1ReportsReceived  DisplayString,
   sispm10403166lMVRStatisticsIGMPv3MLDv2ReportsReceived  DisplayString,
   sispm10403166lMVRStatisticsIGMPv2MLDv1LeavesReceived   DisplayString
}

sispm10403166lMVRStatisticsIndex OBJECT-TYPE
   SYNTAX      Integer32(1..65535)
   MAX-ACCESS  not-accessible
   STATUS      current
   DESCRIPTION
       "Index"
   ::= {     sispm10403166lMVRStatisticsEntry 1 }

sispm10403166lMVRStatisticsVLANID OBJECT-TYPE
   SYNTAX      Integer32
   MAX-ACCESS  read-only
   STATUS      current
   DESCRIPTION
       "VLAN ID"
   ::= {     sispm10403166lMVRStatisticsEntry 2 }

sispm10403166lMVRStatisticsIGMPMLDQueriesReceived OBJECT-TYPE
   SYNTAX      DisplayString
   MAX-ACCESS  read-only
   STATUS      current
   DESCRIPTION
       "IGMP/MLD Queries Received"
   ::= {     sispm10403166lMVRStatisticsEntry 3 }

sispm10403166lMVRStatisticsIGMPMLDQueriesTransmitted OBJECT-TYPE
   SYNTAX      DisplayString
   MAX-ACCESS  read-only
   STATUS      current
   DESCRIPTION
       "IGMP/MLD Queries Transmitted"
   ::= {     sispm10403166lMVRStatisticsEntry 4 }

sispm10403166lMVRStatisticsIGMPv1JoinsReceived OBJECT-TYPE
   SYNTAX      DisplayString
   MAX-ACCESS  read-only
   STATUS      current
   DESCRIPTION
       "IGMPv1 Joins Received"
   ::= {     sispm10403166lMVRStatisticsEntry 5 }

sispm10403166lMVRStatisticsIGMPv2MLDv1ReportsReceived OBJECT-TYPE
   SYNTAX      DisplayString
   MAX-ACCESS  read-only
   STATUS      current
   DESCRIPTION
       "IGMPv2/MLDv1 Reports Received"
   ::= {     sispm10403166lMVRStatisticsEntry 6 }

sispm10403166lMVRStatisticsIGMPv3MLDv2ReportsReceived OBJECT-TYPE
   SYNTAX      DisplayString
   MAX-ACCESS  read-only
   STATUS      current
   DESCRIPTION
       "IGMPv3/MLDv2 Reports Received"
   ::= {     sispm10403166lMVRStatisticsEntry 7 }

sispm10403166lMVRStatisticsIGMPv2MLDv1LeavesReceived OBJECT-TYPE
   SYNTAX      DisplayString
   MAX-ACCESS  read-only
   STATUS      current
   DESCRIPTION
       "IGMPv2/MLDv1 Leaves Received"
   ::= {     sispm10403166lMVRStatisticsEntry 8 }


sispm10403166lGroupInformation  OBJECT IDENTIFIER ::= { sispm10403166lMVR 3 }

sispm10403166lMVRGroupInfoTable OBJECT-TYPE
   SYNTAX      SEQUENCE OF SISPM10403166LMVRGroupInfoEntry
   MAX-ACCESS  not-accessible
   STATUS      current
   DESCRIPTION
       " "
   ::= { sispm10403166lGroupInformation 1 }

sispm10403166lMVRGroupInfoEntry OBJECT-TYPE
   SYNTAX      SISPM10403166LMVRGroupInfoEntry
   MAX-ACCESS  not-accessible
   STATUS      current
   DESCRIPTION
       " "
   INDEX    { sispm10403166lMVRGroupInfoIndex  }
   ::= { sispm10403166lMVRGroupInfoTable 1 }

SISPM10403166LMVRGroupInfoEntry ::= SEQUENCE {
   sispm10403166lMVRGroupInfoIndex       Integer32,
   sispm10403166lMVRGroupInfoVLANID      Integer32,
   sispm10403166lMVRGroupInfoGroups      DisplayString,
   sispm10403166lMVRGroupInfoPortMembers DisplayString
}

sispm10403166lMVRGroupInfoIndex OBJECT-TYPE
   SYNTAX      Integer32(1..65535)
   MAX-ACCESS  not-accessible
   STATUS      current
   DESCRIPTION
       "Index"
   ::= {     sispm10403166lMVRGroupInfoEntry 1 }

sispm10403166lMVRGroupInfoVLANID OBJECT-TYPE
   SYNTAX      Integer32
   MAX-ACCESS  read-only
   STATUS      current
   DESCRIPTION
       "VLAN ID"
   ::= {     sispm10403166lMVRGroupInfoEntry 2 }

sispm10403166lMVRGroupInfoGroups OBJECT-TYPE
   SYNTAX      DisplayString
   MAX-ACCESS  read-only
   STATUS      current
   DESCRIPTION
       "Groups"
   ::= {     sispm10403166lMVRGroupInfoEntry 3 }

sispm10403166lMVRGroupInfoPortMembers OBJECT-TYPE
   SYNTAX      DisplayString
   MAX-ACCESS  read-only
   STATUS      current
   DESCRIPTION
       "Port Members"
   ::= {     sispm10403166lMVRGroupInfoEntry 4 }

sispm10403166lMVRSFMInformation  OBJECT IDENTIFIER ::= { sispm10403166lMVR 4 }

sispm10403166lMVRSFMInfoTable OBJECT-TYPE
   SYNTAX      SEQUENCE OF SISPM10403166LMVRSFMInfoEntry
   MAX-ACCESS  not-accessible
   STATUS      current
   DESCRIPTION
       " "
   ::= { sispm10403166lMVRSFMInformation 2 }

sispm10403166lMVRSFMInfoEntry OBJECT-TYPE
   SYNTAX      SISPM10403166LMVRSFMInfoEntry
   MAX-ACCESS  not-accessible
   STATUS      current
   DESCRIPTION
       " "
   INDEX    { sispm10403166lMVRSFMInfoIndex  }
   ::= { sispm10403166lMVRSFMInfoTable 1 }

SISPM10403166LMVRSFMInfoEntry ::= SEQUENCE {
   sispm10403166lMVRSFMInfoIndex                Integer32,
   sispm10403166lMVRSFMInfoVLANID               Integer32,
   sispm10403166lMVRSFMInfoGroup                DisplayString,
   sispm10403166lMVRSFMInfoPort                 Integer32,
   sispm10403166lMVRSFMInfoMode                 Integer32,
   sispm10403166lMVRSFMInfoSourceAddress        DisplayString,
   sispm10403166lMVRSFMInfoType                 Integer32,
   sispm10403166lMVRSFMInfoHardwareFilterSwitch Integer32

}

sispm10403166lMVRSFMInfoIndex OBJECT-TYPE
   SYNTAX      Integer32(1..65535)
   MAX-ACCESS  not-accessible
   STATUS      current
   DESCRIPTION
       "Index"
   ::= {     sispm10403166lMVRSFMInfoEntry 1 }

sispm10403166lMVRSFMInfoVLANID OBJECT-TYPE
   SYNTAX      Integer32
   MAX-ACCESS  read-only
   STATUS      current
   DESCRIPTION
       "VLAN ID"
   ::= {     sispm10403166lMVRSFMInfoEntry 2 }

sispm10403166lMVRSFMInfoGroup OBJECT-TYPE
   SYNTAX      DisplayString
   MAX-ACCESS  read-only
   STATUS      current
   DESCRIPTION
       "Group"
   ::= {     sispm10403166lMVRSFMInfoEntry 3 }

sispm10403166lMVRSFMInfoPort OBJECT-TYPE
   SYNTAX      Integer32
   MAX-ACCESS  read-only
   STATUS      current
   DESCRIPTION
       "Port"
   ::= {     sispm10403166lMVRSFMInfoEntry 4 }

sispm10403166lMVRSFMInfoMode OBJECT-TYPE
   SYNTAX      Integer32
   MAX-ACCESS  read-only
   STATUS      current
   DESCRIPTION
       "Mode
       0:Exclude.
       1:Include"
   ::= {     sispm10403166lMVRSFMInfoEntry 5 }

sispm10403166lMVRSFMInfoSourceAddress OBJECT-TYPE
   SYNTAX      DisplayString
   MAX-ACCESS  read-only
   STATUS      current
   DESCRIPTION
       "Source Address"
   ::= {     sispm10403166lMVRSFMInfoEntry 6 }

sispm10403166lMVRSFMInfoType OBJECT-TYPE
   SYNTAX      Integer32
   MAX-ACCESS  read-only
   STATUS      current
   DESCRIPTION
       "Type
       0:Deny
       1:Allow"
   ::= {     sispm10403166lMVRSFMInfoEntry 7 }

sispm10403166lMVRSFMInfoHardwareFilterSwitch OBJECT-TYPE
   SYNTAX      Integer32
   MAX-ACCESS  read-only
   STATUS      current
   DESCRIPTION
       "Hardware Filter\Switch
       0:No
       1:Yes"
   ::= {     sispm10403166lMVRSFMInfoEntry 8 }


sispm10403166lIPMCLIB    OBJECT IDENTIFIER ::= { sispm10403166lConfiguration 34 }

sispm10403166lMulticastFilteringProfileMode OBJECT-TYPE
   SYNTAX      Integer32
   MAX-ACCESS  read-write
   STATUS      current
   DESCRIPTION
       "Multicast Filtering Profile Mode.
       0:Disable
       1:Enable"
   ::= {     sispm10403166lIPMCLIB 1 }


sispm10403166lMulticastFilteringProfileSettingTable  OBJECT-TYPE
   SYNTAX      SEQUENCE OF SISPM10403166LMulticastFilteringProfileSettingEntry
   MAX-ACCESS  not-accessible
   STATUS      current
   DESCRIPTION
       "Multicast Filtering Profile Setting table"
 ::= { sispm10403166lIPMCLIB 2 }

sispm10403166lMulticastFilteringProfileSettingEntry OBJECT-TYPE
    SYNTAX        SISPM10403166LMulticastFilteringProfileSettingEntry
    MAX-ACCESS    not-accessible
    STATUS        current
    DESCRIPTION
        "Multicast Filtering Profile Setting table."
    INDEX        { sispm10403166lMulticastFilteringProfileSettingIndex }
    ::= { sispm10403166lMulticastFilteringProfileSettingTable 1 }

SISPM10403166LMulticastFilteringProfileSettingEntry ::=
    SEQUENCE {
        sispm10403166lMulticastFilteringProfileSettingIndex               Integer32,
        sispm10403166lMulticastFilteringProfileSettingProfileName         DisplayString,
        sispm10403166lMulticastFilteringProfileSettingProfileDescription  DisplayString,
        sispm10403166lMulticastFilteringProfileSettingRowStatus           RowStatus
    }

sispm10403166lMulticastFilteringProfileSettingIndex OBJECT-TYPE
   SYNTAX      Integer32(1..65535)
   MAX-ACCESS  not-accessible
   STATUS      current
   DESCRIPTION
       "Multicast Filtering Profile Setting index."
   ::= {sispm10403166lMulticastFilteringProfileSettingEntry 1 }


sispm10403166lMulticastFilteringProfileSettingProfileName OBJECT-TYPE
   SYNTAX      DisplayString
   MAX-ACCESS  read-create
   STATUS      current
   DESCRIPTION
       "Profile Name. Length:1-16"
   ::= {sispm10403166lMulticastFilteringProfileSettingEntry 2 }

sispm10403166lMulticastFilteringProfileSettingProfileDescription OBJECT-TYPE
   SYNTAX      DisplayString
   MAX-ACCESS  read-create
   STATUS      current
   DESCRIPTION
       "Profile Description. Length:0-64"
   ::= {sispm10403166lMulticastFilteringProfileSettingEntry 3 }

sispm10403166lMulticastFilteringProfileSettingRowStatus OBJECT-TYPE
   SYNTAX      RowStatus
   MAX-ACCESS  read-create
   STATUS      current
   DESCRIPTION
       "Row Status."
   ::= {sispm10403166lMulticastFilteringProfileSettingEntry 4 }



sispm10403166lMulticastFilterProfRuleSettingsProfileNameIndex OBJECT-TYPE
   SYNTAX      DisplayString
   MAX-ACCESS  read-write
   STATUS      current
   DESCRIPTION
       "Set this Profile Name value before use MulticastFilteringProfileRuleSettingsTable table"
   ::= {     sispm10403166lIPMCLIB 3 }



sispm10403166lMulticastFilteringProfileRuleSettingsTable  OBJECT-TYPE
   SYNTAX      SEQUENCE OF SISPM10403166LMulticastFilteringProfileRuleSettingsEntry
   MAX-ACCESS  not-accessible
   STATUS      current
   DESCRIPTION
       "Multicast Filtering Profile Rule Setting table"
 ::= { sispm10403166lIPMCLIB 4 }

sispm10403166lMulticastFilteringProfileRuleSettingsEntry OBJECT-TYPE
    SYNTAX        SISPM10403166LMulticastFilteringProfileRuleSettingsEntry
    MAX-ACCESS    not-accessible
    STATUS        current
    DESCRIPTION
        "Multicast Filtering Profile Rule Setting table."
    INDEX        { sispm10403166lMulticastFilteringProfileRuleSettingsIndex }
    ::= { sispm10403166lMulticastFilteringProfileRuleSettingsTable 1 }

SISPM10403166LMulticastFilteringProfileRuleSettingsEntry ::=
    SEQUENCE {
        sispm10403166lMulticastFilteringProfileRuleSettingsTableIndex          Integer32,
        sispm10403166lMulticastFilteringProfileRuleSettingsProfileName         DisplayString,
        sispm10403166lMulticastFilteringProfileRuleSettingsIndex               Integer32,
        sispm10403166lMulticastFilteringProfileRuleSettingsEntryName           DisplayString,
        sispm10403166lMulticastFilteringProfileRuleSettingsAddressRange        DisplayString,
        sispm10403166lMulticastFilteringProfileRuleSettingsAction              Integer32,
        sispm10403166lMulticastFilteringProfileRuleSettingsLog                 Integer32,
        sispm10403166lMulticastFilteringProfileRuleSettingsRowStatus           RowStatus
    }

sispm10403166lMulticastFilteringProfileRuleSettingsTableIndex OBJECT-TYPE
   SYNTAX      Integer32
   MAX-ACCESS  not-accessible
   STATUS      current
   DESCRIPTION
       "Multicast Filtering Profile Rule Setting index."
   ::= {sispm10403166lMulticastFilteringProfileRuleSettingsEntry 1 }


sispm10403166lMulticastFilteringProfileRuleSettingsProfileName OBJECT-TYPE
   SYNTAX      DisplayString
   MAX-ACCESS  read-only
   STATUS      current
   DESCRIPTION
       "Profile Name"
   ::= {sispm10403166lMulticastFilteringProfileRuleSettingsEntry 2 }

sispm10403166lMulticastFilteringProfileRuleSettingsIndex OBJECT-TYPE
   SYNTAX      Integer32(1..65535)
   MAX-ACCESS  read-only
   STATUS      current
   DESCRIPTION
       "Index"
   ::= {sispm10403166lMulticastFilteringProfileRuleSettingsEntry 3 }

sispm10403166lMulticastFilteringProfileRuleSettingsEntryName OBJECT-TYPE
   SYNTAX      DisplayString
   MAX-ACCESS  read-create
   STATUS      current
   DESCRIPTION
       "Entry Name, Length: 1-16"
   ::= {sispm10403166lMulticastFilteringProfileRuleSettingsEntry 4 }

sispm10403166lMulticastFilteringProfileRuleSettingsAddressRange OBJECT-TYPE
   SYNTAX      DisplayString
   MAX-ACCESS  read-only
   STATUS      current
   DESCRIPTION
       "Address Range"
   ::= {sispm10403166lMulticastFilteringProfileRuleSettingsEntry 5 }


sispm10403166lMulticastFilteringProfileRuleSettingsAction OBJECT-TYPE
   SYNTAX      Integer32
   MAX-ACCESS  read-create
   STATUS      current
   DESCRIPTION
       "0:Deny
        1:Permit"
   ::= {sispm10403166lMulticastFilteringProfileRuleSettingsEntry 6 }

sispm10403166lMulticastFilteringProfileRuleSettingsLog OBJECT-TYPE
   SYNTAX      Integer32
   MAX-ACCESS  read-create
   STATUS      current
   DESCRIPTION
       "0:Disable
        1:Enable"
   ::= {sispm10403166lMulticastFilteringProfileRuleSettingsEntry 7 }


sispm10403166lMulticastFilteringProfileRuleSettingsRowStatus OBJECT-TYPE
   SYNTAX      RowStatus
   MAX-ACCESS  read-create
   STATUS      current
   DESCRIPTION
       "Row Status."
   ::= {sispm10403166lMulticastFilteringProfileRuleSettingsEntry 8 }


sispm10403166lMulticastFilteringProfileAddressConfigTable  OBJECT-TYPE
   SYNTAX      SEQUENCE OF SISPM10403166LMulticastFilteringProfileAddressConfigEntry
   MAX-ACCESS  not-accessible
   STATUS      current
   DESCRIPTION
       "Multicast Filtering Profile Address Config table"
 ::= { sispm10403166lIPMCLIB 5 }

sispm10403166lMulticastFilteringProfileAddressConfigEntry OBJECT-TYPE
    SYNTAX        SISPM10403166LMulticastFilteringProfileAddressConfigEntry
    MAX-ACCESS    not-accessible
    STATUS        current
    DESCRIPTION
        "Multicast Filtering Profile Address Config table."
    INDEX        { sispm10403166lMulticastFilteringProfileAddressConfigTableIndex }
    ::= { sispm10403166lMulticastFilteringProfileAddressConfigTable 1 }

SISPM10403166LMulticastFilteringProfileAddressConfigEntry ::=
    SEQUENCE {
        sispm10403166lMulticastFilteringProfileAddressConfigTableIndex     Integer32,
        sispm10403166lMulticastFilteringProfileAddressConfigEntryName      DisplayString,
        sispm10403166lMulticastFilteringProfileAddressConfigStartAddress   DisplayString,
        sispm10403166lMulticastFilteringProfileAddressConfigEndAddress     DisplayString,
        sispm10403166lMulticastFilteringProfileAddressConfigRowStatus      RowStatus
    }

sispm10403166lMulticastFilteringProfileAddressConfigTableIndex OBJECT-TYPE
   SYNTAX      Integer32(1..65535)
   MAX-ACCESS  not-accessible
   STATUS      current
   DESCRIPTION
       "Multicast Filtering Profile Address Config index."
   ::= {sispm10403166lMulticastFilteringProfileAddressConfigEntry 1 }


sispm10403166lMulticastFilteringProfileAddressConfigEntryName OBJECT-TYPE
   SYNTAX      DisplayString
   MAX-ACCESS  read-create
   STATUS      current
   DESCRIPTION
       "Entry Name, Length: 1-16"
   ::= {sispm10403166lMulticastFilteringProfileAddressConfigEntry 2 }

sispm10403166lMulticastFilteringProfileAddressConfigStartAddress OBJECT-TYPE
   SYNTAX      DisplayString
   MAX-ACCESS  read-create
   STATUS      current
   DESCRIPTION
       "IPv4/IPv6 Multicast Group Address"
   ::= {sispm10403166lMulticastFilteringProfileAddressConfigEntry 3 }

sispm10403166lMulticastFilteringProfileAddressConfigEndAddress OBJECT-TYPE
   SYNTAX      DisplayString
   MAX-ACCESS  read-create
   STATUS      current
   DESCRIPTION
       "IPv4/IPv6 Multicast Group Address"
   ::= {sispm10403166lMulticastFilteringProfileAddressConfigEntry 4 }

sispm10403166lMulticastFilteringProfileAddressConfigRowStatus OBJECT-TYPE
   SYNTAX      RowStatus
   MAX-ACCESS  read-create
   STATUS      current
   DESCRIPTION
       "Row Status."
   ::= {sispm10403166lMulticastFilteringProfileAddressConfigEntry 5 }

sispm10403166lEEE    OBJECT IDENTIFIER ::= { sispm10403166lConfiguration 35 }

sispm10403166lPortPowerSavings   OBJECT IDENTIFIER ::= { sispm10403166lEEE 1 }

sispm10403166lEnergyEfficientEthernetConfigTable OBJECT-TYPE
   SYNTAX      SEQUENCE OF SISPM10403166LEnergyEfficientEthernetConfigEntry
   MAX-ACCESS  not-accessible
   STATUS      current
   DESCRIPTION
       " "
   ::= { sispm10403166lPortPowerSavings 2 }

sispm10403166lEnergyEfficientEthernetConfigEntry OBJECT-TYPE
   SYNTAX      SISPM10403166LEnergyEfficientEthernetConfigEntry
   MAX-ACCESS  not-accessible
   STATUS      current
   DESCRIPTION
       " "
   INDEX    { sispm10403166lEnergyEfficientEthernetConfigPort  }
   ::= { sispm10403166lEnergyEfficientEthernetConfigTable 1 }

SISPM10403166LEnergyEfficientEthernetConfigEntry ::= SEQUENCE {
   sispm10403166lEnergyEfficientEthernetConfigPort           Integer32,
   sispm10403166lEnergyEfficientEthernetConfigPortConfig     Integer32
}

sispm10403166lEnergyEfficientEthernetConfigPort OBJECT-TYPE
   SYNTAX      Integer32(1..65535)
   MAX-ACCESS  not-accessible
   STATUS      current
   DESCRIPTION
       "Index"
   ::= { sispm10403166lEnergyEfficientEthernetConfigEntry 1 }

sispm10403166lEnergyEfficientEthernetConfigPortConfig OBJECT-TYPE
   SYNTAX      Integer32
   MAX-ACCESS  read-write
   STATUS      current
   DESCRIPTION
       "Controls whether EEE is enabled for this port.
       0:Disable
       1:Enable"
   ::= { sispm10403166lEnergyEfficientEthernetConfigEntry 2 }

-- =======================================================================================================================

sispm10403166lAggregation    OBJECT IDENTIFIER ::= { sispm10403166lConfiguration 36 }

sispm10403166lAggregationStatic    OBJECT IDENTIFIER ::= { sispm10403166lAggregation 1 }

sispm10403166lAggrSourceMACAddress   OBJECT-TYPE
               SYNTAX      Integer32 (0|1)
               MAX-ACCESS  read-write
               STATUS      current
               DESCRIPTION
                   "Source MAC Address"
               ::= { sispm10403166lAggregationStatic 2 }

sispm10403166lAggrDestinationMACAddress   OBJECT-TYPE
               SYNTAX      Integer32 (0|1)
               MAX-ACCESS  read-write
               STATUS      current
               DESCRIPTION
                   "Destination MAC Address"
               ::= { sispm10403166lAggregationStatic 3 }

sispm10403166lAggrIPAddress   OBJECT-TYPE
               SYNTAX      Integer32 (0|1)
               MAX-ACCESS  read-write
               STATUS      current
               DESCRIPTION
                   "IP Address"
               ::= { sispm10403166lAggregationStatic 4 }

sispm10403166lAggrTCPUDPPortNumber   OBJECT-TYPE
               SYNTAX      Integer32 (0|1)
               MAX-ACCESS  read-write
               STATUS      current
               DESCRIPTION
                   "TCP/UDP Port Number"
               ::= { sispm10403166lAggregationStatic 5 }


sispm10403166lAggrGroupConfigTable OBJECT-TYPE
   SYNTAX      SEQUENCE OF SISPM10403166LAggrGroupConfigEntry
   MAX-ACCESS  not-accessible
   STATUS      current
   DESCRIPTION
       " "
   ::= { sispm10403166lAggregationStatic 6 }

sispm10403166lAggrGroupConfigEntry OBJECT-TYPE
   SYNTAX      SISPM10403166LAggrGroupConfigEntry
   MAX-ACCESS  not-accessible
   STATUS      current
   DESCRIPTION
       " "
   INDEX    { sispm10403166lAggrGroupConfigPort  }
   ::= { sispm10403166lAggrGroupConfigTable 1 }

SISPM10403166LAggrGroupConfigEntry ::= SEQUENCE {
   sispm10403166lAggrGroupConfigPort                 Integer32,
   sispm10403166lAggrGroupConfigGroup                Integer32,
   sispm10403166lAggrGroupConfig                     Integer32
}

sispm10403166lAggrGroupConfigPort OBJECT-TYPE
   SYNTAX      Integer32(1..65535)
   MAX-ACCESS  not-accessible
   STATUS      current
   DESCRIPTION
       "port index"
   ::= { sispm10403166lAggrGroupConfigEntry 1 }

sispm10403166lAggrGroupConfigGroup OBJECT-TYPE
   SYNTAX      Integer32
   MAX-ACCESS  not-accessible
   STATUS      current
   DESCRIPTION
       "group index"
   ::= { sispm10403166lAggrGroupConfigEntry 2 }

sispm10403166lAggrGroupConfig OBJECT-TYPE
   SYNTAX      Integer32 (0|1)
   MAX-ACCESS  read-write
   STATUS      current
   DESCRIPTION
       "Aggregation Group Configuration"
   ::= { sispm10403166lAggrGroupConfigEntry 3 }

sispm10403166lLACPConfiguration    OBJECT IDENTIFIER ::= { sispm10403166lAggregation 2 }

sispm10403166lLACPPortConfigTable OBJECT-TYPE
   SYNTAX      SEQUENCE OF SISPM10403166LLACPPortConfigEntry
   MAX-ACCESS  not-accessible
   STATUS      current
   DESCRIPTION
       " "
   ::= { sispm10403166lLACPConfiguration 1 }

sispm10403166lLACPPortConfigEntry OBJECT-TYPE
   SYNTAX      SISPM10403166LLACPPortConfigEntry
   MAX-ACCESS  not-accessible
   STATUS      current
   DESCRIPTION
       " "
   INDEX    { sispm10403166lLACPPortConfigPort  }
   ::= { sispm10403166lLACPPortConfigTable 1 }

SISPM10403166LLACPPortConfigEntry ::= SEQUENCE {
   sispm10403166lLACPPortConfigPort                  Integer32,
   sispm10403166lLACPPortConfigEnabled               Integer32,
   sispm10403166lLACPPortConfigKey                   Integer32,
   sispm10403166lLACPPortConfigRole                  Integer32,
   sispm10403166lLACPPortConfigTimeout               Integer32,
   sispm10403166lLACPPortConfigPrio                  Integer32
}

sispm10403166lLACPPortConfigPort OBJECT-TYPE
   SYNTAX      Integer32(1..65535)
   MAX-ACCESS  not-accessible
   STATUS      current
   DESCRIPTION
       "port index"
   ::= { sispm10403166lLACPPortConfigEntry 1 }

sispm10403166lLACPPortConfigEnabled OBJECT-TYPE
   SYNTAX      Integer32 (0|1)
   MAX-ACCESS  read-write
   STATUS      current
   DESCRIPTION
       "Controls whether LACP is enabled on this switch port.
       0:Disable
       1:Enable"
   ::= { sispm10403166lLACPPortConfigEntry 2 }

sispm10403166lLACPPortConfigKey OBJECT-TYPE
   SYNTAX      Integer32
   MAX-ACCESS  read-write
   STATUS      current
   DESCRIPTION
       "The Key value incurred by the port, range 1-Number of link aggregations.
       0:autokey."
   ::= { sispm10403166lLACPPortConfigEntry 3 }

sispm10403166lLACPPortConfigRole OBJECT-TYPE
   SYNTAX      Integer32 (0|1)
   MAX-ACCESS  read-write
   STATUS      current
   DESCRIPTION
       "The Role shows the LACP activity status.
       0:Passive
       1:Active"
   ::= { sispm10403166lLACPPortConfigEntry 4 }

sispm10403166lLACPPortConfigTimeout OBJECT-TYPE
   SYNTAX      Integer32 (0|1)
   MAX-ACCESS  read-write
   STATUS      current
   DESCRIPTION
       "The Timeout controls the period between BPDU transmissions.
       0:Slow
       1:Fast"
   ::= { sispm10403166lLACPPortConfigEntry 5 }

sispm10403166lLACPPortConfigPrio OBJECT-TYPE
   SYNTAX      Integer32 (1..65535)
   MAX-ACCESS  read-write
   STATUS      current
   DESCRIPTION
       "The Prio controls the priority of the port."
   ::= { sispm10403166lLACPPortConfigEntry 6 }


sispm10403166lLacpSystemStatus    OBJECT IDENTIFIER ::= { sispm10403166lAggregation 3 }

sispm10403166lLacpSystemStatusTable OBJECT-TYPE
   SYNTAX      SEQUENCE OF SISPM10403166LLacpSystemStatusEntry
   MAX-ACCESS  not-accessible
   STATUS      current
   DESCRIPTION
       " "
   ::= { sispm10403166lLacpSystemStatus 1 }

sispm10403166lLacpSystemStatusEntry OBJECT-TYPE
   SYNTAX      SISPM10403166LLacpSystemStatusEntry
   MAX-ACCESS  not-accessible
   STATUS      current
   DESCRIPTION
       " "
   INDEX    { sispm10403166lLacpSystemStatusIndex  }
   ::= { sispm10403166lLacpSystemStatusTable 1 }

SISPM10403166LLacpSystemStatusEntry ::= SEQUENCE {
   sispm10403166lLacpSystemStatusIndex              Integer32,
   sispm10403166lLacpSystemStatusAggrID             DisplayString,
   sispm10403166lLacpSystemStatusPartnerSystemID    DisplayString,
   sispm10403166lLacpSystemStatusPartnerKey         DisplayString,
   sispm10403166lLacpSystemStatusPartnerPrio        DisplayString,
   sispm10403166lLacpSystemStatusLastChanged        DisplayString,
   sispm10403166lLacpSystemStatusLocalPorts         DisplayString
}

sispm10403166lLacpSystemStatusIndex OBJECT-TYPE
   SYNTAX      Integer32(1..65535)
   MAX-ACCESS  not-accessible
   STATUS      current
   DESCRIPTION
       "index"
   ::= { sispm10403166lLacpSystemStatusEntry 1 }

sispm10403166lLacpSystemStatusAggrID OBJECT-TYPE
   SYNTAX      DisplayString
   MAX-ACCESS  read-only
   STATUS      current
   DESCRIPTION
       "The Aggregation ID associated with this aggregation instance."
   ::= { sispm10403166lLacpSystemStatusEntry 2 }

sispm10403166lLacpSystemStatusPartnerSystemID OBJECT-TYPE
   SYNTAX      DisplayString
   MAX-ACCESS  read-only
   STATUS      current
   DESCRIPTION
       "The system ID (MAC address) of the aggregation partner."
   ::= { sispm10403166lLacpSystemStatusEntry 3 }

sispm10403166lLacpSystemStatusPartnerKey OBJECT-TYPE
   SYNTAX      DisplayString
   MAX-ACCESS  read-only
   STATUS      current
   DESCRIPTION
       "The Key that the partner has assigned to this aggregation ID."
   ::= { sispm10403166lLacpSystemStatusEntry 4 }

sispm10403166lLacpSystemStatusPartnerPrio OBJECT-TYPE
   SYNTAX      DisplayString
   MAX-ACCESS  read-only
   STATUS      current
   DESCRIPTION
       "The priority that the partner has assigned to this aggregation ID."
   ::= { sispm10403166lLacpSystemStatusEntry 5 }

sispm10403166lLacpSystemStatusLastChanged OBJECT-TYPE
   SYNTAX      DisplayString
   MAX-ACCESS  read-only
   STATUS      current
   DESCRIPTION
       "The time since this aggregation changed."
   ::= { sispm10403166lLacpSystemStatusEntry 6 }

sispm10403166lLacpSystemStatusLocalPorts OBJECT-TYPE
   SYNTAX      DisplayString
   MAX-ACCESS  read-only
   STATUS      current
   DESCRIPTION
       "Shows which ports are a part of this aggregation for this switch."
   ::= { sispm10403166lLacpSystemStatusEntry 7 }

sispm10403166lLACPInternalPortStatus    OBJECT IDENTIFIER ::= { sispm10403166lAggregation 4 }

sispm10403166lLACPInternalPortStatusTable OBJECT-TYPE
   SYNTAX      SEQUENCE OF SISPM10403166LLACPInternalPortStatusEntry
   MAX-ACCESS  not-accessible
   STATUS      current
   DESCRIPTION
       " "
   ::= { sispm10403166lLACPInternalPortStatus 1 }

sispm10403166lLACPInternalPortStatusEntry OBJECT-TYPE
   SYNTAX      SISPM10403166LLACPInternalPortStatusEntry
   MAX-ACCESS  not-accessible
   STATUS      current
   DESCRIPTION
       " "
   INDEX    { sispm10403166lLACPInternalPortStatusIndex  }
   ::= { sispm10403166lLACPInternalPortStatusTable 1 }

SISPM10403166LLACPInternalPortStatusEntry ::= SEQUENCE {
   sispm10403166lLACPInternalPortStatusIndex              Integer32,
   sispm10403166lLACPInternalPortStatusPort               DisplayString,
   sispm10403166lLACPInternalPortStatusState              DisplayString,
   sispm10403166lLACPInternalPortStatusKey                DisplayString,
   sispm10403166lLACPInternalPortStatusPriority           DisplayString,
   sispm10403166lLACPInternalPortStatusActivity           DisplayString,
   sispm10403166lLACPInternalPortStatusTimeout            DisplayString,
   sispm10403166lLACPInternalPortStatusAggregation        DisplayString,
   sispm10403166lLACPInternalPortStatusSynchronization    DisplayString,
   sispm10403166lLACPInternalPortStatusCollecting         DisplayString,
   sispm10403166lLACPInternalPortStatusDistributing       DisplayString,
   sispm10403166lLACPInternalPortStatusDefaulted          DisplayString,
   sispm10403166lLACPInternalPortStatusExpired            DisplayString
}

sispm10403166lLACPInternalPortStatusIndex OBJECT-TYPE
   SYNTAX      Integer32(1..65535)
   MAX-ACCESS  not-accessible
   STATUS      current
   DESCRIPTION
       "index"
   ::= { sispm10403166lLACPInternalPortStatusEntry 1 }

sispm10403166lLACPInternalPortStatusPort OBJECT-TYPE
   SYNTAX      DisplayString
   MAX-ACCESS  read-only
   STATUS      current
   DESCRIPTION
       "The switch port number."
   ::= { sispm10403166lLACPInternalPortStatusEntry 2 }

sispm10403166lLACPInternalPortStatusState OBJECT-TYPE
   SYNTAX      DisplayString
   MAX-ACCESS  read-only
   STATUS      current
   DESCRIPTION
       "The current port state:
        Down: The port is not active.
        Active: The port is in active state.
        Standby: The port is in standby state."
   ::= { sispm10403166lLACPInternalPortStatusEntry 3 }

sispm10403166lLACPInternalPortStatusKey OBJECT-TYPE
   SYNTAX      DisplayString
   MAX-ACCESS  read-only
   STATUS      current
   DESCRIPTION
       "The key assigned to this port. Only ports with the same key can aggregate together."
   ::= { sispm10403166lLACPInternalPortStatusEntry 4 }

sispm10403166lLACPInternalPortStatusPriority OBJECT-TYPE
   SYNTAX      DisplayString
   MAX-ACCESS  read-only
   STATUS      current
   DESCRIPTION
       "The priority assigned to this aggregation group."
   ::= { sispm10403166lLACPInternalPortStatusEntry 5 }

sispm10403166lLACPInternalPortStatusActivity OBJECT-TYPE
   SYNTAX      DisplayString
   MAX-ACCESS  read-only
   STATUS      current
   DESCRIPTION
       "The LACP mode of the group (Active or Passive)."
   ::= { sispm10403166lLACPInternalPortStatusEntry 6 }

sispm10403166lLACPInternalPortStatusTimeout OBJECT-TYPE
   SYNTAX      DisplayString
   MAX-ACCESS  read-only
   STATUS      current
   DESCRIPTION
       "The timeout mode configured for the port (Fast or Slow)."
   ::= { sispm10403166lLACPInternalPortStatusEntry 7 }

sispm10403166lLACPInternalPortStatusAggregation OBJECT-TYPE
   SYNTAX      DisplayString
   MAX-ACCESS  read-only
   STATUS      current
   DESCRIPTION
       "Show whether the system considers this link to be aggregateable. i.e., a potential candidate for aggregation."
   ::= { sispm10403166lLACPInternalPortStatusEntry 8 }

sispm10403166lLACPInternalPortStatusSynchronization OBJECT-TYPE
   SYNTAX      DisplayString
   MAX-ACCESS  read-only
   STATUS      current
   DESCRIPTION
       "Show whether the system considers this link to be IN_SYNC."
   ::= { sispm10403166lLACPInternalPortStatusEntry 9 }

sispm10403166lLACPInternalPortStatusCollecting OBJECT-TYPE
   SYNTAX      DisplayString
   MAX-ACCESS  read-only
   STATUS      current
   DESCRIPTION
       "Show if collection of incoming frames on this link is enabled."
   ::= { sispm10403166lLACPInternalPortStatusEntry 10 }

sispm10403166lLACPInternalPortStatusDistributing OBJECT-TYPE
   SYNTAX      DisplayString
   MAX-ACCESS  read-only
   STATUS      current
   DESCRIPTION
       "Show if distribution of outgoing frames on this link is enabled."
   ::= { sispm10403166lLACPInternalPortStatusEntry 11 }

sispm10403166lLACPInternalPortStatusDefaulted OBJECT-TYPE
   SYNTAX      DisplayString
   MAX-ACCESS  read-only
   STATUS      current
   DESCRIPTION
       "Show if the Actor's Receive machine is using Defaulted operational Partner information."
   ::= { sispm10403166lLACPInternalPortStatusEntry 12 }

sispm10403166lLACPInternalPortStatusExpired OBJECT-TYPE
   SYNTAX      DisplayString
   MAX-ACCESS  read-only
   STATUS      current
   DESCRIPTION
       "Show if that the Actor's Receive machine is in the EXPIRED state."
   ::= { sispm10403166lLACPInternalPortStatusEntry 13 }


sispm10403166lLACPNeighborPortStatus    OBJECT IDENTIFIER ::= { sispm10403166lAggregation 5 }

sispm10403166lLACPNeighborPortStatusTable OBJECT-TYPE
   SYNTAX      SEQUENCE OF SISPM10403166LLACPNeighborPortStatusEntry
   MAX-ACCESS  not-accessible
   STATUS      current
   DESCRIPTION
       " "
   ::= { sispm10403166lLACPNeighborPortStatus 1 }

sispm10403166lLACPNeighborPortStatusEntry OBJECT-TYPE
   SYNTAX      SISPM10403166LLACPNeighborPortStatusEntry
   MAX-ACCESS  not-accessible
   STATUS      current
   DESCRIPTION
       " "
   INDEX    { sispm10403166lLACPNeighborPortStatusIndex  }
   ::= { sispm10403166lLACPNeighborPortStatusTable 1 }

SISPM10403166LLACPNeighborPortStatusEntry ::= SEQUENCE {
   sispm10403166lLACPNeighborPortStatusIndex              Integer32,
   sispm10403166lLACPNeighborPortStatusPort               DisplayString,
   sispm10403166lLACPNeighborPortStatusState              DisplayString,
   sispm10403166lLACPNeighborPortStatusAggrID             DisplayString,
   sispm10403166lLACPNeighborPortStatusPartnerKey         DisplayString,
   sispm10403166lLACPNeighborPortStatusPartnerPort        DisplayString,
   sispm10403166lLACPNeighborPortStatusPartnerPortPrio    DisplayString,
   sispm10403166lLACPNeighborPortStatusActivity           DisplayString,
   sispm10403166lLACPNeighborPortStatusTimeout            DisplayString,
   sispm10403166lLACPNeighborPortStatusAggregation        DisplayString,
   sispm10403166lLACPNeighborPortStatusSynchronization    DisplayString,
   sispm10403166lLACPNeighborPortStatusCollecting         DisplayString,
   sispm10403166lLACPNeighborPortStatusDistributing       DisplayString,
   sispm10403166lLACPNeighborPortStatusDefaulted          DisplayString,
   sispm10403166lLACPNeighborPortStatusExpired            DisplayString
}

sispm10403166lLACPNeighborPortStatusIndex OBJECT-TYPE
   SYNTAX      Integer32(1..65535)
   MAX-ACCESS  not-accessible
   STATUS      current
   DESCRIPTION
       "index"
   ::= { sispm10403166lLACPNeighborPortStatusEntry 1 }

sispm10403166lLACPNeighborPortStatusPort OBJECT-TYPE
   SYNTAX      DisplayString
   MAX-ACCESS  read-only
   STATUS      current
   DESCRIPTION
       "The switch port number."
   ::= { sispm10403166lLACPNeighborPortStatusEntry 2 }

sispm10403166lLACPNeighborPortStatusState OBJECT-TYPE
   SYNTAX      DisplayString
   MAX-ACCESS  read-only
   STATUS      current
   DESCRIPTION
       "The current port state:
        Down: The port is not active.
        Active: The port is in active state.
        Standby: The port is in standby state."
   ::= { sispm10403166lLACPNeighborPortStatusEntry 3 }

sispm10403166lLACPNeighborPortStatusAggrID OBJECT-TYPE
   SYNTAX      DisplayString
   MAX-ACCESS  read-only
   STATUS      current
   DESCRIPTION
       "The aggregation group ID which the port is assigned to."
   ::= { sispm10403166lLACPNeighborPortStatusEntry 4 }

sispm10403166lLACPNeighborPortStatusPartnerKey OBJECT-TYPE
   SYNTAX      DisplayString
   MAX-ACCESS  read-only
   STATUS      current
   DESCRIPTION
       "The key assigned to this port by the partner."
   ::= { sispm10403166lLACPNeighborPortStatusEntry 5 }

sispm10403166lLACPNeighborPortStatusPartnerPort OBJECT-TYPE
   SYNTAX      DisplayString
   MAX-ACCESS  read-only
   STATUS      current
   DESCRIPTION
       "The partner port number associated with this link."
   ::= { sispm10403166lLACPNeighborPortStatusEntry 6 }

sispm10403166lLACPNeighborPortStatusPartnerPortPrio OBJECT-TYPE
   SYNTAX      DisplayString
   MAX-ACCESS  read-only
   STATUS      current
   DESCRIPTION
       "The priority assigned to this partner port ."
   ::= { sispm10403166lLACPNeighborPortStatusEntry 7 }

sispm10403166lLACPNeighborPortStatusActivity OBJECT-TYPE
   SYNTAX      DisplayString
   MAX-ACCESS  read-only
   STATUS      current
   DESCRIPTION
       "The LACP mode of the group (Active or Passive)."
   ::= { sispm10403166lLACPNeighborPortStatusEntry 8 }

sispm10403166lLACPNeighborPortStatusTimeout OBJECT-TYPE
   SYNTAX      DisplayString
   MAX-ACCESS  read-only
   STATUS      current
   DESCRIPTION
       "The timeout mode configured for the partner port (Fast or Slow)."
   ::= { sispm10403166lLACPNeighborPortStatusEntry 9 }

sispm10403166lLACPNeighborPortStatusAggregation OBJECT-TYPE
   SYNTAX      DisplayString
   MAX-ACCESS  read-only
   STATUS      current
   DESCRIPTION
       "Show whether the partner considers this link to be aggregateable."
   ::= { sispm10403166lLACPNeighborPortStatusEntry 10 }

sispm10403166lLACPNeighborPortStatusSynchronization OBJECT-TYPE
   SYNTAX      DisplayString
   MAX-ACCESS  read-only
   STATUS      current
   DESCRIPTION
       "Show whether the partner considers this link to be IN_SYNC"
   ::= { sispm10403166lLACPNeighborPortStatusEntry 11 }

sispm10403166lLACPNeighborPortStatusCollecting OBJECT-TYPE
   SYNTAX      DisplayString
   MAX-ACCESS  read-only
   STATUS      current
   DESCRIPTION
       "Show if collection of incoming frames on this link is enabled."
   ::= { sispm10403166lLACPNeighborPortStatusEntry 12 }

sispm10403166lLACPNeighborPortStatusDistributing OBJECT-TYPE
   SYNTAX      DisplayString
   MAX-ACCESS  read-only
   STATUS      current
   DESCRIPTION
       "Show if distribution of outgoing frames on this link is enabled."
   ::= { sispm10403166lLACPNeighborPortStatusEntry 13 }

sispm10403166lLACPNeighborPortStatusDefaulted OBJECT-TYPE
   SYNTAX      DisplayString
   MAX-ACCESS  read-only
   STATUS      current
   DESCRIPTION
       "Show if the partners Receive machine is using Defaulted operational Partner information."
   ::= { sispm10403166lLACPNeighborPortStatusEntry 14 }

sispm10403166lLACPNeighborPortStatusExpired OBJECT-TYPE
   SYNTAX      DisplayString
   MAX-ACCESS  read-only
   STATUS      current
   DESCRIPTION
       "Show if that the partners Receive machine is in the EXPIRED state."
   ::= { sispm10403166lLACPNeighborPortStatusEntry 15 }


sispm10403166lLACPStatus    OBJECT IDENTIFIER ::= { sispm10403166lAggregation 6 }

sispm10403166lLACPStatusTable OBJECT-TYPE
   SYNTAX      SEQUENCE OF SISPM10403166LLACPStatusEntry
   MAX-ACCESS  not-accessible
   STATUS      current
   DESCRIPTION
       " "
   ::= { sispm10403166lLACPStatus 1 }

sispm10403166lLACPStatusEntry OBJECT-TYPE
   SYNTAX      SISPM10403166LLACPStatusEntry
   MAX-ACCESS  not-accessible
   STATUS      current
   DESCRIPTION
       " "
   INDEX    { sispm10403166lLACPStatusPort  }
   ::= { sispm10403166lLACPStatusTable 1 }

SISPM10403166LLACPStatusEntry ::= SEQUENCE {
   sispm10403166lLACPStatusPort               Integer32,
   sispm10403166lLACPStatusLACP               DisplayString,
   sispm10403166lLACPStatusKey                DisplayString,
   sispm10403166lLACPStatusAggrID             DisplayString,
   sispm10403166lLACPStatusPartnerSystemID    DisplayString,
   sispm10403166lLACPStatusPartnerPort        DisplayString,
   sispm10403166lLACPStatusPartnerPrio        DisplayString
}

sispm10403166lLACPStatusPort OBJECT-TYPE
   SYNTAX      Integer32(1..65535)
   MAX-ACCESS  not-accessible
   STATUS      current
   DESCRIPTION
       "index"
   ::= { sispm10403166lLACPStatusEntry 1 }

sispm10403166lLACPStatusLACP OBJECT-TYPE
   SYNTAX      DisplayString
   MAX-ACCESS  read-only
   STATUS      current
   DESCRIPTION
       "Yes: means that LACP is enabled and the port link is up.
       No: means that LACP is not enabled or that the port link is down.
       Backup: means that the port could not join the aggregation group but will join if other port leaves. Meanwhile it's LACP status is disabled."
   ::= { sispm10403166lLACPStatusEntry 2 }

sispm10403166lLACPStatusKey OBJECT-TYPE
   SYNTAX      DisplayString
   MAX-ACCESS  read-only
   STATUS      current
   DESCRIPTION
       "The key assigned to this port. Only ports with the same key can aggregate together."
   ::= { sispm10403166lLACPStatusEntry 3 }

sispm10403166lLACPStatusAggrID OBJECT-TYPE
   SYNTAX      DisplayString
   MAX-ACCESS  read-only
   STATUS      current
   DESCRIPTION
       "The Aggregation ID assigned to this aggregation group."
   ::= { sispm10403166lLACPStatusEntry 4 }

sispm10403166lLACPStatusPartnerSystemID OBJECT-TYPE
   SYNTAX      DisplayString
   MAX-ACCESS  read-only
   STATUS      current
   DESCRIPTION
       "The partner's System ID (MAC address)."
   ::= { sispm10403166lLACPStatusEntry 5 }

sispm10403166lLACPStatusPartnerPort OBJECT-TYPE
   SYNTAX      DisplayString
   MAX-ACCESS  read-only
   STATUS      current
   DESCRIPTION
       "The partner's port number connected to this port."
   ::= { sispm10403166lLACPStatusEntry 6 }

sispm10403166lLACPStatusPartnerPrio OBJECT-TYPE
   SYNTAX      DisplayString
   MAX-ACCESS  read-only
   STATUS      current
   DESCRIPTION
       "The partner's port priority."
   ::= { sispm10403166lLACPStatusEntry 7 }

sispm10403166lAggrGroupStateTable OBJECT-TYPE
   SYNTAX      SEQUENCE OF SISPM10403166LAggrGroupStateEntry
   MAX-ACCESS  not-accessible
   STATUS      current
   DESCRIPTION
       " "
   ::= { sispm10403166lAggregation 7 }

sispm10403166lAggrGroupStateEntry OBJECT-TYPE
   SYNTAX      SISPM10403166LAggrGroupStateEntry
   MAX-ACCESS  not-accessible
   STATUS      current
   DESCRIPTION
       " "
   INDEX    { sispm10403166lAggrGroupStateIndex  }
   ::= { sispm10403166lAggrGroupStateTable 1 }

SISPM10403166LAggrGroupStateEntry ::= SEQUENCE {
   sispm10403166lAggrGroupStateIndex             Integer32,
   sispm10403166lAggrGroupStateAggrID            DisplayString,
   sispm10403166lAggrGroupStateName              DisplayString,
   sispm10403166lAggrGroupStateType              DisplayString,
   sispm10403166lAggrGroupStateSpeed             DisplayString,
   sispm10403166lAggrGroupStateConfiguredPorts   DisplayString,
   sispm10403166lAggrGroupStateAggregatedPorts   DisplayString,
   sispm10403166lAggrGroupStateAggregatedBandwidth   DisplayString
}

sispm10403166lAggrGroupStateIndex OBJECT-TYPE
   SYNTAX      Integer32(1..65535)
   MAX-ACCESS  not-accessible
   STATUS      current
   DESCRIPTION
       "index"
   ::= { sispm10403166lAggrGroupStateEntry 1 }

sispm10403166lAggrGroupStateAggrID OBJECT-TYPE
   SYNTAX      DisplayString
   MAX-ACCESS  read-only
   STATUS      current
   DESCRIPTION
       "AggrID"
   ::= { sispm10403166lAggrGroupStateEntry 2 }

sispm10403166lAggrGroupStateName OBJECT-TYPE
   SYNTAX      DisplayString
   MAX-ACCESS  read-only
   STATUS      current
   DESCRIPTION
       "Name"
   ::= { sispm10403166lAggrGroupStateEntry 3 }

sispm10403166lAggrGroupStateType OBJECT-TYPE
   SYNTAX      DisplayString
   MAX-ACCESS  read-only
   STATUS      current
   DESCRIPTION
       "Type"
   ::= { sispm10403166lAggrGroupStateEntry 4 }

sispm10403166lAggrGroupStateSpeed OBJECT-TYPE
   SYNTAX      DisplayString
   MAX-ACCESS  read-only
   STATUS      current
   DESCRIPTION
       "Speed"
   ::= { sispm10403166lAggrGroupStateEntry 5 }

sispm10403166lAggrGroupStateConfiguredPorts OBJECT-TYPE
   SYNTAX      DisplayString
   MAX-ACCESS  read-only
   STATUS      current
   DESCRIPTION
       "Configured Ports"
   ::= { sispm10403166lAggrGroupStateEntry 6 }

sispm10403166lAggrGroupStateAggregatedPorts OBJECT-TYPE
   SYNTAX      DisplayString
   MAX-ACCESS  read-only
   STATUS      current
   DESCRIPTION
       "Aggregated Ports"
   ::= { sispm10403166lAggrGroupStateEntry 7 }

sispm10403166lAggrGroupStateAggregatedBandwidth OBJECT-TYPE
   SYNTAX      DisplayString
   MAX-ACCESS  read-only
   STATUS      current
   DESCRIPTION
       "Aggregated Bandwidth"
   ::= { sispm10403166lAggrGroupStateEntry 8 }

-- =======================================================================================================================
sispm10403166lSecurity                                              OBJECT IDENTIFIER ::= { sispm10403166lProductId 3 }

sispm10403166lIPSourceGuard                                         OBJECT IDENTIFIER ::= { sispm10403166lSecurity 1 }

sispm10403166lIPSourceGuardConf                                     OBJECT IDENTIFIER ::= { sispm10403166lIPSourceGuard 1 }

-- RowStatus Info:  createAndGo, notReady not supported.
-- =======================================================================================================================
-- Textual Conventions for the SISPM10403166L IP Source Guard Mib
-- =======================================================================================================================
--
--    sispm10403166lIPSourceGuard        OBJECT IDENTIFIER  ::= { sispm10403166lIPSourceGuardMIB 1 }
--    sispm10403166lIPSourceGuardConf    OBJECT IDENTIFIER  ::= { sispm10403166lIPSourceGuard 1 }

--
-- =======================================================================================================================
-- Start sispm10403166lIPSourceGuard group
-- =======================================================================================================================
--sispm10403166lIPSourceGuardConf

    sispm10403166lIPSourceGuardMode OBJECT-TYPE
               SYNTAX      AdminMode
               MAX-ACCESS  read-write
               STATUS      current
               DESCRIPTION
                   "Enable the Global IP Source Guard or disable the
                    Global IP Source Guard."
               ::= {     sispm10403166lIPSourceGuardConf 1 }

    sispm10403166lIPSourceGuardDynamicToStaticCmd OBJECT-TYPE
               SYNTAX      ActivateCmd
               MAX-ACCESS  read-write
               STATUS      current
               DESCRIPTION
                   "Translate all dynamic entries to static entries."
               DEFVAL  { noAction }
               ::= {     sispm10403166lIPSourceGuardConf 2 }

--sispm10403166lIPSourceGuardPortConfigTable

    sispm10403166lIPSourceGuardPortConfigTable OBJECT-TYPE
               SYNTAX      SEQUENCE OF     SISPM10403166LIPSourceGuardPortConfigEntry
               MAX-ACCESS  not-accessible
               STATUS      current
               DESCRIPTION
                   "The IP Source Guard Port Configuration Table.
                    INDEX for this table is ifIndex which is
                    equivalent to the panel port number."
               ::= {     sispm10403166lIPSourceGuardConf 3 }

    sispm10403166lIPSourceGuardPortConfigEntry OBJECT-TYPE
               SYNTAX          SISPM10403166LIPSourceGuardPortConfigEntry
               MAX-ACCESS  not-accessible
               STATUS      current
               DESCRIPTION
                   "The IP Source Guard Port Configuration Entry."
               INDEX    {    ifIndex  }
               ::= {     sispm10403166lIPSourceGuardPortConfigTable 1 }

    SISPM10403166LIPSourceGuardPortConfigEntry             ::= SEQUENCE {
                 sispm10403166lIPSourceGuardPortConfigMode            AdminMode,
                 sispm10403166lIPSourceGuardPortMaxDynamicClients     Integer32
                 }

    sispm10403166lIPSourceGuardPortConfigMode OBJECT-TYPE
               SYNTAX      AdminMode
               MAX-ACCESS  read-write
               STATUS      current
               DESCRIPTION
                   "Specify IP Source Guard is enabled on which ports."
               ::= {     sispm10403166lIPSourceGuardPortConfigEntry 2 }

    sispm10403166lIPSourceGuardPortMaxDynamicClients OBJECT-TYPE
               SYNTAX      Integer32(0..2|99)
               MAX-ACCESS  read-write
               STATUS      current
               DESCRIPTION
                   "Specify the maximum number of dynamic clients that can
                    be learned on given port.
                    default: 99
                    0~2: Max Dynamic clients
                    99:Unlimited "
               ::= {     sispm10403166lIPSourceGuardPortConfigEntry 3 }

--sispm10403166lIPSourceGuardStaticTable

    sispm10403166lIPSourceGuardStaticTable OBJECT-TYPE
               SYNTAX      SEQUENCE OF     SISPM10403166LIPSourceGuardStaticEntry
               MAX-ACCESS  not-accessible
               STATUS      current
               DESCRIPTION
                   "The IP Source Guard Static Table."
               ::= {     sispm10403166lIPSourceGuard 2 }

    sispm10403166lIPSourceGuardStaticEntry OBJECT-TYPE
               SYNTAX          SISPM10403166LIPSourceGuardStaticEntry
               MAX-ACCESS  not-accessible
               STATUS      current
               DESCRIPTION
                   "The IP Source Guard Static Entry."
               INDEX    {    sispm10403166lIPSourceGuardStaticIndex  }
               ::= {     sispm10403166lIPSourceGuardStaticTable 1 }

    SISPM10403166LIPSourceGuardStaticEntry             ::= SEQUENCE {
                 sispm10403166lIPSourceGuardStaticSwitchIndex   Integer32,
                 sispm10403166lIPSourceGuardStaticIndex         Integer32,
                 sispm10403166lIPSourceGuardStaticPort          Integer32,
                 sispm10403166lIPSourceGuardStaticVLANId        Integer32,
                 sispm10403166lIPSourceGuardStaticIPAddress     IpAddress,
--                 sispm10403166lIPSourceGuardStaticIPMask        IpAddress,
                 sispm10403166lIPSourceGuardStaticMACAddress    DisplayString,
                 sispm10403166lIPSourceGuardStaticRowStatus     RowStatus
                 }

    sispm10403166lIPSourceGuardStaticSwitchIndex OBJECT-TYPE
               SYNTAX      Integer32(1..16)
               MAX-ACCESS  not-accessible
               STATUS      current
               DESCRIPTION
                   "Switch Index."
               ::= {     sispm10403166lIPSourceGuardStaticEntry 1 }

    sispm10403166lIPSourceGuardStaticIndex OBJECT-TYPE
               SYNTAX      Integer32(1..28)
               MAX-ACCESS  not-accessible
               STATUS      current
               DESCRIPTION
                   "The entry of table."
               ::= {     sispm10403166lIPSourceGuardStaticEntry 2 }

    sispm10403166lIPSourceGuardStaticPort OBJECT-TYPE
               SYNTAX      Integer32(1..255)
               MAX-ACCESS  read-create
               STATUS      current
               DESCRIPTION
                   "The port number of table.
                    range: 1 - port number."
               ::= {     sispm10403166lIPSourceGuardStaticEntry 3 }

    sispm10403166lIPSourceGuardStaticVLANId OBJECT-TYPE
               SYNTAX      Integer32(1..4095)
               MAX-ACCESS  read-create
               STATUS      current
               DESCRIPTION
                   "VLAN ID, range: 1 - 4095."
               ::= {     sispm10403166lIPSourceGuardStaticEntry 4 }

    sispm10403166lIPSourceGuardStaticIPAddress OBJECT-TYPE
               SYNTAX      IpAddress
               MAX-ACCESS  read-create
               STATUS      current
               DESCRIPTION
                   "IP address allowed for doing IP source guard."
               ::= {     sispm10403166lIPSourceGuardStaticEntry 5 }

--    sispm10403166lIPSourceGuardStaticIPMask OBJECT-TYPE
--               SYNTAX      IpAddress
--               MAX-ACCESS  read-create
--               STATUS      current
--               DESCRIPTION
--                   "IP Mask allowed for doing IP source guard."
--               ::= {     sispm10403166lIPSourceGuardStaticEntry 6 }

    sispm10403166lIPSourceGuardStaticMACAddress OBJECT-TYPE
               SYNTAX      DisplayString
               MAX-ACCESS  read-create
               STATUS      current
               DESCRIPTION
                   "Allowed Source MAC address, format: 0a 1b 2c 3d 4e 5f."
               ::= {     sispm10403166lIPSourceGuardStaticEntry 7 }

    sispm10403166lIPSourceGuardStaticRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sispm10403166lIPSourceGuardStaticEntry 8 }

--sispm10403166lIPSourceGuardDynamicTable

    sispm10403166lIPSourceGuardDynamicTable OBJECT-TYPE
               SYNTAX      SEQUENCE OF     SISPM10403166LIPSourceGuardDynamicEntry
               MAX-ACCESS  not-accessible
               STATUS      current
               DESCRIPTION
                   "The IP Source Guard Dynamic Table."
               ::= {     sispm10403166lIPSourceGuard 3 }

    sispm10403166lIPSourceGuardDynamicEntry OBJECT-TYPE
               SYNTAX          SISPM10403166LIPSourceGuardDynamicEntry
               MAX-ACCESS  not-accessible
               STATUS      current
               DESCRIPTION
                   "The IP Source Guard Dynamic Entry."
               INDEX    {    sispm10403166lIPSourceGuardDynamicIndex  }
               ::= {     sispm10403166lIPSourceGuardDynamicTable 1 }

    SISPM10403166LIPSourceGuardDynamicEntry             ::= SEQUENCE {
                 sispm10403166lIPSourceGuardDynamicSwitchIndex    Integer32,
                 sispm10403166lIPSourceGuardDynamicIndex          Integer32,
                 sispm10403166lIPSourceGuardDynamicPort           Integer32,
                 sispm10403166lIPSourceGuardDynamicVLANId         Integer32,
                 sispm10403166lIPSourceGuardDynamicIPAddress      IpAddress,
                 sispm10403166lIPSourceGuardDynamicMACAddress     DisplayString
                 }

    sispm10403166lIPSourceGuardDynamicSwitchIndex OBJECT-TYPE
               SYNTAX      Integer32(1..16)
               MAX-ACCESS  not-accessible
               STATUS      current
               DESCRIPTION
                   "Switch Index."
               ::= {     sispm10403166lIPSourceGuardDynamicEntry 1 }

    sispm10403166lIPSourceGuardDynamicIndex OBJECT-TYPE
               SYNTAX      Integer32(1..4095)
               MAX-ACCESS  not-accessible
               STATUS      current
               DESCRIPTION
                   "The entry of table."
               ::= {     sispm10403166lIPSourceGuardDynamicEntry 2 }

    sispm10403166lIPSourceGuardDynamicPort OBJECT-TYPE
               SYNTAX      Integer32(1..255)
               MAX-ACCESS  read-only
               STATUS      current
               DESCRIPTION
                   "The logical port for the settings."
               ::= {     sispm10403166lIPSourceGuardDynamicEntry 3 }

    sispm10403166lIPSourceGuardDynamicVLANId OBJECT-TYPE
               SYNTAX      Integer32(1..4094)
               MAX-ACCESS  read-only
               STATUS      current
               DESCRIPTION
                   "The vlan id for the settings."
               ::= {     sispm10403166lIPSourceGuardDynamicEntry 4 }

    sispm10403166lIPSourceGuardDynamicIPAddress OBJECT-TYPE
               SYNTAX      IpAddress
               MAX-ACCESS  read-only
               STATUS      current
               DESCRIPTION
                   "Allowed Source IP address."
               ::= {     sispm10403166lIPSourceGuardDynamicEntry 5 }

    sispm10403166lIPSourceGuardDynamicMACAddress OBJECT-TYPE
               SYNTAX      DisplayString
               MAX-ACCESS  read-only
               STATUS      current
               DESCRIPTION
                   "Allowed Source MAC address."
               ::= {     sispm10403166lIPSourceGuardDynamicEntry 6 }
-- =======================================================================================================================
sispm10403166lARPInspection                                          OBJECT IDENTIFIER ::= { sispm10403166lSecurity 2 }
-- RowStatus Info:  createAndGo, notReady not supported.
-- =======================================================================================================================
-- Textual Conventions for the sispm10403166l Arp Mib
-- =======================================================================================================================
--
    sispm10403166lARP                  OBJECT IDENTIFIER  ::= { sispm10403166lARPInspection 1 }
    sispm10403166lARPConfig            OBJECT IDENTIFIER  ::= { sispm10403166lARP 1 }

--
-- =======================================================================================================================
-- Start sispm10403166lARP group
-- =======================================================================================================================
--sispm10403166lARPConfig

    sispm10403166lARPConfMode OBJECT-TYPE
               SYNTAX      AdminMode
               MAX-ACCESS  read-write
               STATUS      current
               DESCRIPTION
                   "Enable the Global ARP Inspection or disable the Global
                    ARP Inspection."
               ::= {     sispm10403166lARPConfig 1 }

--sispm10403166lARPPortConfTable

    sispm10403166lARPPortConfTable OBJECT-TYPE
               SYNTAX      SEQUENCE OF     SISPM10403166LARPPortConfEntry
               MAX-ACCESS  not-accessible
               STATUS      current
               DESCRIPTION
                   "The ARP Port Configuration Table."
               ::= {     sispm10403166lARPConfig 3 }

    sispm10403166lARPPortConfEntry OBJECT-TYPE
               SYNTAX          SISPM10403166LARPPortConfEntry
               MAX-ACCESS  not-accessible
               STATUS      current
               DESCRIPTION
                   "The ARP Port Configuration Entry."
               INDEX    {    sispm10403166lARPPortConfPort  }
               ::= {     sispm10403166lARPPortConfTable 1 }

    SISPM10403166LARPPortConfEntry             ::= SEQUENCE {
                 sispm10403166lARPPortConfPort            Integer32,
                 sispm10403166lARPPortConfMode            AdminMode,
                 sispm10403166lARPPortConfCheckVLAN       AdminMode,
                 sispm10403166lARPPortConfLogType         INTEGER
                 }

    sispm10403166lARPPortConfPort OBJECT-TYPE
               SYNTAX      Integer32(1..255)
               MAX-ACCESS  not-accessible
               STATUS      current
               DESCRIPTION
                   "The port number for which the configuration below applies.
                    range: 1 - port number."
               ::= {     sispm10403166lARPPortConfEntry 1 }

    sispm10403166lARPPortConfMode OBJECT-TYPE
               SYNTAX      AdminMode
               MAX-ACCESS  read-write
               STATUS      current
               DESCRIPTION
                   "Specify ARP Inspection is enabled on which ports."
               ::= {     sispm10403166lARPPortConfEntry 2 }

    sispm10403166lARPPortConfCheckVLAN OBJECT-TYPE
               SYNTAX      AdminMode
               MAX-ACCESS  read-write
               STATUS      current
               DESCRIPTION
                   "When the setting of 'Check VLAN' is disabled, the log
                   type of ARP Inspection will refer to the port setting.
                   And the setting of 'Check VLAN' is enabled, the log type
                   of ARP Inspection will refer to the VLAN setting."
               ::= {     sispm10403166lARPPortConfEntry 3 }

    sispm10403166lARPPortConfLogType OBJECT-TYPE
               SYNTAX      INTEGER{none(0),deny(1),permit(2),all(3)}
               MAX-ACCESS  read-write
               STATUS      current
               DESCRIPTION
                   "The log type of ARP Inspection will refer to the
                    port setting.
                    0: none,
                    1: deny,
                    2: permit,
                    3: all,
                    range: 0-3."
               ::= {     sispm10403166lARPPortConfEntry 4 }

--sispm10403166lARPVlanConfig

    sispm10403166lARPVlanConfigTable OBJECT-TYPE
               SYNTAX      SEQUENCE OF     SISPM10403166LARPVlanConfigEntry
               MAX-ACCESS  not-accessible
               STATUS      current
               DESCRIPTION
                   "The ARP Vlan Configuration Table."
               ::= {     sispm10403166lARP 2 }

    sispm10403166lARPVlanConfigEntry OBJECT-TYPE
               SYNTAX          SISPM10403166LARPVlanConfigEntry
               MAX-ACCESS  not-accessible
               STATUS      current
               DESCRIPTION
                   "The ARP Vlan Configuration Entry."
               INDEX    {    sispm10403166lARPVlanConfigVlan  }
               ::= {     sispm10403166lARPVlanConfigTable 1 }

    SISPM10403166LARPVlanConfigEntry             ::= SEQUENCE {
                 sispm10403166lARPPortConfigIndex      Integer32,
                 sispm10403166lARPVlanConfigVlan       Integer32,
                 sispm10403166lARPVlanConfigLogType    INTEGER,
                 sispm10403166lARPVlanConfigRowStatus  RowStatus
                 }

    sispm10403166lARPPortConfigIndex OBJECT-TYPE
               SYNTAX      Integer32(1..4095)
               MAX-ACCESS  not-accessible
               STATUS      current
               DESCRIPTION
                   "The Index of Vlan config Table"
               ::= {     sispm10403166lARPVlanConfigEntry 1 }

    sispm10403166lARPVlanConfigVlan OBJECT-TYPE
               SYNTAX      Integer32(1..4095)
               MAX-ACCESS  read-create
               STATUS      current
               DESCRIPTION
                   "Specify ARP Inspection is enabled on which VLANs.
                    range: 1 - 4095."
               ::= {     sispm10403166lARPVlanConfigEntry 2 }

    sispm10403166lARPVlanConfigLogType OBJECT-TYPE
               SYNTAX      INTEGER{none(0),deny(1),permit(2),all(3)}
               MAX-ACCESS  read-create
               STATUS      current
               DESCRIPTION
                   "The log type also can be configured on per VLAN setting.
                    0: none,
                    1: deny,
                    2: permit,
                    3: all,
                    range: 0-3."
               ::= {     sispm10403166lARPVlanConfigEntry 3 }

    sispm10403166lARPVlanConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sispm10403166lARPVlanConfigEntry 4 }

--sispm10403166lARPStaticTable

    sispm10403166lARPStaticTable OBJECT-TYPE
               SYNTAX      SEQUENCE OF     SISPM10403166LARPStaticEntry
               MAX-ACCESS  not-accessible
               STATUS      current
               DESCRIPTION
                   "The ARP Static Table."
               ::= {     sispm10403166lARP 3 }

    sispm10403166lARPStaticEntry OBJECT-TYPE
               SYNTAX          SISPM10403166LARPStaticEntry
               MAX-ACCESS  not-accessible
               STATUS      current
               DESCRIPTION
                   "The ARP Static Entry."
               INDEX    {    sispm10403166lARPStaticIndex  }
               ::= {     sispm10403166lARPStaticTable 1 }

    SISPM10403166LARPStaticEntry             ::= SEQUENCE {
                 sispm10403166lARPStaticSwitchIndex   Integer32,
                 sispm10403166lARPStaticIndex         Integer32,
                 sispm10403166lARPStaticPort          Integer32,
                 sispm10403166lARPStaticVlanID        Integer32,
                 sispm10403166lARPStaticMACAddress    DisplayString,
                 sispm10403166lARPStaticIPAddress     IpAddress,
                 sispm10403166lARPStaticRowStatus     RowStatus
                 }


    sispm10403166lARPStaticSwitchIndex OBJECT-TYPE
               SYNTAX      Integer32(1..16)
               MAX-ACCESS  not-accessible
               STATUS      current
               DESCRIPTION
                   "Switch Index."
               ::= {     sispm10403166lARPStaticEntry 1 }

    sispm10403166lARPStaticIndex OBJECT-TYPE
               SYNTAX      Integer32(1..255)
               MAX-ACCESS  not-accessible
               STATUS      current
               DESCRIPTION
                   "The entry of table."
               ::= {     sispm10403166lARPStaticEntry 2 }

    sispm10403166lARPStaticPort OBJECT-TYPE
               SYNTAX      Integer32(1..255)
               MAX-ACCESS  read-create
               STATUS      current
               DESCRIPTION
                   "The logical port for the settings.
                    range: 1 - port number."
               ::= {     sispm10403166lARPStaticEntry 3 }

    sispm10403166lARPStaticVlanID OBJECT-TYPE
               SYNTAX      Integer32(1..4095)
               MAX-ACCESS  read-create
               STATUS      current
               DESCRIPTION
                   "The vlan id for the settings.
                    range: 1-4095."
               ::= {     sispm10403166lARPStaticEntry 4 }

    sispm10403166lARPStaticMACAddress OBJECT-TYPE
               SYNTAX      DisplayString
               MAX-ACCESS  read-create
               STATUS      current
               DESCRIPTION
                   "Allowed Source MAC address in ARP request packets."
               ::= {     sispm10403166lARPStaticEntry 5 }

    sispm10403166lARPStaticIPAddress OBJECT-TYPE
               SYNTAX      IpAddress
               MAX-ACCESS  read-create
               STATUS      current
               DESCRIPTION
                   "Allowed Source IP address in ARP request packets."
               ::= {     sispm10403166lARPStaticEntry 6 }

    sispm10403166lARPStaticRowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sispm10403166lARPStaticEntry 7 }

--sispm10403166lARPDynamicTable

    sispm10403166lARPDynamicTable OBJECT-TYPE
               SYNTAX      SEQUENCE OF     SISPM10403166LARPDynamicEntry
               MAX-ACCESS  not-accessible
               STATUS      current
               DESCRIPTION
                   "The ARP Dynamic Table."
               ::= {    sispm10403166lARP 4 }

    sispm10403166lARPDynamicEntry OBJECT-TYPE
               SYNTAX          SISPM10403166LARPDynamicEntry
               MAX-ACCESS  not-accessible
               STATUS      current
               DESCRIPTION
                   "The ARP Dynamic Entry."
               INDEX    {   sispm10403166lARPDynamicIndex  }
               ::= {    sispm10403166lARPDynamicTable 1 }

    SISPM10403166LARPDynamicEntry             ::= SEQUENCE {
                 sispm10403166lARPDynamicIndex          Integer32,
                 sispm10403166lARPDynamicPort           Integer32,
                 sispm10403166lARPDynamicVLANId         Integer32,
                 sispm10403166lARPDynamicMACAddress     MacAddress,
                 sispm10403166lARPDynamicIPAddress      IpAddress,
                 sispm10403166lARPDynamicToStaticCmd    INTEGER
                 }

    sispm10403166lARPDynamicIndex OBJECT-TYPE
               SYNTAX      Integer32(1..4095)
               MAX-ACCESS  not-accessible
               STATUS      current
               DESCRIPTION
                   "The entry of table."
               ::= {    sispm10403166lARPDynamicEntry 1 }

    sispm10403166lARPDynamicPort OBJECT-TYPE
               SYNTAX      Integer32(1..255)
               MAX-ACCESS  read-only
               STATUS      current
               DESCRIPTION
                   "Switch Port Number for which the entries are displayed."
               ::= {    sispm10403166lARPDynamicEntry 2 }

    sispm10403166lARPDynamicVLANId OBJECT-TYPE
               SYNTAX      Integer32(1..4095)
               MAX-ACCESS  read-only
               STATUS      current
               DESCRIPTION
                   "VLAN-ID in which the ARP traffic is permitted."
               ::= {    sispm10403166lARPDynamicEntry 3 }

    sispm10403166lARPDynamicMACAddress OBJECT-TYPE
               SYNTAX      MacAddress
               MAX-ACCESS  read-only
               STATUS      current
               DESCRIPTION
                   "User MAC address of the entry."
               ::= {    sispm10403166lARPDynamicEntry 4 }

    sispm10403166lARPDynamicIPAddress OBJECT-TYPE
               SYNTAX      IpAddress
               MAX-ACCESS  read-only
               STATUS      current
               DESCRIPTION
                   "User IP address of the entry."
               ::= {    sispm10403166lARPDynamicEntry 5 }

    sispm10403166lARPDynamicToStaticCmd OBJECT-TYPE
               SYNTAX      ActivateCmd
               MAX-ACCESS  read-write
               STATUS      current
               DESCRIPTION
                   "Enable the Global ARP Inspection or disable the Global
                    ARP Inspection."
               ::= {     sispm10403166lARPDynamicEntry 6 }


-- =======================================================================================================================
-- sispm10403166lARPConformance
-- =======================================================================================================================
sispm10403166lARPConformance OBJECT IDENTIFIER ::= { sispm10403166lARPInspection 200 }

sispm10403166lARPCompliances OBJECT IDENTIFIER ::= { sispm10403166lARPConformance 1 }

sispm10403166lARPGroups      OBJECT IDENTIFIER ::= { sispm10403166lARPConformance 2 }

sispm10403166lARPGroup OBJECT-GROUP
    OBJECTS {
                -- sispm10403166lARPConfig
                sispm10403166lARPConfMode,

                --sispm10403166lARPPortConfTable
                sispm10403166lARPPortConfMode,
                sispm10403166lARPPortConfCheckVLAN,
                sispm10403166lARPPortConfLogType,

                --sispm10403166lARPVlanConfig
                sispm10403166lARPVlanConfigLogType,
                sispm10403166lARPVlanConfigRowStatus,

                --sispm10403166lARPStaticTable
                sispm10403166lARPStaticPort,
                sispm10403166lARPStaticVlanID,
                sispm10403166lARPStaticMACAddress,
                sispm10403166lARPStaticIPAddress,
                sispm10403166lARPStaticRowStatus,

                --sispm10403166lARPDynamicTable
                sispm10403166lARPDynamicPort,
                sispm10403166lARPDynamicVLANId,
                sispm10403166lARPDynamicMACAddress,
                sispm10403166lARPDynamicIPAddress,
                sispm10403166lARPDynamicToStaticCmd
            }
     STATUS  current
     DESCRIPTION
            "The collection of objects which are used to indicate
            sispm10403166l ARP information."
    ::= { sispm10403166lARPGroups 1 }

-- =======================================================================================================================
sispm10403166lDHCPSnooping                                          OBJECT IDENTIFIER ::= { sispm10403166lSecurity 3 }

sispm10403166lDHCPSnoopingConf                                          OBJECT IDENTIFIER ::= { sispm10403166lDHCPSnooping 1 }

sispm10403166lDHCPSnoopingMode OBJECT-TYPE
   SYNTAX      Integer32(0|1)
   MAX-ACCESS  read-write
   STATUS      current
   DESCRIPTION
       "default: 0
       0: disable
       1: enable"
   ::= { sispm10403166lDHCPSnoopingConf 1 }

sispm10403166lDHCPSnoopingPortModeConfigurationTable OBJECT-TYPE
   SYNTAX      SEQUENCE OF SISPM10403166LDHCPSnoopingPortModeConfigurationEntry
   MAX-ACCESS  not-accessible
   STATUS      current
   DESCRIPTION
       " "
   ::= { sispm10403166lDHCPSnoopingConf 2 }

sispm10403166lDHCPSnoopingPortModeConfigurationEntry OBJECT-TYPE
   SYNTAX      SISPM10403166LDHCPSnoopingPortModeConfigurationEntry
   MAX-ACCESS  not-accessible
   STATUS      current
   DESCRIPTION
       " "
   INDEX    { sispm10403166lDHCPSnoopingPortModeConfigurationPort  }
   ::= { sispm10403166lDHCPSnoopingPortModeConfigurationTable 1 }

SISPM10403166LDHCPSnoopingPortModeConfigurationEntry ::= SEQUENCE {
   sispm10403166lDHCPSnoopingPortModeConfigurationPort	Integer32,
   sispm10403166lDHCPSnoopingPortModeConfigurationMode	Integer32
}

sispm10403166lDHCPSnoopingPortModeConfigurationPort OBJECT-TYPE
   SYNTAX      Integer32(1..4095)
   MAX-ACCESS  not-accessible
   STATUS      current
   DESCRIPTION
       " "
   ::= { sispm10403166lDHCPSnoopingPortModeConfigurationEntry 1 }

sispm10403166lDHCPSnoopingPortModeConfigurationMode OBJECT-TYPE
   SYNTAX      Integer32 (0|1)
   MAX-ACCESS  read-write
   STATUS      current
   DESCRIPTION
       "default: 1
       0: trust port mode
       1: untrust port mode"
   ::= { sispm10403166lDHCPSnoopingPortModeConfigurationEntry 2 }

sispm10403166lDHCPSnoopingStatisticsTable OBJECT-TYPE
   SYNTAX      SEQUENCE OF SISPM10403166LDHCPSnoopingStatisticsEntry
   MAX-ACCESS  not-accessible
   STATUS      current
   DESCRIPTION
       " "
   ::= { sispm10403166lDHCPSnooping 2 }

sispm10403166lDHCPSnoopingStatisticsEntry OBJECT-TYPE
   SYNTAX      SISPM10403166LDHCPSnoopingStatisticsEntry
   MAX-ACCESS  not-accessible
   STATUS      current
   DESCRIPTION
       " "
   INDEX    { sispm10403166lDHCPSnoopingStatisticsPort  }
   ::= { sispm10403166lDHCPSnoopingStatisticsTable 1 }

SISPM10403166LDHCPSnoopingStatisticsEntry ::= SEQUENCE {
   sispm10403166lDHCPSnoopingStatisticsPort         Integer32,
   sispm10403166lDHCPSnoopingStatisticsClear        Integer32,
   sispm10403166lDHCPSnoopingRxDiscover             Counter32,
   sispm10403166lDHCPSnoopingRxOffer                Counter32,
   sispm10403166lDHCPSnoopingRxRequest              Counter32,
   sispm10403166lDHCPSnoopingRxDecline              Counter32,
   sispm10403166lDHCPSnoopingRxACK                  Counter32,
   sispm10403166lDHCPSnoopingRxNAK                  Counter32,
   sispm10403166lDHCPSnoopingRxRelease              Counter32,
   sispm10403166lDHCPSnoopingRxInform               Counter32,
   sispm10403166lDHCPSnoopingRxLeaseQuery           Counter32,
   sispm10403166lDHCPSnoopingRxLeaseUnassigned      Counter32,
   sispm10403166lDHCPSnoopingRxLeaseUnknown         Counter32,
   sispm10403166lDHCPSnoopingRxLeaseActive          Counter32,
   sispm10403166lDHCPSnoopingTxDiscover             Counter32,
   sispm10403166lDHCPSnoopingTxOffer                Counter32,
   sispm10403166lDHCPSnoopingTxRequest              Counter32,
   sispm10403166lDHCPSnoopingTxDecline              Counter32,
   sispm10403166lDHCPSnoopingTxACK                  Counter32,
   sispm10403166lDHCPSnoopingTxNAK                  Counter32,
   sispm10403166lDHCPSnoopingTxRelease              Counter32,
   sispm10403166lDHCPSnoopingTxInform               Counter32,
   sispm10403166lDHCPSnoopingTxLeaseQuery           Counter32,
   sispm10403166lDHCPSnoopingTxLeaseUnassigned      Counter32,
   sispm10403166lDHCPSnoopingTxLeaseUnknown         Counter32,
   sispm10403166lDHCPSnoopingTxLeaseActive          Counter32,
   sispm10403166lDHCPSnoopingRxDiscardedChecksumError  Counter32,
   sispm10403166lDHCPSnoopingRxDiscardedFromUntrusted  Counter32
}

sispm10403166lDHCPSnoopingStatisticsPort OBJECT-TYPE
   SYNTAX      Integer32(1..4095)
   MAX-ACCESS  not-accessible
   STATUS      current
   DESCRIPTION
       " "
   ::= { sispm10403166lDHCPSnoopingStatisticsEntry 1 }

sispm10403166lDHCPSnoopingStatisticsClear OBJECT-TYPE
   SYNTAX      Integer32 (0|1)
   MAX-ACCESS  read-write
   STATUS      current
   DESCRIPTION
       "default: 0
       0: none
       1: clear"
   ::= { sispm10403166lDHCPSnoopingStatisticsEntry 2 }

sispm10403166lDHCPSnoopingRxDiscover OBJECT-TYPE
   SYNTAX      Counter32
   MAX-ACCESS  read-only
   STATUS      current
   DESCRIPTION
       " "
   ::= { sispm10403166lDHCPSnoopingStatisticsEntry 3 }

sispm10403166lDHCPSnoopingRxOffer OBJECT-TYPE
   SYNTAX      Counter32
   MAX-ACCESS  read-only
   STATUS      current
   DESCRIPTION
       " "
   ::= { sispm10403166lDHCPSnoopingStatisticsEntry 4 }

sispm10403166lDHCPSnoopingRxRequest OBJECT-TYPE
   SYNTAX      Counter32
   MAX-ACCESS  read-only
   STATUS      current
   DESCRIPTION
       " "
   ::= { sispm10403166lDHCPSnoopingStatisticsEntry 5 }

sispm10403166lDHCPSnoopingRxDecline OBJECT-TYPE
   SYNTAX      Counter32
   MAX-ACCESS  read-only
   STATUS      current
   DESCRIPTION
       " "
   ::= { sispm10403166lDHCPSnoopingStatisticsEntry 6 }

sispm10403166lDHCPSnoopingRxACK OBJECT-TYPE
   SYNTAX      Counter32
   MAX-ACCESS  read-only
   STATUS      current
   DESCRIPTION
       " "
   ::= { sispm10403166lDHCPSnoopingStatisticsEntry 7 }

sispm10403166lDHCPSnoopingRxNAK OBJECT-TYPE
   SYNTAX      Counter32
   MAX-ACCESS  read-only
   STATUS      current
   DESCRIPTION
       " "
   ::= { sispm10403166lDHCPSnoopingStatisticsEntry 8 }

sispm10403166lDHCPSnoopingRxRelease OBJECT-TYPE
   SYNTAX      Counter32
   MAX-ACCESS  read-only
   STATUS      current
   DESCRIPTION
       " "
   ::= { sispm10403166lDHCPSnoopingStatisticsEntry 9 }

sispm10403166lDHCPSnoopingRxInform OBJECT-TYPE
   SYNTAX      Counter32
   MAX-ACCESS  read-only
   STATUS      current
   DESCRIPTION
       " "
   ::= { sispm10403166lDHCPSnoopingStatisticsEntry 10 }

sispm10403166lDHCPSnoopingRxLeaseQuery OBJECT-TYPE
   SYNTAX      Counter32
   MAX-ACCESS  read-only
   STATUS      current
   DESCRIPTION
       " "
   ::= { sispm10403166lDHCPSnoopingStatisticsEntry 11 }

sispm10403166lDHCPSnoopingRxLeaseUnassigned OBJECT-TYPE
   SYNTAX      Counter32
   MAX-ACCESS  read-only
   STATUS      current
   DESCRIPTION
       " "
   ::= { sispm10403166lDHCPSnoopingStatisticsEntry 12 }

sispm10403166lDHCPSnoopingRxLeaseUnknown OBJECT-TYPE
   SYNTAX      Counter32
   MAX-ACCESS  read-only
   STATUS      current
   DESCRIPTION
       " "
   ::= { sispm10403166lDHCPSnoopingStatisticsEntry 13 }

sispm10403166lDHCPSnoopingRxLeaseActive OBJECT-TYPE
   SYNTAX      Counter32
   MAX-ACCESS  read-only
   STATUS      current
   DESCRIPTION
       " "
   ::= { sispm10403166lDHCPSnoopingStatisticsEntry 14 }

sispm10403166lDHCPSnoopingTxDiscover OBJECT-TYPE
   SYNTAX      Counter32
   MAX-ACCESS  read-only
   STATUS      current
   DESCRIPTION
       " "
   ::= { sispm10403166lDHCPSnoopingStatisticsEntry 15 }

sispm10403166lDHCPSnoopingTxOffer OBJECT-TYPE
   SYNTAX      Counter32
   MAX-ACCESS  read-only
   STATUS      current
   DESCRIPTION
       " "
   ::= { sispm10403166lDHCPSnoopingStatisticsEntry 16 }

sispm10403166lDHCPSnoopingTxRequest OBJECT-TYPE
   SYNTAX      Counter32
   MAX-ACCESS  read-only
   STATUS      current
   DESCRIPTION
       " "
   ::= { sispm10403166lDHCPSnoopingStatisticsEntry 17 }

sispm10403166lDHCPSnoopingTxDecline OBJECT-TYPE
   SYNTAX      Counter32
   MAX-ACCESS  read-only
   STATUS      current
   DESCRIPTION
       " "
   ::= { sispm10403166lDHCPSnoopingStatisticsEntry 18 }

sispm10403166lDHCPSnoopingTxACK OBJECT-TYPE
   SYNTAX      Counter32
   MAX-ACCESS  read-only
   STATUS      current
   DESCRIPTION
       " "
   ::= { sispm10403166lDHCPSnoopingStatisticsEntry 19 }

sispm10403166lDHCPSnoopingTxNAK OBJECT-TYPE
   SYNTAX      Counter32
   MAX-ACCESS  read-only
   STATUS      current
   DESCRIPTION
       " "
   ::= { sispm10403166lDHCPSnoopingStatisticsEntry 20 }

sispm10403166lDHCPSnoopingTxRelease OBJECT-TYPE
   SYNTAX      Counter32
   MAX-ACCESS  read-only
   STATUS      current
   DESCRIPTION
       " "
   ::= { sispm10403166lDHCPSnoopingStatisticsEntry 21 }

sispm10403166lDHCPSnoopingTxInform OBJECT-TYPE
   SYNTAX      Counter32
   MAX-ACCESS  read-only
   STATUS      current
   DESCRIPTION
       " "
   ::= { sispm10403166lDHCPSnoopingStatisticsEntry 22 }

sispm10403166lDHCPSnoopingTxLeaseQuery OBJECT-TYPE
   SYNTAX      Counter32
   MAX-ACCESS  read-only
   STATUS      current
   DESCRIPTION
       " "
   ::= { sispm10403166lDHCPSnoopingStatisticsEntry 23 }

sispm10403166lDHCPSnoopingTxLeaseUnassigned OBJECT-TYPE
   SYNTAX      Counter32
   MAX-ACCESS  read-only
   STATUS      current
   DESCRIPTION
       " "
   ::= { sispm10403166lDHCPSnoopingStatisticsEntry 24 }

sispm10403166lDHCPSnoopingTxLeaseUnknown OBJECT-TYPE
   SYNTAX      Counter32
   MAX-ACCESS  read-only
   STATUS      current
   DESCRIPTION
       " "
   ::= { sispm10403166lDHCPSnoopingStatisticsEntry 25 }

sispm10403166lDHCPSnoopingTxLeaseActive OBJECT-TYPE
   SYNTAX      Counter32
   MAX-ACCESS  read-only
   STATUS      current
   DESCRIPTION
       " "
   ::= { sispm10403166lDHCPSnoopingStatisticsEntry 26 }

sispm10403166lDHCPSnoopingRxDiscardedChecksumError OBJECT-TYPE
   SYNTAX      Counter32
   MAX-ACCESS  read-only
   STATUS      current
   DESCRIPTION
       " "
   ::= { sispm10403166lDHCPSnoopingStatisticsEntry 27 }

sispm10403166lDHCPSnoopingRxDiscardedFromUntrusted OBJECT-TYPE
   SYNTAX      Counter32
   MAX-ACCESS  read-only
   STATUS      current
   DESCRIPTION
       " "
   ::= { sispm10403166lDHCPSnoopingStatisticsEntry 28 }

sispm10403166lDHCPRelay                                             OBJECT IDENTIFIER ::= { sispm10403166lSecurity 4 }

sispm10403166lDHCPRelayConfiguration                                         OBJECT IDENTIFIER ::= { sispm10403166lDHCPRelay 1 }

sispm10403166lDHCPRelayMode OBJECT-TYPE
   SYNTAX      Integer32(0|1)
   MAX-ACCESS  read-write
   STATUS      current
   DESCRIPTION
       "default: 0
       0: disable
       1: enable
       We need at least one server"
   ::= { sispm10403166lDHCPRelayConfiguration 1 }

sispm10403166lDHCPRelayServer OBJECT-TYPE
   SYNTAX      IpAddress
   MAX-ACCESS  read-write
   STATUS      current
   DESCRIPTION
       " "
   ::= { sispm10403166lDHCPRelayConfiguration 2 }

sispm10403166lDHCPRelayInformationMode OBJECT-TYPE
   SYNTAX      Integer32(0|1)
   MAX-ACCESS  read-write
   STATUS      current
   DESCRIPTION
       "default: 0
       0: disable
       1: enable "
   ::= { sispm10403166lDHCPRelayConfiguration 3 }

sispm10403166lDHCPRelayInformationPolicy OBJECT-TYPE
   SYNTAX      Integer32(0..2)
   MAX-ACCESS  read-write
   STATUS      current
   DESCRIPTION
       "default: 0
       0: replace
       1: keep
       2: drop "
   ::= { sispm10403166lDHCPRelayConfiguration 4 }

sispm10403166lDHCPRelayStatistics                                   OBJECT IDENTIFIER ::= { sispm10403166lDHCPRelay 2 }

sispm10403166lDHCPRelayServerStatistics                                   OBJECT IDENTIFIER ::= { sispm10403166lDHCPRelayStatistics 1 }

sispm10403166lServerStatTransmitToServer OBJECT-TYPE
   SYNTAX      Counter32
   MAX-ACCESS  read-only
   STATUS      current
   DESCRIPTION
       " "
   ::= { sispm10403166lDHCPRelayServerStatistics 1 }

sispm10403166lServerStatTransmitError OBJECT-TYPE
   SYNTAX      Counter32
   MAX-ACCESS  read-only
   STATUS      current
   DESCRIPTION
       " "
   ::= { sispm10403166lDHCPRelayServerStatistics 2 }

sispm10403166lServerStatReceiveFromServer OBJECT-TYPE
   SYNTAX      Counter32
   MAX-ACCESS  read-only
   STATUS      current
   DESCRIPTION
       " "
   ::= { sispm10403166lDHCPRelayServerStatistics 3 }

sispm10403166lServerStatReceiveMissingAgentOption OBJECT-TYPE
   SYNTAX      Counter32
   MAX-ACCESS  read-only
   STATUS      current
   DESCRIPTION
       " "
   ::= { sispm10403166lDHCPRelayServerStatistics 4 }

sispm10403166lServerStatReceiveMissingCircuitID OBJECT-TYPE
   SYNTAX      Counter32
   MAX-ACCESS  read-only
   STATUS      current
   DESCRIPTION
       " "
   ::= { sispm10403166lDHCPRelayServerStatistics 5 }

sispm10403166lServerStatReceiveMissingRemoteID OBJECT-TYPE
   SYNTAX      Counter32
   MAX-ACCESS  read-only
   STATUS      current
   DESCRIPTION
       " "
   ::= { sispm10403166lDHCPRelayServerStatistics 6 }

sispm10403166lServerStatReceiveBadCircuitID OBJECT-TYPE
   SYNTAX      Counter32
   MAX-ACCESS  read-only
   STATUS      current
   DESCRIPTION
       " "
   ::= { sispm10403166lDHCPRelayServerStatistics 7 }

sispm10403166lServerStatReceiveBadRemoteID OBJECT-TYPE
   SYNTAX      Counter32
   MAX-ACCESS  read-only
   STATUS      current
   DESCRIPTION
       " "
   ::= { sispm10403166lDHCPRelayServerStatistics 8 }

sispm10403166lDHCPRelayClientStatistics                                   OBJECT IDENTIFIER ::= { sispm10403166lDHCPRelayStatistics 2 }

sispm10403166lClientStatTransmitToClient OBJECT-TYPE
   SYNTAX      Counter32
   MAX-ACCESS  read-only
   STATUS      current
   DESCRIPTION
       " "
   ::= { sispm10403166lDHCPRelayClientStatistics 1 }

sispm10403166lClientStatTransmitError OBJECT-TYPE
   SYNTAX      Counter32
   MAX-ACCESS  read-only
   STATUS      current
   DESCRIPTION
       " "
   ::= { sispm10403166lDHCPRelayClientStatistics 2 }

sispm10403166lClientStatReceivefromClient OBJECT-TYPE
   SYNTAX      Counter32
   MAX-ACCESS  read-only
   STATUS      current
   DESCRIPTION
       " "
   ::= { sispm10403166lDHCPRelayClientStatistics 3 }

sispm10403166lClientStatReceiveAgentOption OBJECT-TYPE
   SYNTAX      Counter32
   MAX-ACCESS  read-only
   STATUS      current
   DESCRIPTION
       " "
   ::= { sispm10403166lDHCPRelayClientStatistics 4 }

sispm10403166lClientStatReplaceAgentOption OBJECT-TYPE
   SYNTAX      Counter32
   MAX-ACCESS  read-only
   STATUS      current
   DESCRIPTION
       " "
   ::= { sispm10403166lDHCPRelayClientStatistics 5 }

sispm10403166lClientStatKeepAgentOption OBJECT-TYPE
   SYNTAX      Counter32
   MAX-ACCESS  read-only
   STATUS      current
   DESCRIPTION
       " "
   ::= { sispm10403166lDHCPRelayClientStatistics 6 }

sispm10403166lClientStatDropAgentOption OBJECT-TYPE
   SYNTAX      Counter32
   MAX-ACCESS  read-only
   STATUS      current
   DESCRIPTION
       " "
   ::= { sispm10403166lDHCPRelayClientStatistics 7 }

sispm10403166lPortSecurity                                          OBJECT IDENTIFIER ::= { sispm10403166lSecurity 5 }

sispm10403166lPortSecLimitCtrl                                      OBJECT IDENTIFIER ::= { sispm10403166lPortSecurity 1 }

sispm10403166lPortSecLimitCtrlSystemConf                                      OBJECT IDENTIFIER ::= { sispm10403166lPortSecLimitCtrl 1 }

-- sispm10403166lPortSecurityMode OBJECT-TYPE
--   SYNTAX      Integer32(0|1)
--   MAX-ACCESS  read-write
--   STATUS      current
--   DESCRIPTION
--       "default: 0
--       0: disable
--       1: enable "
--   ::= { sispm10403166lPortSecLimitCtrlSystemConf 1 }

sispm10403166lPortSecurityAging OBJECT-TYPE
   SYNTAX      Integer32(0|1)
   MAX-ACCESS  read-write
   STATUS      current
   DESCRIPTION
       "default: 0
       0: disable
       1: enable "
   ::= { sispm10403166lPortSecLimitCtrlSystemConf 1 }

sispm10403166lPortSecurityAgingPeriod OBJECT-TYPE
   SYNTAX      Integer32(10..10000000)
   MAX-ACCESS  read-write
   STATUS      current
   DESCRIPTION
       "default: 3600, range: 10-10000000 "
   ::= { sispm10403166lPortSecLimitCtrlSystemConf 2 }

sispm10403166lPortSecurityHoldTime OBJECT-TYPE
   SYNTAX      Integer32(10..10000000)
   MAX-ACCESS  read-write
   STATUS      current
   DESCRIPTION
       "default: 300, range: 10-10000000 "
   ::= { sispm10403166lPortSecLimitCtrlSystemConf 3 }

sispm10403166lPortSecLimitCtrlTable OBJECT-TYPE
   SYNTAX      SEQUENCE OF SISPM10403166LPortSecLimitCtrlEntry
   MAX-ACCESS  not-accessible
   STATUS      current
   DESCRIPTION
       " "
   ::= { sispm10403166lPortSecLimitCtrl 2 }

sispm10403166lPortSecLimitCtrlEntry OBJECT-TYPE
   SYNTAX      SISPM10403166LPortSecLimitCtrlEntry
   MAX-ACCESS  not-accessible
   STATUS      current
   DESCRIPTION
       " "
   INDEX    { sispm10403166lPortSecLimitCtrlPort  }
   ::= { sispm10403166lPortSecLimitCtrlTable 1 }

SISPM10403166LPortSecLimitCtrlEntry ::= SEQUENCE {
   sispm10403166lPortSecLimitCtrlPort                Integer32,
   sispm10403166lPortSecLimitCtrlPortMode            Integer32,
   sispm10403166lPortSecLimitCtrlPortLimit           Integer32,
   sispm10403166lPortSecLimitCtrlPortViolationmMode  Integer32,
   sispm10403166lPortSecLimitCtrlPortViolationmLimit Integer32,
   sispm10403166lPortSecLimitCtrlPortState           DisplayString,
   sispm10403166lPortSecLimitCtrlPortReOpen          Integer32,
   sispm10403166lPortSecLimitCtrlPortSticky          Integer32,
   sispm10403166lPortSecLimitCtrlPortClear           Integer32
}

sispm10403166lPortSecLimitCtrlPort OBJECT-TYPE
   SYNTAX      Integer32(1..65535)
   MAX-ACCESS  not-accessible
   STATUS      current
   DESCRIPTION
       " "
   ::= { sispm10403166lPortSecLimitCtrlEntry 1 }

sispm10403166lPortSecLimitCtrlPortMode OBJECT-TYPE
   SYNTAX      Integer32 (0|1)
   MAX-ACCESS  read-write
   STATUS      current
   DESCRIPTION
       "default: 0
       0: disable
       1: enable"
   ::= { sispm10403166lPortSecLimitCtrlEntry 2 }

sispm10403166lPortSecLimitCtrlPortLimit OBJECT-TYPE
   SYNTAX      Integer32(1..1024)
   MAX-ACCESS  read-write
   STATUS      current
   DESCRIPTION
       "default: 4, range: 1-1024"
   ::= { sispm10403166lPortSecLimitCtrlEntry 3 }

sispm10403166lPortSecLimitCtrlPortViolationmMode OBJECT-TYPE
   SYNTAX      Integer32(0..2)
   MAX-ACCESS  read-write
   STATUS      current
   DESCRIPTION
       "default: 0
       0: Protect
       1: Restrict
       2: Shutdown"
   ::= { sispm10403166lPortSecLimitCtrlEntry 4 }

sispm10403166lPortSecLimitCtrlPortViolationmLimit OBJECT-TYPE
   SYNTAX      Integer32(1..1024)
   MAX-ACCESS  read-write
   STATUS      current
   DESCRIPTION
       "default: 4, range: 1-1024"
   ::= { sispm10403166lPortSecLimitCtrlEntry 5 }


sispm10403166lPortSecLimitCtrlPortState OBJECT-TYPE
   SYNTAX      DisplayString
   MAX-ACCESS  read-only
   STATUS      current
   DESCRIPTION
       " "
   ::= { sispm10403166lPortSecLimitCtrlEntry 6 }

sispm10403166lPortSecLimitCtrlPortReOpen OBJECT-TYPE
   SYNTAX      Integer32 (0|1)
   MAX-ACCESS  read-write
   STATUS      current
   DESCRIPTION
       "default: 0
       0: none
       1: reopen"
   ::= { sispm10403166lPortSecLimitCtrlEntry 7 }

sispm10403166lPortSecLimitCtrlPortSticky OBJECT-TYPE
   SYNTAX      Integer32 (0|1)
   MAX-ACCESS  read-write
   STATUS      current
   DESCRIPTION
       "default: 0
       0: disable
       1: enable"
   ::= { sispm10403166lPortSecLimitCtrlEntry 8 }

sispm10403166lPortSecLimitCtrlPortClear OBJECT-TYPE
   SYNTAX      Integer32 (0|1)
   MAX-ACCESS  read-write
   STATUS      current
   DESCRIPTION
       "default: 0
       1: clear"
   ::= { sispm10403166lPortSecLimitCtrlEntry 9 }


sispm10403166lPortSecSwitchStatusTable OBJECT-TYPE
   SYNTAX      SEQUENCE OF SISPM10403166LPortSecSwitchStatusEntry
   MAX-ACCESS  not-accessible
   STATUS      current
   DESCRIPTION
       " "
   ::= { sispm10403166lPortSecurity 2 }

sispm10403166lPortSecSwitchStatusEntry OBJECT-TYPE
   SYNTAX      SISPM10403166LPortSecSwitchStatusEntry
   MAX-ACCESS  not-accessible
   STATUS      current
   DESCRIPTION
       " "
   INDEX    { sispm10403166lPortSecSwitchStatusPort  }
   ::= { sispm10403166lPortSecSwitchStatusTable 1 }

SISPM10403166LPortSecSwitchStatusEntry ::= SEQUENCE {
   sispm10403166lPortSecSwitchStatusPort                Integer32,
--   sispm10403166lPortSecSwitchStatusUsers               DisplayString,
   sispm10403166lPortSecSwitchStatusViolationmMode      DisplayString,
   sispm10403166lPortSecSwitchStatusState               DisplayString,
   sispm10403166lPortSecSwitchStatusMACCountCurrent     Integer32,
   sispm10403166lPortSecSwitchStatusMACCountViolating   Integer32,
   sispm10403166lPortSecSwitchStatusMACCountLimit       Integer32,
   sispm10403166lPortSecSwitchStatusClear               Integer32
}

sispm10403166lPortSecSwitchStatusPort OBJECT-TYPE
   SYNTAX      Integer32(1..65535)
   MAX-ACCESS  not-accessible
   STATUS      current
   DESCRIPTION
       " "
   ::= { sispm10403166lPortSecSwitchStatusEntry 1 }

-- sispm10403166lPortSecSwitchStatusUsers OBJECT-TYPE
--   SYNTAX      DisplayString
--   MAX-ACCESS  read-only
--   STATUS      current
--   DESCRIPTION
--       " Users Abbr: L = Limit Control, 8 = 802.1X, D = DHCP Snooping, V = Voice VLAN,
--         '-' means that the corresponding user module is not enabled. "
--   ::= { sispm10403166lPortSecSwitchStatusEntry 2 }

sispm10403166lPortSecSwitchStatusViolationmMode OBJECT-TYPE
   SYNTAX      DisplayString
   MAX-ACCESS  read-only
   STATUS      current
   DESCRIPTION
       "Shows the configured Violation Mode of the port."
   ::= { sispm10403166lPortSecSwitchStatusEntry 3 }

sispm10403166lPortSecSwitchStatusState OBJECT-TYPE
   SYNTAX      DisplayString
   MAX-ACCESS  read-only
   STATUS      current
   DESCRIPTION
       " Shows the current state of the port : Disabled, Ready, Limit Reached, Shutdown. "
   ::= { sispm10403166lPortSecSwitchStatusEntry 4 }

sispm10403166lPortSecSwitchStatusMACCountCurrent OBJECT-TYPE
   SYNTAX      Integer32
   MAX-ACCESS  read-only
   STATUS      current
   DESCRIPTION
       " "
   ::= { sispm10403166lPortSecSwitchStatusEntry 5 }

sispm10403166lPortSecSwitchStatusMACCountViolating OBJECT-TYPE
   SYNTAX      Integer32
   MAX-ACCESS  read-only
   STATUS      current
   DESCRIPTION
       " "
   ::= { sispm10403166lPortSecSwitchStatusEntry 6 }

sispm10403166lPortSecSwitchStatusMACCountLimit OBJECT-TYPE
   SYNTAX      Integer32
   MAX-ACCESS  read-only
   STATUS      current
   DESCRIPTION
       " "
   ::= { sispm10403166lPortSecSwitchStatusEntry 7 }

sispm10403166lPortSecSwitchStatusClear OBJECT-TYPE
   SYNTAX      Integer32 (0|1)
   MAX-ACCESS  read-write
   STATUS      current
   DESCRIPTION
       "Remove all MAC addresses on all VLANs on this port."
   ::= { sispm10403166lPortSecSwitchStatusEntry 8 }

sispm10403166lPortSecPortStatus                                      OBJECT IDENTIFIER ::= { sispm10403166lPortSecurity 3 }

sispm10403166lPortSecPortStatusPort OBJECT-TYPE
   SYNTAX       Integer32
   MAX-ACCESS   read-write
   STATUS       current
   DESCRIPTION
       "port number
        default: 1
        range: 1 - port number."
   ::= { sispm10403166lPortSecPortStatus 1 }

sispm10403166lPortSecPortStatusTable OBJECT-TYPE
   SYNTAX      SEQUENCE OF SISPM10403166LPortSecPortStatusEntry
   MAX-ACCESS  not-accessible
   STATUS      current
   DESCRIPTION
      " "
   ::= { sispm10403166lPortSecPortStatus 2 }

sispm10403166lPortSecPortStatusEntry OBJECT-TYPE
   SYNTAX      SISPM10403166LPortSecPortStatusEntry
   MAX-ACCESS  not-accessible
   STATUS      current
   DESCRIPTION
       " "
   INDEX    { sispm10403166lPortSecPortStatusIndex  }
   ::= { sispm10403166lPortSecPortStatusTable 1 }

SISPM10403166LPortSecPortStatusEntry ::= SEQUENCE {
   sispm10403166lPortSecPortStatusIndex              Integer32,
   sispm10403166lPortSecPortStatusMACAddress         DisplayString,
   sispm10403166lPortSecPortStatusVLANId             Integer32,
   sispm10403166lPortSecPortStatusState              DisplayString,
   sispm10403166lPortSecPortStatusAgeAndHold         DisplayString,
   sispm10403166lPortSecPortStatusClear              Integer32
}

sispm10403166lPortSecPortStatusIndex OBJECT-TYPE
   SYNTAX      Integer32(1..65535)
   MAX-ACCESS  not-accessible
   STATUS      current
   DESCRIPTION
       " "
   ::= { sispm10403166lPortSecPortStatusEntry 1 }

sispm10403166lPortSecPortStatusMACAddress OBJECT-TYPE
   SYNTAX      DisplayString
   MAX-ACCESS  read-only
   STATUS      current
   DESCRIPTION
       "MAC address that is seen on this port."
   ::= { sispm10403166lPortSecPortStatusEntry 2 }

sispm10403166lPortSecPortStatusVLANId OBJECT-TYPE
   SYNTAX      Integer32(1..4094)
   MAX-ACCESS  read-only
   STATUS      current
   DESCRIPTION
       "VLAN ID that is seen on this port"
   ::= { sispm10403166lPortSecPortStatusEntry 3 }

sispm10403166lPortSecPortStatusState OBJECT-TYPE
   SYNTAX      DisplayString
   MAX-ACCESS  read-only
   STATUS      current
   DESCRIPTION
       "Indicates whether the corresponding MAC address is violating
	   (administrative user has configured the interface in Restrict mode and the MAC address is blocked),
	   blocked, or forwarding."
   ::= { sispm10403166lPortSecPortStatusEntry 4 }

sispm10403166lPortSecPortStatusAgeAndHold OBJECT-TYPE
   SYNTAX      DisplayString
   MAX-ACCESS  read-only
   STATUS      current
   DESCRIPTION
       " "
   ::= { sispm10403166lPortSecPortStatusEntry 5 }

sispm10403166lPortSecPortStatusClear OBJECT-TYPE
   SYNTAX      Integer32(0|1)
   MAX-ACCESS  read-write
   STATUS      current
   DESCRIPTION
       "Remove particular MAC addresses from MAC table
	   1:clear"
   ::= { sispm10403166lPortSecPortStatusEntry 6 }

sispm10403166lAccessManagement                                      OBJECT IDENTIFIER ::= { sispm10403166lSecurity 6 }

sispm10403166lAccessMgmtConf                                         OBJECT IDENTIFIER ::= { sispm10403166lAccessManagement 1 }

sispm10403166lAccessMgmtStatistics                                   OBJECT IDENTIFIER ::= { sispm10403166lAccessManagement 2 }
--
-- =======================================================================================================================
-- Start sispm10403166lAccessManagement group
-- =======================================================================================================================
--sispm10403166lAccessMgmtConf

    sispm10403166lAccessMgmtConfMode OBJECT-TYPE
               SYNTAX      AdminMode
               MAX-ACCESS  read-write
               STATUS      current
               DESCRIPTION
                   "Indicates the access management mode operation."
               DEFVAL  { disable }
               ::= {     sispm10403166lAccessMgmtConf 1 }

--sispm10403166lAccessMgmtConfTable

    sispm10403166lAccessMgmtConfTable OBJECT-TYPE
               SYNTAX      SEQUENCE OF     SISPM10403166LAccessMgmtConfEntry
               MAX-ACCESS  not-accessible
               STATUS      current
               DESCRIPTION
                   "The Access Mgmt Conf Table. "
               ::= {     sispm10403166lAccessMgmtConf 2 }

    sispm10403166lAccessMgmtConfEntry OBJECT-TYPE
               SYNTAX          SISPM10403166LAccessMgmtConfEntry
               MAX-ACCESS  not-accessible
               STATUS      current
               DESCRIPTION
                   "The Access Mgmt Conf Entry "
               INDEX    {    sispm10403166lAccessMgmtIndex  }
               ::= {     sispm10403166lAccessMgmtConfTable 1 }

    SISPM10403166LAccessMgmtConfEntry             ::= SEQUENCE {
                 sispm10403166lAccessMgmtIndex            Integer32,
                 sispm10403166lAccessMgmtVlanID           Integer32,
                 sispm10403166lAccessMgmtStartIpAddress   IpAddress,
                 sispm10403166lAccessMgmtEndIpAddress     IpAddress,
                 sispm10403166lAccessMgmtHttpHttps        AdminMode,
                 sispm10403166lAccessMgmtSNMP             AdminMode,
                 sispm10403166lAccessMgmtTelnetSSH        AdminMode,
                 sispm10403166lAccessMgmtRowStatus        RowStatus
                 }

    sispm10403166lAccessMgmtIndex OBJECT-TYPE
               SYNTAX      Integer32(1..16)
               MAX-ACCESS  not-accessible
               STATUS      current
               DESCRIPTION
                   "The Access Management config index.
                    range : 1-16."
               ::= {     sispm10403166lAccessMgmtConfEntry 1 }

    sispm10403166lAccessMgmtVlanID OBJECT-TYPE
               SYNTAX      Integer32 (1..4095)
               MAX-ACCESS  read-create
               STATUS      current
               DESCRIPTION
                   "The VLAN ID for the access management entry.
                    range: 1-4095."
               ::= {     sispm10403166lAccessMgmtConfEntry 2 }

    sispm10403166lAccessMgmtStartIpAddress OBJECT-TYPE
               SYNTAX      IpAddress
               MAX-ACCESS  read-create
               STATUS      current
               DESCRIPTION
                   "The start IP address for the access management
                    entry."
               ::= {     sispm10403166lAccessMgmtConfEntry 3 }

    sispm10403166lAccessMgmtEndIpAddress OBJECT-TYPE
               SYNTAX      IpAddress
               MAX-ACCESS  read-create
               STATUS      current
               DESCRIPTION
                   "The end IP address for the access management
                    entry. "
               ::= {     sispm10403166lAccessMgmtConfEntry 4 }

    sispm10403166lAccessMgmtHttpHttps OBJECT-TYPE
               SYNTAX      AdminMode
               MAX-ACCESS  read-create
               STATUS      current
               DESCRIPTION
                   "Indicates that the host can access the switch from
                    HTTP/HTTPS interface if the host IP address matches the IP
                    address range provided in the entry."
               DEFVAL  { disable }
               ::= {     sispm10403166lAccessMgmtConfEntry 5 }

    sispm10403166lAccessMgmtSNMP OBJECT-TYPE
               SYNTAX      AdminMode
               MAX-ACCESS  read-create
               STATUS      current
               DESCRIPTION
                   "Indicates that the host can access the switch from SNMP
                    interface if the host IP address matches the IP address
                    range provided in the entry."
               DEFVAL  { disable }
               ::= {     sispm10403166lAccessMgmtConfEntry 6 }

    sispm10403166lAccessMgmtTelnetSSH OBJECT-TYPE
               SYNTAX      AdminMode
               MAX-ACCESS  read-create
               STATUS      current
               DESCRIPTION
                   "Indicates that the host can access the switch from
                    TELNET/SSH interface if the host IP address matches
                    the IP address range provided in the entry."
               DEFVAL  { disable }
               ::= {     sispm10403166lAccessMgmtConfEntry 7 }

    sispm10403166lAccessMgmtRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sispm10403166lAccessMgmtConfEntry 8 }

--sispm10403166lAccessMgmtStatistics

    sispm10403166lAccessMgmtStatisticsClear OBJECT-TYPE
               SYNTAX      ActivateCmd
               MAX-ACCESS  read-write
               STATUS      current
               DESCRIPTION
                   "Clear all statistics."
               ::= {     sispm10403166lAccessMgmtStatistics 1 }

--sispm10403166lAccessMgmtStatisticsTable

    sispm10403166lAccessMgmtStatisticsTable OBJECT-TYPE
               SYNTAX      SEQUENCE OF     SISPM10403166LAccessMgmtStatisticsEntry
               MAX-ACCESS  not-accessible
               STATUS      current
               DESCRIPTION
                   "The Access Mgmt Statistics Table. "
               ::= {     sispm10403166lAccessMgmtStatistics 2 }

    sispm10403166lAccessMgmtStatisticsEntry OBJECT-TYPE
               SYNTAX          SISPM10403166LAccessMgmtStatisticsEntry
               MAX-ACCESS  not-accessible
               STATUS      current
               DESCRIPTION
                   "The Access Mgmt Statistics Entry. "
               INDEX    {    sispm10403166lAccessMgmtStatisticsInterface  }
               ::= {     sispm10403166lAccessMgmtStatisticsTable 1 }

    SISPM10403166LAccessMgmtStatisticsEntry ::= SEQUENCE {
                 sispm10403166lAccessMgmtStatisticsInterface         INTEGER,
                 sispm10403166lAccessMgmtStatisticsReceivedPackets   Integer32,
                 sispm10403166lAccessMgmtStatisticsAllowedPackets    Integer32,
                 sispm10403166lAccessMgmtStatisticsDiscardedPackets  Integer32
                 }

    sispm10403166lAccessMgmtStatisticsInterface OBJECT-TYPE
               SYNTAX      INTEGER { http(1), https(2), snmp(3), telnet(4), ssh (5) }
               MAX-ACCESS  not-accessible
               STATUS      current
               DESCRIPTION
                   "The interface type through which the remote host can
                    access the switch.
                    1: HTTP,
                    2: HTTPs,
                    3: SNMP,
                    4: TELNET,
                    5: SSH"
               ::= {     sispm10403166lAccessMgmtStatisticsEntry 1 }

    sispm10403166lAccessMgmtStatisticsReceivedPackets OBJECT-TYPE
               SYNTAX      Integer32(1..10000000)
               MAX-ACCESS  read-only
               STATUS      current
               DESCRIPTION
                   "Number of received packets from the interface when
                    access management mode is enabled. "
               ::= {     sispm10403166lAccessMgmtStatisticsEntry 2 }

    sispm10403166lAccessMgmtStatisticsAllowedPackets OBJECT-TYPE
               SYNTAX      Integer32(1..10000000)
               MAX-ACCESS  read-only
               STATUS      current
               DESCRIPTION
                   "Number of allowed packets from the interface when
                    access management mode is enabled. "
               ::= {     sispm10403166lAccessMgmtStatisticsEntry 3 }

    sispm10403166lAccessMgmtStatisticsDiscardedPackets OBJECT-TYPE
               SYNTAX      Integer32(1..10000000)
               MAX-ACCESS  read-only
               STATUS      current
               DESCRIPTION
                   "Number of discarded packets from the interface when
                    access management mode is enabled. "
               ::= {     sispm10403166lAccessMgmtStatisticsEntry 4 }

-- =======================================================================================================================

--sispm10403166lSSH                                                   OBJECT IDENTIFIER ::= { sispm10403166lSecurity 7 }
--
--sispm10403166lSSHMode OBJECT-TYPE
--   SYNTAX      Integer32(0|1)
--   MAX-ACCESS  read-write
--   STATUS      current
--   DESCRIPTION
--       "default: 1
--        0: disable
--        1: enable"
--   ::= { sispm10403166lSSH 1 }

--sispm10403166lSSHPort OBJECT-TYPE
--   SYNTAX      Integer32(1..65535)
--   MAX-ACCESS  read-write
--   STATUS      current
--   DESCRIPTION
--       "SSH service port number.
--        range : 1-65535, default : 22."
--   ::= { sispm10403166lSSH 2 }

sispm10403166lHTTPS                                                 OBJECT IDENTIFIER ::= { sispm10403166lSecurity 8 }
--
--sispm10403166lHTTPSMode OBJECT-TYPE
--   SYNTAX      Integer32(0|1)
--   MAX-ACCESS  read-write
--   STATUS      current
--   DESCRIPTION
--       "default: 1
--        0: disable
--        1: enable"
--   ::= { sispm10403166lHTTPS 1 }
--
--sispm10403166lHTTPSAutoRedirect OBJECT-TYPE
--   SYNTAX      Integer32(0|1)
--   MAX-ACCESS  read-write
--   STATUS      current
--   DESCRIPTION
--       "default: 0
--        0: disable
--        1: enable"
--   ::= { sispm10403166lHTTPS 2 }
--
--sispm10403166lHTTPSPort OBJECT-TYPE
--   SYNTAX      Integer32(1..65535)
--   MAX-ACCESS  read-write
--   STATUS      current
--   DESCRIPTION
--       "HTTPS service port number.
--        range : 1-65535, default : 443."
--   ::= { sispm10403166lHTTPS 3 }
--
sispm10403166lHTTPSCertificateMaintain OBJECT-TYPE
   SYNTAX      Integer32(2..3)
   MAX-ACCESS  read-write
   STATUS      current
   DESCRIPTION
       "2: Upload
		3: Generate"
   ::= { sispm10403166lHTTPS 4 }

sispm10403166lHTTPSCertificatePassPhrase OBJECT-TYPE
   SYNTAX      DisplayString
   MAX-ACCESS  read-write
   STATUS      current
   DESCRIPTION
       "Enter the pass phrase in this field if your uploading certificate is protected by a specific passphrase."
   ::= { sispm10403166lHTTPS 5 }

sispm10403166lHTTPSCertificateUpload OBJECT-TYPE
   SYNTAX      Integer32(0|1)
   MAX-ACCESS  read-write
   STATUS      current
   DESCRIPTION
       "default: 0
        0: TFTP
        1: URL"
   ::= { sispm10403166lHTTPS 6 }

sispm10403166lHTTPSFileUploadFileURL OBJECT-TYPE
   SYNTAX      DisplayString
   MAX-ACCESS  read-write
   STATUS      current
   DESCRIPTION
       "TFTP: filename
	    URL: URL"
   ::= { sispm10403166lHTTPS 7 }

sispm10403166lHTTPSFileUploadTFTPServer OBJECT-TYPE
   SYNTAX       IpAddress
   MAX-ACCESS   read-write
   STATUS       current
   DESCRIPTION
		"TFTP server IP address"
   ::= { sispm10403166lHTTPS 8 }

sispm10403166lHTTPSApply OBJECT-TYPE
   SYNTAX      Integer32(0|1)
   MAX-ACCESS  read-write
   STATUS      current
   DESCRIPTION
       "1: apply the above https settings"
   ::= { sispm10403166lHTTPS 9 }

sispm10403166lHTTPSCertificateStatus OBJECT-TYPE
   SYNTAX      DisplayString
   MAX-ACCESS  read-only
   STATUS      current
   DESCRIPTION
       "Display the current status of certificate on the switch."
   ::= { sispm10403166lHTTPS 10 }

sispm10403166lAuthMethod                                            OBJECT IDENTIFIER ::= { sispm10403166lSecurity 9 }

--
-- =======================================================================================================================
-- Start sispm10403166lAuthMethodConfig group
-- =======================================================================================================================
--sispm10403166lAuthMethodConfigTable

    sispm10403166lAuthMethodConfigTable OBJECT-TYPE
               SYNTAX      SEQUENCE OF     SISPM10403166LAuthMethodConfigEntry
               MAX-ACCESS  not-accessible
               STATUS      current
               DESCRIPTION
                   "The Auth Method Config Table."
               ::= {     sispm10403166lAuthMethod 1 }

    sispm10403166lAuthMethodConfigEntry OBJECT-TYPE
               SYNTAX          SISPM10403166LAuthMethodConfigEntry
               MAX-ACCESS  not-accessible
               STATUS      current
               DESCRIPTION
                   "The Auth Method Config Entry."
               INDEX    {    sispm10403166lAuthMethodConfigClient  }
               ::= {     sispm10403166lAuthMethodConfigTable 1 }

    SISPM10403166LAuthMethodConfigEntry             ::= SEQUENCE {
                 sispm10403166lAuthMethodConfigClient        INTEGER,
                 sispm10403166lAuthMethodConfigMethod1       INTEGER,
                 sispm10403166lAuthMethodConfigMethod2       INTEGER,
                 sispm10403166lAuthMethodConfigMethod3       INTEGER,
                 sispm10403166lAuthMethodConfigMethod4       INTEGER,
                 sispm10403166lAuthMethodConfigServicePort   Integer32
                 }

    sispm10403166lAuthMethodConfigClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sispm10403166lAuthMethodConfigEntry 1 }

    sispm10403166lAuthMethodConfigMethod1 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sispm10403166lAuthMethodConfigEntry 2 }

    sispm10403166lAuthMethodConfigMethod2 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sispm10403166lAuthMethodConfigEntry 3 }

    sispm10403166lAuthMethodConfigMethod3 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sispm10403166lAuthMethodConfigEntry 4 }

    sispm10403166lAuthMethodConfigMethod4 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sispm10403166lAuthMethodConfigEntry 5 }

    sispm10403166lAuthMethodConfigServicePort OBJECT-TYPE
               SYNTAX      Integer32 (1..65535)
               MAX-ACCESS  read-write
               STATUS      current
               DESCRIPTION
                   "The network port number this client bound to provide service."
               ::= {     sispm10403166lAuthMethodConfigEntry 6 }

    sispm10403166lCommandAuthorizationMethodTable OBJECT-TYPE
               SYNTAX      SEQUENCE OF     SISPM10403166LCommandAuthorizationMethodEntry
               MAX-ACCESS  not-accessible
               STATUS      current
               DESCRIPTION
                   "The Command Authorized Method Config Table."
               ::= {     sispm10403166lAuthMethod 2 }

    sispm10403166lCommandAuthorizationMethodEntry OBJECT-TYPE
               SYNTAX          SISPM10403166LCommandAuthorizationMethodEntry
               MAX-ACCESS  not-accessible
               STATUS      current
               DESCRIPTION
                   "The Command Authorized Method Config Entry."
               INDEX    {    sispm10403166lCommandAuthorizationMethodClient  }
               ::= {     sispm10403166lCommandAuthorizationMethodTable 1 }

    SISPM10403166LCommandAuthorizationMethodEntry             ::= SEQUENCE {
                 sispm10403166lCommandAuthorizationMethodClient       INTEGER,
                 sispm10403166lCommandAuthorizationMethodMethod       Integer32,
                 sispm10403166lCommandAuthorizationMethodCmdLvl       Integer32,
                 sispm10403166lCommandAuthorizationMethodCfgCmd       Integer32
                 }

    sispm10403166lCommandAuthorizationMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sispm10403166lCommandAuthorizationMethodEntry 1 }

    sispm10403166lCommandAuthorizationMethodMethod OBJECT-TYPE
               SYNTAX      Integer32
               MAX-ACCESS  read-write
               STATUS      current
               DESCRIPTION
                   "Method can be set to one of the following values:
                    0:no: Command authorization is disabled.
					  User is granted access to CLI commands according to his privilege level.
                    4:tacacs: Use remote TACACS+ server(s) for command authorization.
					  If all remote servers are offline, the user is granted access to CLI commands
					  according to his privilege level."
               ::= {     sispm10403166lCommandAuthorizationMethodEntry 2 }

    sispm10403166lCommandAuthorizationMethodCmdLvl OBJECT-TYPE
               SYNTAX      Integer32
               MAX-ACCESS  read-write
               STATUS      current
               DESCRIPTION
                   "Authorize all commands with a privilege level higher than or equal to this level.
                    Valid values are in the range 0 to 15."
               ::= {     sispm10403166lCommandAuthorizationMethodEntry 3 }

    sispm10403166lCommandAuthorizationMethodCfgCmd OBJECT-TYPE
               SYNTAX      Integer32
               MAX-ACCESS  read-write
               STATUS      current
               DESCRIPTION
                   "Also authorize configuration commands.
				   0:Disable
				   1:Enable"
               ::= {     sispm10403166lCommandAuthorizationMethodEntry 4 }


    sispm10403166lAccountingMethodTable OBJECT-TYPE
               SYNTAX      SEQUENCE OF     SISPM10403166LAccountingMethodEntry
               MAX-ACCESS  not-accessible
               STATUS      current
               DESCRIPTION
                   "The Accounting Method Config Table."
               ::= {     sispm10403166lAuthMethod 3 }

    sispm10403166lAccountingMethodEntry OBJECT-TYPE
               SYNTAX          SISPM10403166LAccountingMethodEntry
               MAX-ACCESS  not-accessible
               STATUS      current
               DESCRIPTION
                   "The Accounting Method Config Entry."
               INDEX    {    sispm10403166lAccountingMethodClient  }
               ::= {     sispm10403166lAccountingMethodTable 1 }

    SISPM10403166LAccountingMethodEntry             ::= SEQUENCE {
                 sispm10403166lAccountingMethodClient       INTEGER,
                 sispm10403166lAccountingMethodMethod       Integer32,
                 sispm10403166lAccountingMethodCmdLvl       Integer32,
                 sispm10403166lAccountingMethodCfgCmd       Integer32
                 }

    sispm10403166lAccountingMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sispm10403166lAccountingMethodEntry 1 }

    sispm10403166lAccountingMethodMethod OBJECT-TYPE
               SYNTAX      Integer32
               MAX-ACCESS  read-write
               STATUS      current
               DESCRIPTION
                   "Method can be set to one of the following values:
                    0:no: Accounting is disabled.
                    4:tacacs: Use remote TACACS+ server(s) for accounting."
               ::= {     sispm10403166lAccountingMethodEntry 2 }

    sispm10403166lAccountingMethodCmdLvl OBJECT-TYPE
               SYNTAX      Integer32
               MAX-ACCESS  read-write
               STATUS      current
               DESCRIPTION
                   "Enable accounting of all commands with a privilege level higher than or equal to this level.
                    Valid values are in the range 0 to 15. Leave the field empty to disable command accounting."
               ::= {     sispm10403166lAccountingMethodEntry 3 }

    sispm10403166lAccountingMethodCfgCmd OBJECT-TYPE
               SYNTAX      Integer32
               MAX-ACCESS  read-write
               STATUS      current
               DESCRIPTION
                   "Enable exec (login) accounting.
				   0:Disable
				   1:Enable"
               ::= {     sispm10403166lAccountingMethodEntry 4 }

-- sispm10403166lTELNET                                                 OBJECT IDENTIFIER ::= { sispm10403166lSecurity 10 }

-- sispm10403166lTELNETPort OBJECT-TYPE
--   SYNTAX      Integer32(1..65535)
--   MAX-ACCESS  read-write
--   STATUS      current
--   DESCRIPTION
--       "TELNET service port number.
--        range : 1-65535, default : 23."
--   ::= { sispm10403166lTELNET 1 }

-- =======================================================================================================================
sispm10403166lMaintenance                                           OBJECT IDENTIFIER ::= { sispm10403166lProductId 4 }

sispm10403166lSoftware                      OBJECT IDENTIFIER   ::= {  sispm10403166lMaintenance 3 }
sispm10403166lConfig                        OBJECT IDENTIFIER   ::= {  sispm10403166lMaintenance 4 }

--
-- =======================================================================================================================
-- Objects in the sispm10403166lMaintenance Group
-- =======================================================================================================================
    sispm10403166lRestartDevice OBJECT-TYPE
               SYNTAX      ActivateCmd
               MAX-ACCESS  read-write
               STATUS      current
               DESCRIPTION
                   "Command to restart the device."
               DEFVAL  { noAction }
               ::= {     sispm10403166lMaintenance 1 }

    sispm10403166lFactoryDefaults OBJECT-TYPE
               SYNTAX      ActivateCmd
               MAX-ACCESS  read-write
               STATUS      current
               DESCRIPTION
                   "Reset the configuration to Factory Defaults keep-ip."
               DEFVAL  { noAction }
               ::= {     sispm10403166lMaintenance 2 }

--sispm10403166lSoftware

    sispm10403166lSoftwareUsername OBJECT-TYPE
               SYNTAX       DisplayString
               MAX-ACCESS   read-write
               STATUS       current
               DESCRIPTION
                    "Get/Set the username for 'tftp' firmware upgrading."
               ::= {     sispm10403166lSoftware 1 }

    sispm10403166lSoftwarePassword OBJECT-TYPE
               SYNTAX       DisplayString
               MAX-ACCESS   read-write
               STATUS       current
               DESCRIPTION
                    "Get/Set the password for 'tftp' firmware upgrading."
               ::= {     sispm10403166lSoftware 2 }

    sispm10403166lSoftwareIpAddress OBJECT-TYPE
               SYNTAX       IpAddress
               MAX-ACCESS   read-write
               STATUS       current
               DESCRIPTION
                    "Get/Set the firmware tftp server."
               ::= {     sispm10403166lSoftware 3 }

    sispm10403166lSoftwareFileName OBJECT-TYPE
               SYNTAX       DisplayString
               MAX-ACCESS   read-write
               STATUS       current
               DESCRIPTION
                    "Get/Set the path and filename for firmware upgrading."
               ::= {     sispm10403166lSoftware 4 }

    sispm10403166lSoftwareUpgradeCmd OBJECT-TYPE
               SYNTAX       INTEGER  {  noAction ( 0 ),
                                        tftpUpgrade ( 1 ),
                                        ftpUpgrade ( 2 )
                                     }
               MAX-ACCESS   read-write
               STATUS       current
               DESCRIPTION
                    "Firmware upgrade command.
                     noAction(0 )- do nothing   (read only).
                     tftpUpgrade (1) - activate 'tftp' firmware upgrade"

               DEFVAL  { noAction }
               ::= {     sispm10403166lSoftware 5 }

    sispm10403166lSoftwareImageSelectionCmd OBJECT-TYPE
               SYNTAX       ActivateCmd
               MAX-ACCESS   read-write
               STATUS       current
               DESCRIPTION
                    "Activate firmware image selection.
                     noAction(0) - do nothing - returned upon get.
                     activate(1) - activate firmware image selection."
               DEFVAL  { noAction }
               ::= {     sispm10403166lSoftware 6 }

    sispm10403166lSaveStartCmd OBJECT-TYPE
               SYNTAX      ActivateCmd
               MAX-ACCESS  read-write
               STATUS      current
               DESCRIPTION
                   "This copies running-config to startup-config,
                   thereby ensuring that the currently active
                   configuration will be used at the next reboot. "
               DEFVAL  { noAction }
               ::= {     sispm10403166lConfig 1 }

    sispm10403166lConfigUsername OBJECT-TYPE
               SYNTAX       DisplayString
               MAX-ACCESS   read-write
               STATUS       current
               DESCRIPTION
                    "Get/Set the username for 'tftp' 'upload config' or 'download config'."
               ::= {     sispm10403166lConfig 2 }

    sispm10403166lConfigPassword OBJECT-TYPE
               SYNTAX       DisplayString
               MAX-ACCESS   read-write
               STATUS       current
               DESCRIPTION
                    "Get/Set the password for 'tftp' 'upload config' or 'download config'."
               ::= {     sispm10403166lConfig 3 }

    sispm10403166lConfigIpAddress OBJECT-TYPE
               SYNTAX       IpAddress
               MAX-ACCESS   read-write
               STATUS       current
               DESCRIPTION
                    "Get/Set the IP address for 'tftp' 'upload config'
                    or 'download config'."
               ::= {     sispm10403166lConfig 4 }

    sispm10403166lConfigFilename OBJECT-TYPE
               SYNTAX       DisplayString
               MAX-ACCESS   read-write
               STATUS       current
               DESCRIPTION
                    "Get/Set the filename in switch for 'tftp'
                    'upload config' or 'download config'."
               ::= {     sispm10403166lConfig 5 }

    sispm10403166lConfigFileTable OBJECT-TYPE
               SYNTAX      SEQUENCE OF     SISPM10403166LConfigFileEntry
               MAX-ACCESS  not-accessible
               STATUS      current
               DESCRIPTION
                   "The config file tabe."
               ::= {     sispm10403166lConfig 6 }

    sispm10403166lConfigFileEntry OBJECT-TYPE
               SYNTAX          SISPM10403166LConfigFileEntry
               MAX-ACCESS  not-accessible
               STATUS      current
               DESCRIPTION
                   "an entry in the config file tabe."
               INDEX    {     sispm10403166lConfigFileIndex }
               ::= {     sispm10403166lConfigFileTable 1 }

    SISPM10403166LConfigFileEntry             ::= SEQUENCE {
                sispm10403166lConfigFileIndex         Integer32,
                sispm10403166lShowConfigFileName      DisplayString,
                sispm10403166lActivateConfigCmd       ActivateCmd,
                sispm10403166lDeleteConfigCmd         ActivateCmd,
                sispm10403166lUploadConfigCmd         INTEGER,
                sispm10403166lDownloadConfigCmd       INTEGER
                }

    sispm10403166lConfigFileIndex OBJECT-TYPE
               SYNTAX      Integer32(1..255)
               MAX-ACCESS  not-accessible
               STATUS      current
               DESCRIPTION
                   "The config file index."
               ::= {     sispm10403166lConfigFileEntry 1 }

    sispm10403166lShowConfigFileName OBJECT-TYPE
               SYNTAX      DisplayString
               MAX-ACCESS  read-write
               STATUS      current
               DESCRIPTION
                   "Shows the config file name. Without config filename:'NewConfig'
                   is temp file when 'activate download
                   config' can 'create new file' and 'change create filename'."
               ::= {     sispm10403166lConfigFileEntry 2 }

    sispm10403166lActivateConfigCmd OBJECT-TYPE
               SYNTAX       ActivateCmd
               MAX-ACCESS   read-write
               STATUS       current
               DESCRIPTION
                    "Activate config command.
                     noAction(0) : do nothing  (read only).
                     activate(1) : activate the config"
               DEFVAL  { noAction }
               ::= {     sispm10403166lConfigFileEntry 3 }

    sispm10403166lDeleteConfigCmd OBJECT-TYPE
               SYNTAX       ActivateCmd
               MAX-ACCESS   read-write
               STATUS       current
               DESCRIPTION
                    "Delete config command.
                     noAction(0) : do nothing  (read only).
                     activate(1) : delete the config"
               DEFVAL  { noAction }
               ::= {     sispm10403166lConfigFileEntry 4 }

    sispm10403166lDownloadConfigCmd OBJECT-TYPE
               SYNTAX       INTEGER  {  noAction ( 0 ),
                                        tftpUpload ( 1 )
                                        --ftpUpload ( 2 )
                                     }
               MAX-ACCESS   read-write
               STATUS       current
               DESCRIPTION
                    "Download config command.
                     noAction   (0) - do nothing   (read only).
                     tftpUpload (1) - activate 'tftp' config download."
               DEFVAL  { noAction }
               ::= {     sispm10403166lConfigFileEntry 5 }

    sispm10403166lUploadConfigCmd OBJECT-TYPE
               SYNTAX       INTEGER  {  noAction ( 0 ),
                                        tftpDownload ( 1 )
                                        --ftpDownload ( 2 )
                                     }
               MAX-ACCESS   read-write
               STATUS       current
               DESCRIPTION
                    "Upload config command.
                     noAction   (0) - do nothing   (read only).
                     tftpDownload (1) - activate 'tftp' config upload.
					 For merge/replace running-config:
					 1:merge
					 3:replace"
               DEFVAL  { noAction }
               ::= {     sispm10403166lConfigFileEntry 6 }

-- =======================================================================================================================
sispm10403166lDiagnostics                                           OBJECT IDENTIFIER ::= { sispm10403166lMaintenance 5 }

sispm10403166lPingIpAddress OBJECT-TYPE
   SYNTAX      IpAddress
   MAX-ACCESS  read-write
   STATUS      current
   DESCRIPTION
       " The destination IP Address. "
   ::= { sispm10403166lDiagnostics 1 }

sispm10403166lPingSize OBJECT-TYPE
   SYNTAX      Integer32(60..1400)
   MAX-ACCESS  read-write
   STATUS      current
   DESCRIPTION
       " Size of ICMP echo packet.
         range : 60-1400, default : 64. "
   ::= { sispm10403166lDiagnostics 2 }

sispm10403166lDoPingConfig OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sispm10403166lDiagnostics 3 }

sispm10403166lPingResult OBJECT-TYPE
   SYNTAX      DisplayString
   MAX-ACCESS  read-only
   STATUS      current
   DESCRIPTION
       " Show ping result. "
   ::= { sispm10403166lDiagnostics 4 }

sispm10403166lPing6IpAddress OBJECT-TYPE
   SYNTAX      DisplayString
   MAX-ACCESS  read-write
   STATUS      current
   DESCRIPTION
       " The destination IPv6 Address. "
   ::= { sispm10403166lDiagnostics 5 }

sispm10403166lPing6Size OBJECT-TYPE
   SYNTAX      Integer32(60..1400)
   MAX-ACCESS  read-write
   STATUS      current
   DESCRIPTION
       " Size of ICMP echo packet.
         range : 60-1400. "
   ::= { sispm10403166lDiagnostics 6 }

sispm10403166lPing6EgressInterface OBJECT-TYPE
   SYNTAX      Integer32(1..4095)
   MAX-ACCESS  read-write
   STATUS      current
   DESCRIPTION
       "The VLAN ID (VID) of the specific egress IPv6 interface which ICMP packet goes."
   ::= { sispm10403166lDiagnostics 7 }

sispm10403166lDoPing6Config OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sispm10403166lDiagnostics 8 }

sispm10403166lPing6Result OBJECT-TYPE
   SYNTAX      DisplayString
   MAX-ACCESS  read-only
   STATUS      current
   DESCRIPTION
       " Show ping result. "
   ::= { sispm10403166lDiagnostics 9 }

sispm10403166ltracerouteIpAddress OBJECT-TYPE
   SYNTAX      IpAddress
   MAX-ACCESS  read-write
   STATUS      current
   DESCRIPTION
       " The destination IP Address. "
   ::= { sispm10403166lDiagnostics 10 }

--sispm10403166ltracerouteProtocol OBJECT-TYPE
--   SYNTAX      Integer32(0..2)
--   MAX-ACCESS  read-write
--   STATUS      current
--   DESCRIPTION
--       " Specify protocol including icmp=0, udp=1 and tcp=2.
--         range : 0-2, default : 0. "
--   ::= { sispm10403166lDiagnostics 11 }

sispm10403166ltracerouteWaittime OBJECT-TYPE
   SYNTAX      Integer32(1..60)
   MAX-ACCESS  read-write
   STATUS      current
   DESCRIPTION
       " Specify wait time for waiting probe packets come back.
         range : 1-60(sec), default : 5(sec). "
   ::= { sispm10403166lDiagnostics 12 }

sispm10403166ltracerouteMaxTTL OBJECT-TYPE
   SYNTAX      Integer32(1..255)
   MAX-ACCESS  read-write
   STATUS      current
   DESCRIPTION
       " Specify max TTL.
         range : 1-255, default : 30. "
   ::= { sispm10403166lDiagnostics 13 }

sispm10403166ltracerouteNqueries OBJECT-TYPE
   SYNTAX      Integer32(1..10)
   MAX-ACCESS  read-write
   STATUS      current
   DESCRIPTION
       " Specify number of probe packets.
         range : 1-10, default : 3. "
   ::= { sispm10403166lDiagnostics 14 }

sispm10403166lDotracerouteConfig OBJECT-TYPE
   SYNTAX      Integer32(1)
   MAX-ACCESS  read-write
   STATUS      current
   DESCRIPTION
       "Do traceroute-config.
         Get this OID always return zero.
         1 - ping. Uses the traceroute program to get
         ip address of the middle gateway. "
   ::= { sispm10403166lDiagnostics 15 }

sispm10403166ltracerouteResult OBJECT-TYPE
   SYNTAX      DisplayString
   MAX-ACCESS  read-only
   STATUS      current
   DESCRIPTION
       " Show traceroute result. "
   ::= { sispm10403166lDiagnostics 16 }

sispm10403166lCableDiagnostics                                           OBJECT IDENTIFIER ::= { sispm10403166lDiagnostics 17 }

sispm10403166lCableDiagnosticsTest OBJECT-TYPE
   SYNTAX      Integer32
   MAX-ACCESS  read-write
   STATUS      current
   DESCRIPTION
       "Run Cable Diagnostics.
        port, range : 1 - port number."
   ::= { sispm10403166lCableDiagnostics 1 }

sispm10403166lCableDiagnosticsTable OBJECT-TYPE
   SYNTAX      SEQUENCE OF SISPM10403166LCableDiagnosticsEntry
   MAX-ACCESS  not-accessible
   STATUS      current
   DESCRIPTION
       " "
   ::= { sispm10403166lCableDiagnostics 2 }

sispm10403166lCableDiagnosticsEntry OBJECT-TYPE
   SYNTAX      SISPM10403166LCableDiagnosticsEntry
   MAX-ACCESS  not-accessible
   STATUS      current
   DESCRIPTION
       " "
   INDEX    { sispm10403166lCableDiagnosticsPort  }
   ::= { sispm10403166lCableDiagnosticsTable 1 }

SISPM10403166LCableDiagnosticsEntry ::= SEQUENCE {
   sispm10403166lCableDiagnosticsPort        Integer32,
   sispm10403166lCableDiagnosticsLinkStatus  DisplayString,
   sispm10403166lCableDiagnosticsTestResult  DisplayString,
   sispm10403166lCableDiagnosticsLength      DisplayString
}

sispm10403166lCableDiagnosticsPort OBJECT-TYPE
   SYNTAX      Integer32(1..65535)
   MAX-ACCESS  not-accessible
   STATUS      current
   DESCRIPTION
       "port index"
   ::= { sispm10403166lCableDiagnosticsEntry 1 }

sispm10403166lCableDiagnosticsLinkStatus OBJECT-TYPE
   SYNTAX      DisplayString
   MAX-ACCESS  read-only
   STATUS      current
   DESCRIPTION
       "The status of the cable."
   ::= { sispm10403166lCableDiagnosticsEntry 2 }

sispm10403166lCableDiagnosticsTestResult OBJECT-TYPE
   SYNTAX      DisplayString
   MAX-ACCESS  read-only
   STATUS      current
   DESCRIPTION
       "Test Result of the cable."
   ::= { sispm10403166lCableDiagnosticsEntry 3 }

sispm10403166lCableDiagnosticsLength OBJECT-TYPE
   SYNTAX      DisplayString
   MAX-ACCESS  read-only
   STATUS      current
   DESCRIPTION
       "The length (in meters) of the cable."
   ::= { sispm10403166lCableDiagnosticsEntry 4 }

sispm10403166lSwitchRebootSchedule OBJECT IDENTIFIER ::= { sispm10403166lMaintenance 6 }

sispm10403166lSwitchRebootMode OBJECT-TYPE
   SYNTAX      Integer32
   MAX-ACCESS  read-write
   STATUS      current
   DESCRIPTION
       "Switch Reboot Mode.
	    0:disable
		1:enable"
   ::= { sispm10403166lSwitchRebootSchedule 1 }

sispm10403166lSwitchRebootTimeTable OBJECT-TYPE
   SYNTAX      SEQUENCE OF SISPM10403166LSwitchRebootTimeEntry
   MAX-ACCESS  not-accessible
   STATUS      current
   DESCRIPTION
       " Configure the Switch reboot time. "
   ::= { sispm10403166lSwitchRebootSchedule 2 }

sispm10403166lSwitchRebootTimeEntry OBJECT-TYPE
   SYNTAX      SISPM10403166LSwitchRebootTimeEntry
   MAX-ACCESS  not-accessible
   STATUS      current
   DESCRIPTION
       " "
   INDEX    { sispm10403166lSwitchRebootWeekIndex  }
   ::= { sispm10403166lSwitchRebootTimeTable 1 }

SISPM10403166LSwitchRebootTimeEntry ::= SEQUENCE {
   sispm10403166lSwitchRebootWeekIndex	       Integer32,
   sispm10403166lSwitchRebootTimeHour           Integer32,
   sispm10403166lSwitchRebootTimeMinute         Integer32
}

sispm10403166lSwitchRebootWeekIndex OBJECT-TYPE
   SYNTAX      Integer32 (1..7)
   MAX-ACCESS  not-accessible
   STATUS      current
   DESCRIPTION
       "Switch reboot week index.
	   1: Sun, 2: Mon, 3:Tue, 4: Wed, 5: Thu, 6: Fri, 7: Sat"
   ::= { sispm10403166lSwitchRebootTimeEntry 1 }

sispm10403166lSwitchRebootTimeHour OBJECT-TYPE
   SYNTAX      Integer32 (-1..23)
   MAX-ACCESS  read-write
   STATUS      current
   DESCRIPTION
       "Switch Reboot Time (Hour). Range: 0-23.
	   -1:disable"
   ::= { sispm10403166lSwitchRebootTimeEntry 2 }

sispm10403166lSwitchRebootTimeMinute OBJECT-TYPE
   SYNTAX      Integer32 (-1..55)
   MAX-ACCESS  read-write
   STATUS      current
   DESCRIPTION
       "Switch Reboot Time (Minute). Range:0,5,10,...,55.
	   -1:disable"
   ::= { sispm10403166lSwitchRebootTimeEntry 3 }

sispm10403166liPerf OBJECT IDENTIFIER ::= { sispm10403166lMaintenance 7 }

sispm10403166liPerfMethod OBJECT-TYPE
   SYNTAX      Integer32
   MAX-ACCESS  read-write
   STATUS      current
   DESCRIPTION
       "The measuring method of iPerf.
	    2:iPerf version 2
		3:iPerf version 3"
   ::= { sispm10403166liPerf 2 }

sispm10403166liPerfHost OBJECT-TYPE
   SYNTAX      IpAddress
   MAX-ACCESS  read-write
   STATUS      current
   DESCRIPTION
       "The address of iPerf server. "
   ::= { sispm10403166liPerf 3 }

sispm10403166liPerfPort OBJECT-TYPE
   SYNTAX      Integer32
   MAX-ACCESS  read-write
   STATUS      current
   DESCRIPTION
       "The listen port of iPerf server. The default value is 5001 for iPerf, 5201 for iPerf3. "
   ::= { sispm10403166liPerf 4 }

sispm10403166liPerfTime OBJECT-TYPE
   SYNTAX      Integer32
   MAX-ACCESS  read-write
   STATUS      current
   DESCRIPTION
       "The time in seconds to transmit for (default 10 secs). "
   ::= { sispm10403166liPerf 5 }

sispm10403166liPerfInterval OBJECT-TYPE
   SYNTAX      Integer32
   MAX-ACCESS  read-write
   STATUS      current
   DESCRIPTION
       "The time in seconds between periodic bandwidth reports (default no periodic reports). "
   ::= { sispm10403166liPerf 6 }

sispm10403166liPerfTTL OBJECT-TYPE
   SYNTAX      Integer32
   MAX-ACCESS  read-write
   STATUS      current
   DESCRIPTION
       "The time-to-live, for multicast (default 1). "
   ::= { sispm10403166liPerf 7 }

sispm10403166liPerfStart OBJECT-TYPE
   SYNTAX      Integer32
   MAX-ACCESS  read-write
   STATUS      current
   DESCRIPTION
       "Start iPerf
	   1:Start."
   ::= { sispm10403166liPerf 8 }

sispm10403166liPerfResult OBJECT-TYPE
   SYNTAX      DisplayString
   MAX-ACCESS  read-only
   STATUS      current
   DESCRIPTION
       "Test result of iPerf"
   ::= { sispm10403166liPerf 9 }

-- =======================================================================================================================
sispm10403166lTrap                                                  OBJECT IDENTIFIER ::= { sispm10403166lProductId 5 }

sispm10403166lTrapEvent                                             OBJECT IDENTIFIER ::= { sispm10403166lTrap 1 }

sispm10403166lEmergency NOTIFICATION-TYPE
  OBJECTS   { sispm10403166lInformation }
  STATUS        current
    DESCRIPTION
        "The severity level is Emergency. Emergency conditions."
    ::= { sispm10403166lTrapEvent 1 }

sispm10403166lAlert NOTIFICATION-TYPE
  OBJECTS   { sispm10403166lInformation }
  STATUS        current
    DESCRIPTION
        "The severity level is Alert. Alert conditions."
    ::= { sispm10403166lTrapEvent 2 }

sispm10403166lCritical NOTIFICATION-TYPE
  OBJECTS   { sispm10403166lInformation }
  STATUS        current
    DESCRIPTION
        "The severity level is Critical. Critical conditions."
    ::= { sispm10403166lTrapEvent 3 }

sispm10403166lError NOTIFICATION-TYPE
  OBJECTS   { sispm10403166lInformation }
  STATUS        current
    DESCRIPTION
        "The severity level is Error. Error conditions."
    ::= { sispm10403166lTrapEvent 4 }

sispm10403166lWarning NOTIFICATION-TYPE
  OBJECTS   { sispm10403166lInformation }
  STATUS        current
    DESCRIPTION
        "The severity level is Warning. Warning conditions."
    ::= { sispm10403166lTrapEvent 5 }

sispm10403166lNotice NOTIFICATION-TYPE
  OBJECTS   { sispm10403166lInformation }
  STATUS        current
    DESCRIPTION
        "The severity level is Notice. Notice conditions."
    ::= { sispm10403166lTrapEvent 6 }

sispm10403166lInformational NOTIFICATION-TYPE
  OBJECTS   { sispm10403166lInformation }
  STATUS        current
    DESCRIPTION
        "The severity level is Informational. Informational conditions."
    ::= { sispm10403166lTrapEvent 7 }

sispm10403166lDebug NOTIFICATION-TYPE
  OBJECTS   { sispm10403166lInformation }
  STATUS        current
    DESCRIPTION
        "The severity level is Debug. Debug conditions."
    ::= { sispm10403166lTrapEvent 8 }

sispm10403166lTrapVariable                                          OBJECT IDENTIFIER ::= { sispm10403166lTrap 2 }

sispm10403166lInformation OBJECT-TYPE
    SYNTAX      DisplayString
    MAX-ACCESS  read-only
    STATUS      current
    DESCRIPTION
        "Trap information."
    ::= { sispm10403166lTrapVariable 1 }

sispm10403166lZTPTrap                                             OBJECT IDENTIFIER ::= { sispm10403166lTrap 3 }

sispm10403166lZTPTrapEvent                                        OBJECT IDENTIFIER ::= { sispm10403166lZTPTrap 0 }

sispm10403166lZTPOnboardTrap NOTIFICATION-TYPE
  OBJECTS   { sysObjectID, sispm10403166lSnmpSystemVersion, sispm10403166lSnmpSystemReadCommunity,
              sispm10403166lSnmpSystemWriteCommunity, sispm10403166lSystemInfoSeriesNumber,
              sispm10403166lSystemInfoHostMACAddress, sispm10403166lIPInterfacesIPv4Address }
  STATUS        current
    DESCRIPTION
        "The switch information."
    ::= { sispm10403166lZTPTrapEvent 1 }

END
