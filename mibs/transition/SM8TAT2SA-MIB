--================================================================================================================
--  SM8TAT2SA-MIB
--================================================================================================================

SM8TAT2SA-MIB DEFINITIONS ::= BEGIN

IMPORTS
    DisplayString,MacAddress,TEXTUAL-CONVENTION,RowStatus                                          FROM SNMPv2-TC
    MODULE-COMPLIANCE,OBJECT-GROUP,NOTIFICATION-GROUP                                              FROM SNMPv2-CONF
    ifIndex                                                                                        FROM IF-MIB
    Unsigned32,Counter64                                                                           FROM SNMPv2-SMI
    enterprises,MODULE-IDENTITY,OBJECT-TYPE,NOTIFICATION-TYPE,Integer32,Counter32,IpAddress        FROM SNMPv2-SMI;

transition  MODULE-IDENTITY
    LAST-UPDATED "202203170850Z"  -- Mar 17, 2022
    ORGANIZATION "Corp."
    CONTACT-INFO " "
    DESCRIPTION  "Smart Managed Switch, 8-port Gigabit PoE+, 2-port 100/1000 SFP"
    REVISION "202203170850Z" --Mar 17, 2022
    DESCRIPTION "Initial Version"
    ::= { enterprises 868 }

switch OBJECT IDENTIFIER ::= { transition 2}
sm8tat2saProductId OBJECT IDENTIFIER ::= { switch 71}

--================================================================================================================
     OperState ::= TEXTUAL-CONVENTION
       STATUS current
       DESCRIPTION
                      "Oper state."
       SYNTAX INTEGER { up ( 1 ) , down ( 2 ) }

     AdminMode ::= TEXTUAL-CONVENTION
       STATUS current
       DESCRIPTION
            "The Admin state - default: disable(0)."
       SYNTAX INTEGER { disable(0), enable(1) }

     AdminMode2 ::= TEXTUAL-CONVENTION
       STATUS current
       DESCRIPTION
            "The Admin state - default: disable(0)."
       SYNTAX INTEGER { disable(0), enable(1), notSupported(2) }

     ActivateCmd ::= TEXTUAL-CONVENTION
       STATUS current
       DESCRIPTION
            "Used to activate commands. default: noAction(0). "
       SYNTAX INTEGER { noAction ( 0 ),
                                  activate ( 1 )
                               }

     KeyType ::= TEXTUAL-CONVENTION
       STATUS current
       DESCRIPTION
           "The key type specifying the key generated for frames received
            on the port.
            0 : Normal,
            1 : Double Tag,
            2 : IP Address,
            3 : MAC and IP Address."
        SYNTAX INTEGER { normal ( 0 ),
                               doubleTag ( 1 ),
                               ipAddr ( 2 ),
                               macAndIpAddr ( 3 )
                             }

     FrameRate ::= TEXTUAL-CONVENTION
       STATUS current
       DESCRIPTION
           "The values for frame rate"
       SYNTAX INTEGER {
                            threeHundredFramesPerSec (0),
                            oneHundredFramesPerSec (1),
                            tenFramesPerSec (2),
                            oneFramePerSec (3),
                            sixFramesPerMin (4),
                            oneFramePerMin (5),
                            sixFramesPerHour (6)
                            }

     DayOfWeek ::= TEXTUAL-CONVENTION
       STATUS current
       DESCRIPTION
            "Used to set the days of the week."
       SYNTAX INTEGER {mon(1),tue(2),wed(3),thur(4),
                             fri(5),sat(6),sun(7) }

     Month ::= TEXTUAL-CONVENTION
       STATUS current
       DESCRIPTION
            "Used to set the month."
       SYNTAX INTEGER {jan(1),feb(2),march(3),april(4),
                             may(5),june(6),july(7),aug(8),
                             sept(9),oct(10),nov(11),dec(12)}

     PortSelect ::= TEXTUAL-CONVENTION
         DISPLAY-HINT "255a"
         STATUS current
         DESCRIPTION
             "Each octet within this value specifies a set of eight
             ports, with the first octet specifying ports 1 through
             8, the second octet specifying ports 9 through 16, etc.
             Within each octet, the least significant bit represents
             the lowest numbered port, and the most significant bit
             represents the highest numbered port. Thus, each port
             of the bridge is represented by a single bit within the
             value of this object. If that bit has a value of '1'
             then that port is included in the set of ports; the port
             is not included if its bit has a value of '0'."
         SYNTAX OCTET STRING (SIZE(0..255))

     VoiceVlanPortDiscoveryProtocol ::= TEXTUAL-CONVENTION
         STATUS current
         DESCRIPTION
             "This enumeration indicates per port Voice VLAN discovery protocol."
         SYNTAX INTEGER { oui(0), lldp(1), both(2) }

     VoiceVlanPortManagementType ::= TEXTUAL-CONVENTION
         STATUS current
         DESCRIPTION
             "This enumeration indicates per port Voice VLAN function administrative
              type."
         SYNTAX INTEGER { automatic(1), forced(2) }

     SeverityLevel ::= TEXTUAL-CONVENTION
       STATUS current
       DESCRIPTION
            "The Severity Level.
             0 : Emerg, 1 : Alert, 2 : Critical, 3 : Error, 4 : Warning, 5 : Notice, 6 : Info, 7 : Debug."
       SYNTAX INTEGER {
                    emergency(0),
                    alert(1),
                    critical(2),
                    error(3),
                    warning(4),
                    notice(5),
                    info(6),
                    debug(7)
               }

     LldpmedAltitudeType ::= TEXTUAL-CONVENTION
         STATUS current
         DESCRIPTION
             "This enumerations the altitude type."
         SYNTAX INTEGER { meters(1), floors(2) }

     LldpmedDatumType ::= TEXTUAL-CONVENTION
         STATUS current
         DESCRIPTION
             "This enumerations the datum (geodetic system)."
         SYNTAX INTEGER { wgs84(1), nad83navd88(2), nad83mllw(3) }

-- ================================================================================================================
sm8tat2saSystem OBJECT IDENTIFIER ::= { sm8tat2saProductId 1 }

-- *************************************************************
-- Objects in the sm8tat2saSystemInformation Group
-- *************************************************************
sm8tat2saSystemInformation OBJECT IDENTIFIER ::= { sm8tat2saSystem 1 }

sm8tat2saSystemInfoModelName OBJECT-TYPE
   SYNTAX DisplayString
   MAX-ACCESS read-only
   STATUS current
   DESCRIPTION
       "Model Name."
   ::= { sm8tat2saSystemInformation 1 }

sm8tat2saSystemInfoSystemDescript OBJECT-TYPE
   SYNTAX DisplayString
   MAX-ACCESS read-only
   STATUS current
   DESCRIPTION
       "System Description."
   ::= { sm8tat2saSystemInformation 2 }

sm8tat2saSystemInfoHardwareVersion OBJECT-TYPE
   SYNTAX DisplayString
   MAX-ACCESS read-only
   STATUS current
   DESCRIPTION
       "Hardware Version."
   ::= { sm8tat2saSystemInformation 3 }

sm8tat2saSystemInfoMechanicalVersion OBJECT-TYPE
   SYNTAX DisplayString
   MAX-ACCESS read-only
   STATUS current
   DESCRIPTION
       "Mechanical Version."
   ::= { sm8tat2saSystemInformation 4 }

sm8tat2saSystemInfoFirmwareVersion OBJECT-TYPE
   SYNTAX DisplayString
   MAX-ACCESS read-only
   STATUS current
   DESCRIPTION
       "Firmware Version."
   ::= { sm8tat2saSystemInformation 5 }

sm8tat2saSystemInfoHostMACAddress OBJECT-TYPE
   SYNTAX DisplayString
   MAX-ACCESS read-only
   STATUS current
   DESCRIPTION
       "MAC Address."
   ::= { sm8tat2saSystemInformation 6 }

sm8tat2saSystemInfoSeriesNumber OBJECT-TYPE
   SYNTAX DisplayString
   MAX-ACCESS read-only
   STATUS current
   DESCRIPTION
       "Series Number."
   ::= { sm8tat2saSystemInformation 7 }

sm8tat2saSystemInfoSystemName OBJECT-TYPE
   SYNTAX DisplayString
   MAX-ACCESS read-write
   STATUS current
   DESCRIPTION
       "System Name."
   ::= { sm8tat2saSystemInformation 8 }

sm8tat2saSystemInfoLocation OBJECT-TYPE
   SYNTAX DisplayString
   MAX-ACCESS read-write
   STATUS current
   DESCRIPTION
       "Location."
   ::= { sm8tat2saSystemInformation 9 }

sm8tat2saSystemInfoContact OBJECT-TYPE
   SYNTAX DisplayString
   MAX-ACCESS read-write
   STATUS current
   DESCRIPTION
       "Contact."
   ::= { sm8tat2saSystemInformation 10 }

sm8tat2saSystemInfoSystemDate OBJECT-TYPE
   SYNTAX DisplayString
   MAX-ACCESS read-only
   STATUS current
   DESCRIPTION
       "System Date."
   ::= { sm8tat2saSystemInformation 11 }

sm8tat2saSystemInfoSystemUptime OBJECT-TYPE
   SYNTAX DisplayString
   MAX-ACCESS read-only
   STATUS current
   DESCRIPTION
       "System Uptime."
   ::= { sm8tat2saSystemInformation 12 }

sm8tat2saSystemInfoPoEFirmwareVersion OBJECT-TYPE
   SYNTAX DisplayString
   MAX-ACCESS read-only
   STATUS current
   DESCRIPTION
       "PoE Firmware Version."
   ::= { sm8tat2saSystemInformation 15 }

-- *************************************************************
-- Objects in the sm8tat2saSystemTime Group
-- *************************************************************
sm8tat2saSystemTimeConf OBJECT IDENTIFIER ::= { sm8tat2saSystem 2 }

sm8tat2saSystemTimeManual OBJECT IDENTIFIER ::= { sm8tat2saSystemTimeConf 1 }

sm8tat2saSystemTimeManualClockSource OBJECT-TYPE
   SYNTAX INTEGER { useLocal(0), useNTP(1) }
   MAX-ACCESS read-write
   STATUS current
   DESCRIPTION
       "0 : Use Local Settings,
        1 : Use NTP Server."
   ::= { sm8tat2saSystemTimeManual 1 }

sm8tat2saSystemTimeManualLocaltime OBJECT-TYPE
   SYNTAX DisplayString
   MAX-ACCESS read-write
   STATUS current
   DESCRIPTION
       "Get/Set the system time of the device.
        The input format is 'Year-Month-Day Hour:Minute:Second'.
        ex: 2011-01-01 05:43:05 means 2011/1/1 - 05:43:05 .
        The value range:
        Year : 2010 - 2090,
        Mouth : 1 - 12,
        Day : 1 - 31,
        Hour : 0 - 23,
        Minute : 0 - 59,
        Sec : 0 - 59."
   ::= { sm8tat2saSystemTimeManual 2 }

sm8tat2saSystemTimeManualTimeZoneOffset OBJECT-TYPE
   SYNTAX Integer32 (-12..12)
   MAX-ACCESS read-write
   STATUS current
   DESCRIPTION
       "Get/Set the NTP Time Zone.
        The value range is between -12 and 12."
   ::= { sm8tat2saSystemTimeManual 3 }

sm8tat2saSystemTimeManualTimeZoneAcronym OBJECT-TYPE
   SYNTAX DisplayString
   MAX-ACCESS read-write
   STATUS current
   DESCRIPTION
       "User can set the acronym of the time zone. This is
        a User configurable acronym to identify the time zone.
        Max: 16 characters."
   ::= { sm8tat2saSystemTimeManual 4 }

sm8tat2saSystemTimeManualDaylightSavings OBJECT-TYPE
   SYNTAX INTEGER { disable(0), enable(1) }
   MAX-ACCESS read-write
   STATUS current
   DESCRIPTION
       "0 : Disable,
        1 : Enable."
   ::= { sm8tat2saSystemTimeManual 5 }

sm8tat2saSystemTimeManualTimeSetOffset OBJECT-TYPE
   SYNTAX Integer32(1..1440)
   MAX-ACCESS read-write
   STATUS current
   DESCRIPTION
       "Get/Set the Daylight Saving Time.
        The value range is between 1 and 1440 (minutes)."
   ::= { sm8tat2saSystemTimeManual 6 }

sm8tat2saSystemTimeManualDaylightSavingsMonthFrom OBJECT-TYPE
   SYNTAX Month
   MAX-ACCESS read-write
   STATUS current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { sm8tat2saSystemTimeManual 7 }

sm8tat2saSystemTimeManualDaylightSavingsWeekFrom OBJECT-TYPE
   SYNTAX INTEGER{
                        firstWeek(1),
                        secondWeek(2),
                        thirdWeek(3),
                        fourthWeek(4),
                        listWeek(5)
                        }
   MAX-ACCESS read-write
   STATUS current
   DESCRIPTION
       "Get/Set the Daylight Saving Time Week From.
        1 : first week, 2, 3, 4, 5 : last week"
   ::= { sm8tat2saSystemTimeManual 8 }

sm8tat2saSystemTimeManualDaylightSavingsDayFrom OBJECT-TYPE
   SYNTAX INTEGER {
                        monday(1),
                        tuseday(2),
                        wednesday(3),
                        thursday(4),
                        friday(5),
                        saturday(6),
                        sunday(7)
                        }
   MAX-ACCESS read-write
   STATUS current
   DESCRIPTION
       "Get/Set the Daylight Saving Time Day From.
        1 : Mon, 2 : Tue, 3 : Wed, 4 : Thu, 5 : Fri, 6 : Sat, 7 : Sun."
   ::= { sm8tat2saSystemTimeManual 9 }

sm8tat2saSystemTimeManualDaylightSavingsHourFrom OBJECT-TYPE
   SYNTAX Integer32(0..23)
   MAX-ACCESS read-write
   STATUS current
   DESCRIPTION
       "Get/Set the Daylight Saving Time Hour From.
        range: 0 - 23."
   ::= { sm8tat2saSystemTimeManual 10 }

sm8tat2saSystemTimeManualDaylightSavingsMonthTo OBJECT-TYPE
   SYNTAX Month
   MAX-ACCESS read-write
   STATUS current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { sm8tat2saSystemTimeManual 11 }

sm8tat2saSystemTimeManualDaylightSavingsWeekTo OBJECT-TYPE
   SYNTAX INTEGER{
                        firstWeek(1),
                        secondWeek(2),
                        thirdWeek(3),
                        fourthWeek(4),
                        listWeek(5)
                        }
   MAX-ACCESS read-write
   STATUS current
   DESCRIPTION
       "Get/Set the Daylight Saving Time Week To.
        1 : first week, 2, 3, 4, 5 : last week"
   ::= { sm8tat2saSystemTimeManual 12 }

sm8tat2saSystemTimeManualDaylightSavingsDayTo OBJECT-TYPE
   SYNTAX INTEGER {
                        monday(1),
                        tuseday(2),
                        wednesday(3),
                        thursday(4),
                        friday(5),
                        saturday(6),
                        sunday(7)
                        }
   MAX-ACCESS read-write
   STATUS current
   DESCRIPTION
       "Get/Set the Daylight Saving Time Day To.
        1 : Mon, 2 : Tue, 3 : Wed, 4 : Thu, 5 : Fri, 6 : Sat, 7 : Sun."
   ::= { sm8tat2saSystemTimeManual 13 }

sm8tat2saSystemTimeManualDaylightSavingsHourTo OBJECT-TYPE
   SYNTAX Integer32(0..23)
   MAX-ACCESS read-write
   STATUS current
   DESCRIPTION
       "Get/Set the Daylight Saving Time Hour To.
        range: 0 - 23."
   ::= { sm8tat2saSystemTimeManual 14 }

-- *************************************************************
-- Objects in the sm8tat2saSystemNTP Group
-- *************************************************************
sm8tat2saSystemTimeNTP OBJECT IDENTIFIER ::= { sm8tat2saSystemTimeConf 2 }

sm8tat2saSystemTimeNTPInterval OBJECT-TYPE
   SYNTAX Integer32(5..120)
   MAX-ACCESS read-write
   STATUS current
   DESCRIPTION
       "NTP poll interval.
        range : 5 min, 10 min, 15 min, 30 min, 60 min, 120 min"
   ::= { sm8tat2saSystemTimeNTP 1 }

sm8tat2saSystemTimeNTPTable OBJECT-TYPE
   SYNTAX SEQUENCE OF SM8TAT2SASystemTimeNTPEntry
   MAX-ACCESS not-accessible
   STATUS current
   DESCRIPTION
       " "
   ::= { sm8tat2saSystemTimeNTP 2 }

sm8tat2saSystemTimeNTPEntry OBJECT-TYPE
   SYNTAX SM8TAT2SASystemTimeNTPEntry
   MAX-ACCESS not-accessible
   STATUS current
   DESCRIPTION
       " "
   INDEX { sm8tat2saSystemTimeNTPIndex }
   ::= { sm8tat2saSystemTimeNTPTable 1 }

SM8TAT2SASystemTimeNTPEntry ::= SEQUENCE {
   sm8tat2saSystemTimeNTPIndex Integer32,
   sm8tat2saSystemTimeNTPServer DisplayString
}

sm8tat2saSystemTimeNTPIndex OBJECT-TYPE
   SYNTAX Integer32(1..6)
   MAX-ACCESS not-accessible
   STATUS current
   DESCRIPTION
       " The index of the ntp entry. "
   ::= { sm8tat2saSystemTimeNTPEntry 1 }

sm8tat2saSystemTimeNTPServer OBJECT-TYPE
   SYNTAX DisplayString
   MAX-ACCESS read-write
   STATUS current
   DESCRIPTION
       "Get/Set the NTP Time Server. You can use the IP address or domain name."
   ::= { sm8tat2saSystemTimeNTPEntry 2 }

-- *************************************************************
-- Start sm8tat2saSystemAccount group
-- *************************************************************
sm8tat2saSystemAccount OBJECT IDENTIFIER ::= { sm8tat2saSystem 3 }

sm8tat2saSystemUsersTable OBJECT-TYPE
   SYNTAX SEQUENCE OF SM8TAT2SASystemUsersEntry
   MAX-ACCESS not-accessible
   STATUS current
   DESCRIPTION
       " "
   ::= { sm8tat2saSystemAccount 1 }

sm8tat2saSystemUsersEntry OBJECT-TYPE
   SYNTAX SM8TAT2SASystemUsersEntry
   MAX-ACCESS not-accessible
   STATUS current
   DESCRIPTION
       " "
   INDEX { sm8tat2saUserIndex }
   ::= { sm8tat2saSystemUsersTable 1 }

SM8TAT2SASystemUsersEntry ::= SEQUENCE {
   sm8tat2saUserIndex Integer32,
   sm8tat2saUserName DisplayString,
   sm8tat2saPassword DisplayString,
   sm8tat2saUserPrivilegeLevel Integer32,
   sm8tat2saAccountUserRowStatus RowStatus
}

sm8tat2saUserIndex OBJECT-TYPE
   SYNTAX Integer32 (1..20)
   MAX-ACCESS not-accessible
   STATUS current
   DESCRIPTION
       "The user Config Index."
   ::= { sm8tat2saSystemUsersEntry 1 }

sm8tat2saUserName OBJECT-TYPE
   SYNTAX DisplayString (SIZE (1..31))
   MAX-ACCESS read-create
   STATUS current
   DESCRIPTION
       "A string identifying the user name for the entry.
        string length: 1-31."
   ::= { sm8tat2saSystemUsersEntry 2 }

sm8tat2saPassword OBJECT-TYPE
   SYNTAX DisplayString (SIZE (1..31))
   MAX-ACCESS read-create
   STATUS current
   DESCRIPTION
       "The password of the user.
        string length: 0-31."
   ::= { sm8tat2saSystemUsersEntry 3 }

sm8tat2saUserPrivilegeLevel OBJECT-TYPE
   SYNTAX Integer32 (0..15)
   MAX-ACCESS read-create
   STATUS current
   DESCRIPTION
       "The privilege level of the user.If the privilege level
        value is 15, it can access all groups.range: 0-15."
   ::= { sm8tat2saSystemUsersEntry 4 }

sm8tat2saAccountUserRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm8tat2saSystemUsersEntry 5 }

-- *************************************************************
-- Start sm8tat2saIP group
-- *************************************************************
sm8tat2saIP OBJECT IDENTIFIER ::= { sm8tat2saSystem 4 }

sm8tat2saIPConfiguration OBJECT IDENTIFIER ::= { sm8tat2saIP 1 }

sm8tat2saDNSServerMode OBJECT-TYPE
   SYNTAX INTEGER {noDNSServer(0), configured(1), fromThisDHCPInterface(2), fromAnyDHCPInterface(3)}
   MAX-ACCESS read-write
   STATUS current
   DESCRIPTION
       "DNS Server Mode.
        0: No DNS Server
        1: Configured
        2: From this DHCP interface
        3: From any DHCP interfaces
        If set: 1:Configured, please also set IPV4 or IPv6 address to DNSServerValueIPVLAN.
        If set: 2:From this DHCP interface, it will set DNSServerValueIPVLAN to VLAN 1 for default, please set it to your value."
   ::= { sm8tat2saIPConfiguration 1 }

sm8tat2saDNSServerIPAddress OBJECT-TYPE
   SYNTAX DisplayString
   MAX-ACCESS read-write
   STATUS current
   DESCRIPTION
       "DNS IPv4/IPv6 Address.
        For set IPv4/IPv6 Address, please set DNSServerMode to : 1:Configured first."
   ::= { sm8tat2saIPConfiguration 2 }

sm8tat2saDNSServerVLAN OBJECT-TYPE
   SYNTAX Integer32 (1..4095)
   MAX-ACCESS read-write
   STATUS current
   DESCRIPTION
       "VLAN value.
        For set VLAN value, please set DNSServerMode to : 2:From this DHCP interface first.
        For set VLAN value, please set an interface with IPv4 DHCP enable. And then set VLAN to it."
   ::= { sm8tat2saIPConfiguration 3 }

sm8tat2saIPInterfacesTable OBJECT-TYPE
   SYNTAX SEQUENCE OF SM8TAT2SAIPInterfacesEntry
   MAX-ACCESS not-accessible
   STATUS current
   DESCRIPTION
       "A table of IP interface for switch."
    ::= { sm8tat2saIPConfiguration 4 }

sm8tat2saIPInterfacesEntry OBJECT-TYPE
    SYNTAX SM8TAT2SAIPInterfacesEntry
    MAX-ACCESS not-accessible
    STATUS current
    DESCRIPTION
        "An entry in the sm8tat2saIPInterfacesTable."
    INDEX { sm8tat2saIPInterfacesIndex }
    ::= { sm8tat2saIPInterfacesTable 1 }

SM8TAT2SAIPInterfacesEntry ::=
    SEQUENCE {
        sm8tat2saIPInterfacesIndex Integer32,
        sm8tat2saIPInterfacesVLAN Integer32,
        sm8tat2saIPInterfacesIPv4DHCPEnable Integer32,
        sm8tat2saIPInterfacesIPv4DHCPFallback Integer32,
        sm8tat2saIPInterfacesIPv4DHCPCurrentLease DisplayString,
        sm8tat2saIPInterfacesIPv4Address DisplayString,
        sm8tat2saIPInterfacesIPv4Mask Integer32,
        sm8tat2saIPInterfacesIPv6Address DisplayString,
        sm8tat2saIPInterfacesIPv6Mask Integer32,
        sm8tat2saIPInterfacesRowStatus RowStatus
    }

sm8tat2saIPInterfacesIndex OBJECT-TYPE
   SYNTAX Integer32 (1..128)
   MAX-ACCESS not-accessible
   STATUS current
   DESCRIPTION
       "Interface Table Index"
   ::= { sm8tat2saIPInterfacesEntry 1 }

sm8tat2saIPInterfacesVLAN OBJECT-TYPE
   SYNTAX Integer32 (1..4095)
   MAX-ACCESS read-create
   STATUS current
   DESCRIPTION
       "VLAN ID for interface, range: 1-4095.
        If you add a new VLAN ID here, you also need to set IPInterfacesIPv4Address, IPInterfacesIPv4Mask, or IPInterfacesIPv6Address, IPInterfacesIPv6Mask."
   ::= { sm8tat2saIPInterfacesEntry 2 }

sm8tat2saIPInterfacesIPv4DHCPEnable OBJECT-TYPE
   SYNTAX Integer32 (0|1)
   MAX-ACCESS read-create
   STATUS current
   DESCRIPTION
       "IPv4 DHCP Setting for interface.
        Please add IPInterfacesVLAN first if you want to set IPInterfacesIPv4DHCP to an empty entry in table.
        default:0
        0: disable
        1: enable"
   ::= { sm8tat2saIPInterfacesEntry 3 }

sm8tat2saIPInterfacesIPv4DHCPFallback OBJECT-TYPE
   SYNTAX Integer32
   MAX-ACCESS read-create
   STATUS current
   DESCRIPTION
       "IPv4 DHCP fallbcak. range: 1-4294967295 seconds.
        Please add IPInterfacesVLAN first if you want to set IPInterfacesIPv4DHCPFallback to an empty entry in table.
        Please enable IPInterfacesIPv4DHCP first if you want to set IPInterfacesIPv4DHCPFallback."
   ::= { sm8tat2saIPInterfacesEntry 4 }

sm8tat2saIPInterfacesIPv4DHCPCurrentLease OBJECT-TYPE
   SYNTAX DisplayString
   MAX-ACCESS read-only
   STATUS current
   DESCRIPTION
       "IPv4 DHCP Current Lease Address for interface."
   ::= { sm8tat2saIPInterfacesEntry 5 }

sm8tat2saIPInterfacesIPv4Address OBJECT-TYPE
   SYNTAX DisplayString
   MAX-ACCESS read-create
   STATUS current
   DESCRIPTION
       "IPv4 address for interface.
        Please add IPInterfacesVLAN first if you want to set IPInterfacesIPv4Address to an empty entry in table.
        If you set IPInterfacesIPv4Address, please also set IPInterfacesIPv4Mask.
        If you set IPInterfacesIPv4Address and not set IPInterfacesIPv4Mask before, it will be set to value default 24."
   ::= { sm8tat2saIPInterfacesEntry 6 }

sm8tat2saIPInterfacesIPv4Mask OBJECT-TYPE
   SYNTAX Integer32 (1..32)
   MAX-ACCESS read-create
   STATUS current
   DESCRIPTION
       "IPv4 mask for interface.
        Please add IPInterfacesVLAN first if you want to set IPInterfacesIPv4Mask to an empty entry in table.
        Please set IPInterfacesIPv4Address first and then set IPInterfacesIPv4Mask."
   ::= { sm8tat2saIPInterfacesEntry 7 }

sm8tat2saIPInterfacesIPv6Address OBJECT-TYPE
   SYNTAX DisplayString (SIZE (0..30))
   MAX-ACCESS read-create
   STATUS current
   DESCRIPTION
       "IPv6 address for interface.
        Please add IPInterfacesVLAN first if you want to set IPInterfacesIPv6Address to an empty entry in table.
        If you set IPInterfacesIPv6Address, please also set IPInterfacesIPv6Mask.
        If you set IPInterfacesIPv6Address and not set IPInterfacesIPv6Mask before, it will be set to value default 64."
   ::= { sm8tat2saIPInterfacesEntry 8 }

sm8tat2saIPInterfacesIPv6Mask OBJECT-TYPE
   SYNTAX Integer32 (1..128)
   MAX-ACCESS read-create
   STATUS current
   DESCRIPTION
       "IPv6 mask for interface.
        Please add IPInterfacesVLAN first if you want to set IPInterfacesIPv6Mask to an empty entry in table.
        Please set IPInterfacesIPv6Address first and then set IPInterfacesIPv6Mask."
   ::= { sm8tat2saIPInterfacesEntry 9 }

sm8tat2saIPInterfacesRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm8tat2saIPInterfacesEntry 10 }

sm8tat2saIPRoutesTable OBJECT-TYPE
   SYNTAX SEQUENCE OF SM8TAT2SAIPRoutesEntry
   MAX-ACCESS not-accessible
   STATUS current
   DESCRIPTION
       "IP routes table for switch."
   ::= { sm8tat2saIPConfiguration 5 }

sm8tat2saIPRoutesEntry OBJECT-TYPE
   SYNTAX SM8TAT2SAIPRoutesEntry
   MAX-ACCESS not-accessible
   STATUS current
   DESCRIPTION
       "Entry in the sm8tat2saIPRoutesTable."
   INDEX { sm8tat2saIPRoutesIndex }
   ::= { sm8tat2saIPRoutesTable 1 }

SM8TAT2SAIPRoutesEntry ::=
    SEQUENCE {
        sm8tat2saIPRoutesIndex Integer32,
        sm8tat2saIPRoutesNetwork DisplayString,
        sm8tat2saIPRoutesMaskLength Integer32,
        sm8tat2saIPRoutesGateway DisplayString,
        sm8tat2saIPRoutesNextHopVLAN Integer32,
        sm8tat2saIPRoutesRowStatus RowStatus
    }

sm8tat2saIPRoutesIndex OBJECT-TYPE
   SYNTAX Integer32 (1..32)
   MAX-ACCESS not-accessible
   STATUS current
   DESCRIPTION
       "routes table index"
   ::= { sm8tat2saIPRoutesEntry 1 }

sm8tat2saIPRoutesNetwork OBJECT-TYPE
   SYNTAX DisplayString
   MAX-ACCESS read-create
   STATUS current
   DESCRIPTION
       "IPv4/IPv6 Network address.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry.
        If Set IPRoutesNetwork, please also set IPRoutesMaskLength, IPRoutesGateway, IPRoutesNextHopVLAN."
   ::= { sm8tat2saIPRoutesEntry 2 }

sm8tat2saIPRoutesMaskLength OBJECT-TYPE
   SYNTAX Integer32 (1..32)
   MAX-ACCESS read-create
   STATUS current
   DESCRIPTION
       "IPv4/IPv6 mask length.
        Please set IPRoutesNetwork first.
        Note: All entries in routes table will be sort by 1.network address 2.mask length 3. gateway 4. next hop VLAN, if you add/modify an entry, all entries will be reordered. Please check all entries in table to find your modified entry after set/add an entry."
   ::= { sm8tat2saIPRoutesEntry 3 }

sm8tat2saIPRoutesGateway OBJECT-TYPE
   SYNTAX DisplayString
   MAX-ACCESS read-create
   STATUS current
   DESCRIPTION
       "IPv4/IPv6 Gateway.
        Please set IPRoutesNetwork first.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry."
   ::= { sm8tat2saIPRoutesEntry 4 }

sm8tat2saIPRoutesNextHopVLAN OBJECT-TYPE
   SYNTAX Integer32 (1..4095)
   MAX-ACCESS read-create
   STATUS current
   DESCRIPTION
       "Next Hop VLAN ID, range: 1-4095.
        Please set IPRoutesNetwork first.
        This entry only work when 1.network address is IPv6, 2.Gateway is link-local, 3.Interface of specific VLAN ID is IPv6.
        Note: All entries in routes table will be sort by 1.network address 2.mask length 3. gateway 4. next hop VLAN, if you add/modify an entry, all entries will be reordered. Please check all entries in table to find your modified entry after set/add an entry."
   ::= { sm8tat2saIPRoutesEntry 5 }

sm8tat2saIPRoutesRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm8tat2saIPRoutesEntry 6 }

sm8tat2saIPStatusInterfaceTable OBJECT-TYPE
   SYNTAX SEQUENCE OF SM8TAT2SAIPStatusInterfaceEntry
   MAX-ACCESS not-accessible
   STATUS current
   DESCRIPTION
       "The system IP Status table to show all IP interfaces."
   ::= { sm8tat2saIPConfiguration 6 }

sm8tat2saIPStatusInterfaceEntry OBJECT-TYPE
   SYNTAX SM8TAT2SAIPStatusInterfaceEntry
   MAX-ACCESS not-accessible
   STATUS current
   DESCRIPTION
       "An entry in the IP Status Table."
       INDEX { sm8tat2saIPStatusInterfaceIndex }
   ::= { sm8tat2saIPStatusInterfaceTable 1 }

SM8TAT2SAIPStatusInterfaceEntry ::=
   SEQUENCE {
       sm8tat2saIPStatusInterfaceIndex Integer32,
       sm8tat2saIPStatusInterfaceName DisplayString,
       sm8tat2saIPStatusInterfaceType DisplayString,
       sm8tat2saIPStatusInterfaceAddress DisplayString,
       sm8tat2saIPStatusInterfaceStatus DisplayString
   }

sm8tat2saIPStatusInterfaceIndex OBJECT-TYPE
   SYNTAX Integer32(1..1024)
   MAX-ACCESS not-accessible
   STATUS current
   DESCRIPTION
       "The entry of table to show all IP interfaces."
   ::= { sm8tat2saIPStatusInterfaceEntry 1 }

sm8tat2saIPStatusInterfaceName OBJECT-TYPE
   SYNTAX DisplayString
   MAX-ACCESS read-only
   STATUS current
   DESCRIPTION
       "The name of the interface."
   ::= { sm8tat2saIPStatusInterfaceEntry 2 }

sm8tat2saIPStatusInterfaceType OBJECT-TYPE
   SYNTAX DisplayString
   MAX-ACCESS read-only
   STATUS current
   DESCRIPTION
       "The address type of the entry. This may be LINK or IPv4."
   ::= { sm8tat2saIPStatusInterfaceEntry 3 }

sm8tat2saIPStatusInterfaceAddress OBJECT-TYPE
   SYNTAX DisplayString
   MAX-ACCESS read-only
   STATUS current
   DESCRIPTION
       "The current address of the interface (of the given type)."
   ::= { sm8tat2saIPStatusInterfaceEntry 4 }

sm8tat2saIPStatusInterfaceStatus OBJECT-TYPE
   SYNTAX DisplayString
   MAX-ACCESS read-only
   STATUS current
   DESCRIPTION
       "The status flags of the interface (and/or address)."
   ::= { sm8tat2saIPStatusInterfaceEntry 5 }

sm8tat2saIPStatusRouteTable OBJECT-TYPE
   SYNTAX SEQUENCE OF SM8TAT2SAIPStatusRouteEntry
   MAX-ACCESS not-accessible
   STATUS current
   DESCRIPTION
      "The IP Status Route table show all routing entries."
   ::= { sm8tat2saIPConfiguration 7 }

sm8tat2saIPStatusRouteEntry OBJECT-TYPE
   SYNTAX SM8TAT2SAIPStatusRouteEntry
   MAX-ACCESS not-accessible
   STATUS current
   DESCRIPTION
       "an entry in the IP Status route table."
       INDEX { sm8tat2saIPStatusRouteIndex }
   ::= { sm8tat2saIPStatusRouteTable 1 }

SM8TAT2SAIPStatusRouteEntry ::=
   SEQUENCE {
       sm8tat2saIPStatusRouteIndex Integer32,
       sm8tat2saIPStatusRouteNetwork DisplayString,
       sm8tat2saIPStatusRouteGateway DisplayString,
       sm8tat2saIPStatusRouteStatus DisplayString,
       sm8tat2saIPStatusRouteInterface DisplayString
   }

sm8tat2saIPStatusRouteIndex OBJECT-TYPE
   SYNTAX Integer32(1..2048)
   MAX-ACCESS not-accessible
   STATUS current
   DESCRIPTION
       "The entry of table to show all routing entries."
   ::= { sm8tat2saIPStatusRouteEntry 1 }

sm8tat2saIPStatusRouteNetwork OBJECT-TYPE
   SYNTAX DisplayString
   MAX-ACCESS read-only
   STATUS current
   DESCRIPTION
       "The destination IP network or host address of this route."
   ::= { sm8tat2saIPStatusRouteEntry 2 }

sm8tat2saIPStatusRouteGateway OBJECT-TYPE
   SYNTAX DisplayString
   MAX-ACCESS read-only
   STATUS current
   DESCRIPTION
       "The gateway address of this route."
   ::= { sm8tat2saIPStatusRouteEntry 3 }

sm8tat2saIPStatusRouteStatus OBJECT-TYPE
   SYNTAX DisplayString
   MAX-ACCESS read-only
   STATUS current
   DESCRIPTION
       "The route address."
   ::= { sm8tat2saIPStatusRouteEntry 4 }

sm8tat2saIPStatusRouteInterface OBJECT-TYPE
   SYNTAX DisplayString
   MAX-ACCESS read-only
   STATUS current
   DESCRIPTION
       "The route interface."
   ::= { sm8tat2saIPStatusRouteEntry 5 }

sm8tat2saIPStatusNeighborCacheTable OBJECT-TYPE
   SYNTAX SEQUENCE OF SM8TAT2SAIPStatusNeighborCacheEntry
   MAX-ACCESS not-accessible
   STATUS current
   DESCRIPTION
       "The Ip Status Neighbor Cache Table."
   ::= { sm8tat2saIPConfiguration 8 }

sm8tat2saIPStatusNeighborCacheEntry OBJECT-TYPE
   SYNTAX SM8TAT2SAIPStatusNeighborCacheEntry
   MAX-ACCESS not-accessible
   STATUS current
   DESCRIPTION
       "An entry in the Ip Status Neighbor Cache Table."
       INDEX { sm8tat2saIPStatusNeighborCacheIndex }
   ::= { sm8tat2saIPStatusNeighborCacheTable 1 }

SM8TAT2SAIPStatusNeighborCacheEntry ::=
   SEQUENCE {
       sm8tat2saIPStatusNeighborCacheIndex Integer32,
       sm8tat2saIPStatusNeighborCacheIPAddress DisplayString,
       sm8tat2saIPStatusNeighborCacheLinkAddress DisplayString
   }

sm8tat2saIPStatusNeighborCacheIndex OBJECT-TYPE
   SYNTAX Integer32(1..1024)
   MAX-ACCESS not-accessible
   STATUS current
   DESCRIPTION
       "The index for the Ip Status Neighbor Cache Table."
   ::= { sm8tat2saIPStatusNeighborCacheEntry 1 }

sm8tat2saIPStatusNeighborCacheIPAddress OBJECT-TYPE
   SYNTAX DisplayString
   MAX-ACCESS read-only
   STATUS current
   DESCRIPTION
       "The IP address of the entry."
   ::= { sm8tat2saIPStatusNeighborCacheEntry 2 }

sm8tat2saIPStatusNeighborCacheLinkAddress OBJECT-TYPE
   SYNTAX DisplayString
   MAX-ACCESS read-only
   STATUS current
   DESCRIPTION
       "The Link (MAC) address for which a binding to the IP address given exist."
   ::= { sm8tat2saIPStatusNeighborCacheEntry 3 }

sm8tat2saIPInterfaces OBJECT IDENTIFIER ::= { sm8tat2saIP 2 }

sm8tat2saIPInterfacesDHCPPerPort OBJECT IDENTIFIER ::= { sm8tat2saIPInterfaces 1 }

sm8tat2saIPInterfacesDHCPPerPortMode OBJECT-TYPE
   SYNTAX INTEGER { disable(0), enable(1) }
   MAX-ACCESS read-write
   STATUS current
   DESCRIPTION
       "The dhcp per-port mode for the interface.
        0: Disable,
        1: Enable,
        default: Disable. "
   ::= { sm8tat2saIPInterfacesDHCPPerPort 2 }

sm8tat2saIPInterfacesDHCPPerPortVlan OBJECT-TYPE
   SYNTAX Integer32
   MAX-ACCESS read-write
   STATUS current
   DESCRIPTION
       "The dhcp per-port vlan for the interface."
   ::= { sm8tat2saIPInterfacesDHCPPerPort 3 }

sm8tat2saIPInterfacesDHCPPerPortIPRangeLow OBJECT-TYPE
   SYNTAX DisplayString
   MAX-ACCESS read-write
   STATUS current
   DESCRIPTION
       "The dhcp per-port ip range low for the interface."
   ::= { sm8tat2saIPInterfacesDHCPPerPort 4 }

sm8tat2saIPInterfacesDHCPPerPortIPRangeHigh OBJECT-TYPE
   SYNTAX DisplayString
   MAX-ACCESS read-write
   STATUS current
   DESCRIPTION
       "The dhcp per-port ip range high for the interface."
   ::= { sm8tat2saIPInterfacesDHCPPerPort 5 }

sm8tat2saIPInterfacesDHCPPerPortRowStatus OBJECT-TYPE
   SYNTAX INTEGER { active(1),
                          notInService(2),
                          notReady(3),
                          createAndGo(4),
                          createAndWait(5),
                          destroy(6) }
   MAX-ACCESS read-write
   STATUS current
   DESCRIPTION
       "The dhcp per-port RowStatus for the interface."
   ::= { sm8tat2saIPInterfacesDHCPPerPort 10 }

-- *************************************************************
-- Objects in the sm8tat2saSyslog Group
-- *************************************************************
sm8tat2saSyslog OBJECT IDENTIFIER ::= { sm8tat2saSystem 5 }

sm8tat2saSyslogConf OBJECT IDENTIFIER ::= { sm8tat2saSyslog 1 }

sm8tat2saSystemLogServerMode OBJECT-TYPE
   SYNTAX AdminMode
   MAX-ACCESS read-write
   STATUS current
   DESCRIPTION
       "The System log server mode admin state."
   ::= { sm8tat2saSyslogConf 1 }

sm8tat2saSystemLogServerTable OBJECT-TYPE
   SYNTAX SEQUENCE OF SM8TAT2SASystemLogServerEntry
   MAX-ACCESS not-accessible
   STATUS current
   DESCRIPTION
       " "
   ::= { sm8tat2saSyslogConf 2 }

sm8tat2saSystemLogServerEntry OBJECT-TYPE
   SYNTAX SM8TAT2SASystemLogServerEntry
   MAX-ACCESS not-accessible
   STATUS current
   DESCRIPTION
       " "
   INDEX { sm8tat2saSystemLogServerIndex }
   ::= { sm8tat2saSystemLogServerTable 1 }

SM8TAT2SASystemLogServerEntry ::= SEQUENCE {
   sm8tat2saSystemLogServerIndex Integer32,
   sm8tat2saSystemLogServerAddress IpAddress
}

sm8tat2saSystemLogServerIndex OBJECT-TYPE
   SYNTAX Integer32(1..6)
   MAX-ACCESS not-accessible
   STATUS current
   DESCRIPTION
       " The index of the server entry. "
   ::= { sm8tat2saSystemLogServerEntry 1 }

sm8tat2saSystemLogServerAddress OBJECT-TYPE
   SYNTAX IpAddress
   MAX-ACCESS read-write
   STATUS current
   DESCRIPTION
       "The Host ip address of syslog server."
   ::= { sm8tat2saSystemLogServerEntry 2 }

sm8tat2saSysLogInfo OBJECT IDENTIFIER ::= { sm8tat2saSyslog 2 }

sm8tat2saSystemLogInfoClear OBJECT-TYPE
   SYNTAX ActivateCmd
   MAX-ACCESS read-write
   STATUS current
   DESCRIPTION
      "System log will be cleared."
   ::= { sm8tat2saSysLogInfo 1 }

sm8tat2saSystemLogDetailedInfoTable OBJECT-TYPE
  SYNTAX SEQUENCE OF SM8TAT2SASystemLogDetailedInfoEntry
  MAX-ACCESS not-accessible
  STATUS current
  DESCRIPTION
           "The system detailed Log Info table."
       ::= { sm8tat2saSysLogInfo 2 }

sm8tat2saSystemLogDetailedInfoEntry OBJECT-TYPE
   SYNTAX SM8TAT2SASystemLogDetailedInfoEntry
   MAX-ACCESS not-accessible
   STATUS current
   DESCRIPTION
           "An entry in the system detailed Log Info table."
   INDEX { sm8tat2saSystemLogDetailedInfoID }
   ::= { sm8tat2saSystemLogDetailedInfoTable 1 }

SM8TAT2SASystemLogDetailedInfoEntry ::= SEQUENCE {
    sm8tat2saSystemLogDetailedInfoID Integer32,
    sm8tat2saSystemLogDetailedInfoLevel SeverityLevel,
    sm8tat2saSystemLogDetailedInfoTime DisplayString,
    sm8tat2saSystemLogDetailedInfoMessage DisplayString
}

sm8tat2saSystemLogDetailedInfoID OBJECT-TYPE
   SYNTAX Integer32(1..65535)
   MAX-ACCESS not-accessible
   STATUS current
   DESCRIPTION
       "The index for the system detailed Log Info table."
   ::= { sm8tat2saSystemLogDetailedInfoEntry 1 }

sm8tat2saSystemLogDetailedInfoLevel OBJECT-TYPE
   SYNTAX SeverityLevel
   MAX-ACCESS read-only
   STATUS current
   DESCRIPTION
       "The Info Level."
   ::= { sm8tat2saSystemLogDetailedInfoEntry 2 }

sm8tat2saSystemLogDetailedInfoTime OBJECT-TYPE
   SYNTAX DisplayString(SIZE (0..20))
   MAX-ACCESS read-only
   STATUS current
   DESCRIPTION
       "The time"
   ::= { sm8tat2saSystemLogDetailedInfoEntry 3 }

sm8tat2saSystemLogDetailedInfoMessage OBJECT-TYPE
   SYNTAX DisplayString
   MAX-ACCESS read-only
   STATUS current
   DESCRIPTION
       "The message of this entry."
   ::= { sm8tat2saSystemLogDetailedInfoEntry 4 }

-- *************************************************************
-- Start sm8tat2saSnmp group
-- *************************************************************
sm8tat2saSnmp OBJECT IDENTIFIER ::= { sm8tat2saSystem 6 }

sm8tat2saSnmpGetCommunity OBJECT-TYPE
   SYNTAX DisplayString
   MAX-ACCESS read-write
   STATUS current
   DESCRIPTION
       "Get/Set the get-community of the SNMP."
   ::= { sm8tat2saSnmp 1 }

sm8tat2saSnmpSetCommunityMode OBJECT-TYPE
   SYNTAX INTEGER { disable(0), enable(1) }
   MAX-ACCESS read-write
   STATUS current
   DESCRIPTION
       "Get/Set the set-community mode of the SNMP.
        default : 1, 0: disable, 1: enable. "
   ::= { sm8tat2saSnmp 2 }

sm8tat2saSnmpSetCommunity OBJECT-TYPE
   SYNTAX DisplayString
   MAX-ACCESS read-write
   STATUS current
   DESCRIPTION
       "Get/Set the set-community of the SNMP."
   ::= { sm8tat2saSnmp 3 }

sm8tat2saSnmpVersion OBJECT-TYPE
   SYNTAX Integer32
   MAX-ACCESS read-only
   STATUS current
   DESCRIPTION
       "Get the get/set-community version of the SNMP."
   ::= { sm8tat2saSnmp 6 }

sm8tat2saSnmpCommunityTable OBJECT-TYPE
   SYNTAX SEQUENCE OF SM8TAT2SASnmpCommunityEntry
   MAX-ACCESS not-accessible
   STATUS current
   DESCRIPTION
       "A list of snmp community entry."
   ::= { sm8tat2saSnmp 4 }

sm8tat2saSnmpCommunityEntry OBJECT-TYPE
   SYNTAX SM8TAT2SASnmpCommunityEntry
   MAX-ACCESS not-accessible
   STATUS current
   DESCRIPTION
       "This is the entry information for snmp community."
   INDEX { sm8tat2saSnmpCommunityIndex }
   ::= { sm8tat2saSnmpCommunityTable 1 }

SM8TAT2SASnmpCommunityEntry ::= SEQUENCE {
    sm8tat2saSnmpCommunityIndex Integer32,
    sm8tat2saSnmpCommunityName DisplayString,
    sm8tat2saSnmpCommunityIP IpAddress,
    sm8tat2saSnmpCommunityMask Integer32,
    sm8tat2saSnmpCommunityRowStatus RowStatus
}

sm8tat2saSnmpCommunityIndex OBJECT-TYPE
   SYNTAX Integer32(1..6)
   MAX-ACCESS not-accessible
   STATUS current
   DESCRIPTION
       " The index of the snmp community entry. "
   ::= { sm8tat2saSnmpCommunityEntry 1 }

sm8tat2saSnmpCommunityName OBJECT-TYPE
   SYNTAX DisplayString(SIZE(1..32))
   MAX-ACCESS read-create
   STATUS current
   DESCRIPTION
       "Indicates the community access string to permit access to
       SNMPv3 agent. The community string will be treated as
       security name and map a SNMPv1 or SNMPv2c community string. "
   ::= { sm8tat2saSnmpCommunityEntry 2 }

sm8tat2saSnmpCommunityIP OBJECT-TYPE
   SYNTAX IpAddress
   MAX-ACCESS read-create
   STATUS current
   DESCRIPTION
       "Indicates the SNMP access source address. A particular
       range of source addresses can be used to restrict source
       subnet when combined with source mask."
   ::= { sm8tat2saSnmpCommunityEntry 3 }

sm8tat2saSnmpCommunityMask OBJECT-TYPE
   SYNTAX Integer32
   MAX-ACCESS read-create
   STATUS current
   DESCRIPTION
       "Indicates the SNMP access source address mask."
   ::= { sm8tat2saSnmpCommunityEntry 4 }

sm8tat2saSnmpCommunityRowStatus OBJECT-TYPE
   SYNTAX RowStatus
   MAX-ACCESS read-create
   STATUS current
   DESCRIPTION
       "This object indicates the status of this entry, and is
       used to create/delete entries. Any object in an entry of
       this table may be modified while the value of the
       corresponding instance of this object is active(1).
       notReady(3) and createAndGo(4) not supported."
   ::= { sm8tat2saSnmpCommunityEntry 5 }

sm8tat2saTrapHostConfTable OBJECT-TYPE
   SYNTAX SEQUENCE OF SM8TAT2SATrapHostConfEntry
   MAX-ACCESS not-accessible
   STATUS current
   DESCRIPTION
       "A list of trap host entry."
   ::= { sm8tat2saSnmp 5 }

sm8tat2saTrapHostConfEntry OBJECT-TYPE
   SYNTAX SM8TAT2SATrapHostConfEntry
   MAX-ACCESS not-accessible
   STATUS current
   DESCRIPTION
       "This is the entry information for trap host."
   INDEX { sm8tat2saTrapHostConfIndex }
   ::= { sm8tat2saTrapHostConfTable 1 }

SM8TAT2SATrapHostConfEntry ::= SEQUENCE {
    sm8tat2saTrapHostConfIndex Integer32,
    sm8tat2saTrapHostConfVersion DisplayString,
    sm8tat2saTrapHostConfMode INTEGER,
    sm8tat2saTrapHostConfIP DisplayString,
    sm8tat2saTrapHostConfPort Integer32,
    sm8tat2saTrapHostConfCommunity DisplayString,
    sm8tat2saTrapHostConfSeverityLevel SeverityLevel,
    sm8tat2saTrapHostConfCurrentMode INTEGER
}

sm8tat2saTrapHostConfIndex OBJECT-TYPE
   SYNTAX Integer32(1..6)
   MAX-ACCESS not-accessible
   STATUS current
   DESCRIPTION
       " The index of the trap host entry. "
   ::= { sm8tat2saTrapHostConfEntry 1 }

sm8tat2saTrapHostConfVersion OBJECT-TYPE
   SYNTAX DisplayString
   MAX-ACCESS read-only
   STATUS current
   DESCRIPTION
       "The version of the Trap PDU."
   ::= { sm8tat2saTrapHostConfEntry 2 }

sm8tat2saTrapHostConfMode OBJECT-TYPE
   SYNTAX INTEGER { disabled(0), udp(1), tcp(2) }
   MAX-ACCESS read-write
   STATUS current
   DESCRIPTION
       "ndicates the trap destination mode operation.
        0:disabled, 1:udp, 2:tcp."
   ::= { sm8tat2saTrapHostConfEntry 3 }

sm8tat2saTrapHostConfIP OBJECT-TYPE
   SYNTAX DisplayString
   MAX-ACCESS read-write
   STATUS current
   DESCRIPTION
       "This is the IP of the trap host."
   ::= { sm8tat2saTrapHostConfEntry 4 }

sm8tat2saTrapHostConfPort OBJECT-TYPE
   SYNTAX Integer32(1..65535)
   MAX-ACCESS read-write
   STATUS current
   DESCRIPTION
       "Indicates the SNMP trap destination port.
        SNMP Agent will send SNMP message via this port,
        the port range is 1~65535. "
   ::= { sm8tat2saTrapHostConfEntry 5 }

sm8tat2saTrapHostConfCommunity OBJECT-TYPE
   SYNTAX DisplayString (SIZE (1..32))
   MAX-ACCESS read-write
   STATUS current
   DESCRIPTION
       "The community name for the trap PDU."
   ::= { sm8tat2saTrapHostConfEntry 6 }

sm8tat2saTrapHostConfSeverityLevel OBJECT-TYPE
   SYNTAX SeverityLevel
   MAX-ACCESS read-write
   STATUS current
   DESCRIPTION
       "The Severity Level."
    ::= { sm8tat2saTrapHostConfEntry 7 }

sm8tat2saTrapHostConfCurrentMode OBJECT-TYPE
   SYNTAX INTEGER { empty(0), active(1), edit(2), delete(3) }
   MAX-ACCESS read-write
   STATUS current
   DESCRIPTION
       "0:Empty, 1:Active mode, 2:Edit mode, 3:Delete."
   ::= { sm8tat2saTrapHostConfEntry 13 }

-- *************************************************************
-- Start sm8tat2saPrivilegeLevel group
-- *************************************************************
sm8tat2saPrivilegeLevel OBJECT IDENTIFIER ::= { sm8tat2saSystem 7 }

sm8tat2saPrivilegeLevelConfigTable OBJECT-TYPE
   SYNTAX SEQUENCE OF SM8TAT2SAPrivilegeLevelConfigEntry
   MAX-ACCESS not-accessible
   STATUS current
   DESCRIPTION
       "The Privilege Level Config Table. "
   ::= { sm8tat2saPrivilegeLevel 1 }

sm8tat2saPrivilegeLevelConfigEntry OBJECT-TYPE
   SYNTAX SM8TAT2SAPrivilegeLevelConfigEntry
   MAX-ACCESS not-accessible
   STATUS current
   DESCRIPTION
       "The Privilege Level Config Entry."
   INDEX { sm8tat2saPrivilegeLevelIndex }
   ::= { sm8tat2saPrivilegeLevelConfigTable 1 }

SM8TAT2SAPrivilegeLevelConfigEntry ::=
SEQUENCE {
   sm8tat2saPrivilegeLevelIndex Integer32,
   sm8tat2saPrivilegeLevelGroupName DisplayString,
   sm8tat2saPrivilegeLevelConfigReadOnly Integer32,
   sm8tat2saPrivilegeLevelConfigReadWrite Integer32
}

sm8tat2saPrivilegeLevelIndex OBJECT-TYPE
   SYNTAX Integer32 (1..34)
   MAX-ACCESS not-accessible
   STATUS current
   DESCRIPTION
       "The Privilege Level Index. "
   ::= { sm8tat2saPrivilegeLevelConfigEntry 1 }

sm8tat2saPrivilegeLevelGroupName OBJECT-TYPE
   SYNTAX DisplayString
   MAX-ACCESS read-write
   STATUS current
   DESCRIPTION
       "The name identifying the privilege group."
   ::= { sm8tat2saPrivilegeLevelConfigEntry 2 }

sm8tat2saPrivilegeLevelConfigReadOnly OBJECT-TYPE
   SYNTAX Integer32 (0..15)
   MAX-ACCESS read-write
   STATUS current
   DESCRIPTION
       "The privilege level of configuration read-only.If the privilege level value is 15,it can access all groups.
        range: 0-15. "
   ::= { sm8tat2saPrivilegeLevelConfigEntry 3 }

sm8tat2saPrivilegeLevelConfigReadWrite OBJECT-TYPE
   SYNTAX Integer32 (0..15)
   MAX-ACCESS read-write
   STATUS current
   DESCRIPTION
       "The privilege level of configuration/execute read/write. If the privilege level value is 15,it can access all groups.
        range: 0-15. "
   ::= { sm8tat2saPrivilegeLevelConfigEntry 4 }

-- *************************************************************
-- Start sm8tat2saLldpConfig group
-- *************************************************************
sm8tat2saLldpConfig OBJECT IDENTIFIER ::= { sm8tat2saSystem 8 }

sm8tat2saLldpConfigTable OBJECT-TYPE
    SYNTAX SEQUENCE OF SM8TAT2SALldpConfigEntry
    MAX-ACCESS not-accessible
    STATUS current
    DESCRIPTION
        "This is a table to configure LLDP configurations for a specific
         interface."
    ::= { sm8tat2saLldpConfig 1 }

sm8tat2saLldpConfigEntry OBJECT-TYPE
    SYNTAX SM8TAT2SALldpConfigEntry
    MAX-ACCESS not-accessible
    STATUS current
    DESCRIPTION
        "Each interface has a set of control parameters"
    INDEX { sm8tat2saLldpConfigIfIndex }
    ::= { sm8tat2saLldpConfigTable 1 }

SM8TAT2SALldpConfigEntry ::= SEQUENCE {
    sm8tat2saLldpConfigIfIndex Integer32,
    sm8tat2saLldpConfigCdpAware INTEGER
}

sm8tat2saLldpConfigIfIndex OBJECT-TYPE
    SYNTAX Integer32 (1..4095)
    MAX-ACCESS not-accessible
    STATUS current
    DESCRIPTION
        "Logical interface number index."
    ::= { sm8tat2saLldpConfigEntry 1 }

sm8tat2saLldpConfigCdpAware OBJECT-TYPE
    SYNTAX INTEGER { disable(0), enable(1) }
    MAX-ACCESS read-write
    STATUS current
    DESCRIPTION
        "Enables/disables CDP awareness for the interface.

         CDP is Cisco's equivalent to LLDP.

         The CDP operation is restricted to decoding incoming CDP frames (The
         switch doesn't transmit CDP frames). CDP frames are only decoded if
         LLDP on the port is enabled.

         Only CDP TLVs that can be mapped to a corresponding field in the LLDP
         neighbors' table are decoded. All other TLVs are discarded
         (Unrecognized CDP TLVs and discarded CDP frames are not shown in the
         LLDP statistics.).

         CDP TLVs are mapped onto LLDP neighbors' table as shown below.

         CDP TLV 'Device ID' is mapped to the LLDP 'Chassis ID' field.

         CDP TLV 'Address' is mapped to the LLDP 'Management Address' field. The
         CDP address TLV can contain multiple addresses, but only the first
         address is shown in the LLDP neighbors table.

         CDP TLV 'Port ID' is mapped to the LLDP 'Port ID' field.

         CDP TLV 'Version and Platform' is mapped to the LLDP 'System
         Description' field.

         Both the CDP and LLDP support 'system capabilities', but the CDP
         capabilities cover capabilities that are not part of the LLDP. These
         capabilities are shown as 'others' in the LLDP neighbors' table.

         If all ports have CDP awareness disabled the switch forwards CDP frames
         received from neighbor devices. If at least one port has CDP awareness
         enabled all CDP frames are terminated by the switch.

         Note: When CDP awareness on a port is disabled the CDP information
         isn't removed immediately, but gets removed when the hold time is
         exceeded."
    ::= { sm8tat2saLldpConfigEntry 2 }

sm8tat2saLldpMedLocInfo OBJECT IDENTIFIER ::= { sm8tat2saLldpConfig 2 }

sm8tat2saLldpMedLatitude OBJECT-TYPE
    SYNTAX Integer32
    MAX-ACCESS read-write
    STATUS current
    DESCRIPTION
        "Latitude degrees"
    ::= { sm8tat2saLldpMedLocInfo 1 }

sm8tat2saLldpMedLatitudeDirection OBJECT-TYPE
    SYNTAX INTEGER { north(0), south(1) }
    MAX-ACCESS read-write
    STATUS current
    DESCRIPTION
        "Latitude degrees direction"
    ::= { sm8tat2saLldpMedLocInfo 2 }

sm8tat2saLldpMedLongitude OBJECT-TYPE
    SYNTAX Integer32
    MAX-ACCESS read-write
    STATUS current
    DESCRIPTION
        "Longitude degrees"
    ::= { sm8tat2saLldpMedLocInfo 3 }

sm8tat2saLldpMedLongitudeDirection OBJECT-TYPE
    SYNTAX INTEGER { east(0), west(1) }
    MAX-ACCESS read-write
    STATUS current
    DESCRIPTION
        "Longitude degrees"
    ::= { sm8tat2saLldpMedLocInfo 4 }

sm8tat2saLldpMedAltitude OBJECT-TYPE
    SYNTAX Integer32
    MAX-ACCESS read-write
    STATUS current
    DESCRIPTION
        "Altitude value"
    ::= { sm8tat2saLldpMedLocInfo 5 }

sm8tat2saLldpMedAltitudeType OBJECT-TYPE
    SYNTAX LldpmedAltitudeType
    MAX-ACCESS read-write
    STATUS current
    DESCRIPTION
        "Setting altitude type

         Possible to select between two altitude types (floors or meters).
         Meters are representing meters of altitude defined by the vertical
         datum specified. Floors are representing altitude in a form more
         relevant in buildings which have different floor-to-floor dimensions.
         An altitude = 0.0 is meaningful even outside a building, and represents
         ground level at the given latitude and longitude. Inside a building,
         0.0 represents the floor level associated with ground level at the main
         entrance."
    ::= { sm8tat2saLldpMedLocInfo 6 }

sm8tat2saLldpMedDatum OBJECT-TYPE
    SYNTAX LldpmedDatumType
    MAX-ACCESS read-write
    STATUS current
    DESCRIPTION
        "Setting datum to configure the datum (geodetic system) to use.

         The Map Datum is used for the coordinates given in these options:

         WGS84: (Geographical 3D) - World Geodesic System 1984, CRS Code 4327,
         Prime Meridian Name: Greenwich.

         NAD83/NAVD88: North American Datum 1983, CRS Code 4269, Prime Meridian
         Name: Greenwich;The associated vertical datum is the North American
         Vertical Datum of 1988 (NAVD88).This datum pair is to be used when
         referencing locations on land, not near tidal water(which would use
         Datum = NAD83/MLLW).

         NAD83/MLLW: North American Datum 1983, CRS Code 4269, Prime Meridian
         Name: Greenwich; The associated vertical datum is Mean Lower Low Water
         (MLLW). This datum pair is to be used when referencing locations on
         water/sea/ocean."
    ::= { sm8tat2saLldpMedLocInfo 7 }

sm8tat2saLldpMedElinAddr OBJECT-TYPE
    SYNTAX DisplayString (SIZE(0..25))
    MAX-ACCESS read-write
    STATUS current
    DESCRIPTION
        "Emergency Call Service ELIN identifier data format is defined to carry
         the ELIN identifier as used during emergency call setup to a
         traditional CAMA or ISDN trunk-based PSAP. This format consists of a
         numerical digit string, corresponding to the ELIN to be used for
         emergency calling. Maximum number of octets are 25."
    ::= { sm8tat2saLldpMedLocInfo 8 }

sm8tat2saLldpMedCivicAddrLocInfoCountryCode OBJECT-TYPE
    SYNTAX DisplayString (SIZE(0..2))
    MAX-ACCESS read-write
    STATUS current
    DESCRIPTION
        "The two-letter ISO 3166 country code in capital ASCII letters -
         Example: DK, DE or US."
    ::= { sm8tat2saLldpMedLocInfo 9 }

sm8tat2saLldpMedCivicAddrLocInfoState OBJECT-TYPE
    SYNTAX DisplayString (SIZE(0..50))
    MAX-ACCESS read-write
    STATUS current
    DESCRIPTION
        "National subdivision"
    ::= { sm8tat2saLldpMedLocInfo 10 }

sm8tat2saLldpMedCivicAddrLocInfoCounty OBJECT-TYPE
    SYNTAX DisplayString (SIZE(0..50))
    MAX-ACCESS read-write
    STATUS current
    DESCRIPTION
        "County"
    ::= { sm8tat2saLldpMedLocInfo 11 }

sm8tat2saLldpMedCivicAddrLocInfoCity OBJECT-TYPE
    SYNTAX DisplayString (SIZE(0..50))
    MAX-ACCESS read-write
    STATUS current
    DESCRIPTION
        "City"
    ::= { sm8tat2saLldpMedLocInfo 12 }

sm8tat2saLldpMedCivicAddrLocInfoDistrict OBJECT-TYPE
    SYNTAX DisplayString (SIZE(0..50))
    MAX-ACCESS read-write
    STATUS current
    DESCRIPTION
        "City district"
    ::= { sm8tat2saLldpMedLocInfo 13 }

sm8tat2saLldpMedCivicAddrLocInfoBlock OBJECT-TYPE
    SYNTAX DisplayString (SIZE(0..50))
    MAX-ACCESS read-write
    STATUS current
    DESCRIPTION
        "Block (Neighborhood)"
    ::= { sm8tat2saLldpMedLocInfo 14 }

sm8tat2saLldpMedCivicAddrLocInfoStreet OBJECT-TYPE
    SYNTAX DisplayString (SIZE(0..50))
    MAX-ACCESS read-write
    STATUS current
    DESCRIPTION
        "Street"
    ::= { sm8tat2saLldpMedLocInfo 15 }

sm8tat2saLldpMedCivicAddrLocInfoLeadingStreetDirection OBJECT-TYPE
    SYNTAX DisplayString (SIZE(0..50))
    MAX-ACCESS read-write
    STATUS current
    DESCRIPTION
        "Street Direction"
    ::= { sm8tat2saLldpMedLocInfo 16 }

sm8tat2saLldpMedCivicAddrLocInfoTrailingStreetSuffix OBJECT-TYPE
    SYNTAX DisplayString (SIZE(0..50))
    MAX-ACCESS read-write
    STATUS current
    DESCRIPTION
        "Trailing Street Suffix"
    ::= { sm8tat2saLldpMedLocInfo 17 }

sm8tat2saLldpMedCivicAddrLocInfoStreetSuffix OBJECT-TYPE
    SYNTAX DisplayString (SIZE(0..50))
    MAX-ACCESS read-write
    STATUS current
    DESCRIPTION
        "Street Suffix"
    ::= { sm8tat2saLldpMedLocInfo 18 }

sm8tat2saLldpMedCivicAddrLocInfoHouseNo OBJECT-TYPE
    SYNTAX DisplayString (SIZE(0..50))
    MAX-ACCESS read-write
    STATUS current
    DESCRIPTION
        "House No."
    ::= { sm8tat2saLldpMedLocInfo 19 }

sm8tat2saLldpMedCivicAddrLocInfoHouseNoSuffix OBJECT-TYPE
    SYNTAX DisplayString (SIZE(0..50))
    MAX-ACCESS read-write
    STATUS current
    DESCRIPTION
        "House No. Suffix"
    ::= { sm8tat2saLldpMedLocInfo 20 }

sm8tat2saLldpMedCivicAddrLocInfoLandmark OBJECT-TYPE
    SYNTAX DisplayString (SIZE(0..50))
    MAX-ACCESS read-write
    STATUS current
    DESCRIPTION
        "Landmark"
    ::= { sm8tat2saLldpMedLocInfo 21 }

sm8tat2saLldpMedCivicAddrLocInfoAdditionalInfo OBJECT-TYPE
    SYNTAX DisplayString (SIZE(0..50))
    MAX-ACCESS read-write
    STATUS current
    DESCRIPTION
        "Additional Location Info"
    ::= { sm8tat2saLldpMedLocInfo 22 }

sm8tat2saLldpMedCivicAddrLocInfoName OBJECT-TYPE
    SYNTAX DisplayString (SIZE(0..50))
    MAX-ACCESS read-write
    STATUS current
    DESCRIPTION
        "Name"
    ::= { sm8tat2saLldpMedLocInfo 23 }

sm8tat2saLldpMedCivicAddrLocInfoZipCode OBJECT-TYPE
    SYNTAX DisplayString (SIZE(0..50))
    MAX-ACCESS read-write
    STATUS current
    DESCRIPTION
        "Zip code"
    ::= { sm8tat2saLldpMedLocInfo 24 }

sm8tat2saLldpMedCivicAddrLocInfoBuilding OBJECT-TYPE
    SYNTAX DisplayString (SIZE(0..50))
    MAX-ACCESS read-write
    STATUS current
    DESCRIPTION
        "Building"
    ::= { sm8tat2saLldpMedLocInfo 25 }

sm8tat2saLldpMedCivicAddrLocInfoApartment OBJECT-TYPE
    SYNTAX DisplayString (SIZE(0..50))
    MAX-ACCESS read-write
    STATUS current
    DESCRIPTION
        "Apartment/unit"
    ::= { sm8tat2saLldpMedLocInfo 26 }

sm8tat2saLldpMedCivicAddrLocInfoFloor OBJECT-TYPE
    SYNTAX DisplayString (SIZE(0..50))
    MAX-ACCESS read-write
    STATUS current
    DESCRIPTION
        "Floor"
    ::= { sm8tat2saLldpMedLocInfo 27 }

sm8tat2saLldpMedCivicAddrLocInfoRoomNumber OBJECT-TYPE
    SYNTAX DisplayString (SIZE(0..50))
    MAX-ACCESS read-write
    STATUS current
    DESCRIPTION
        "Room Number"
    ::= { sm8tat2saLldpMedLocInfo 28 }

sm8tat2saLldpMedCivicAddrLocInfoPlaceType OBJECT-TYPE
    SYNTAX DisplayString (SIZE(0..50))
    MAX-ACCESS read-write
    STATUS current
    DESCRIPTION
        "Place type"
    ::= { sm8tat2saLldpMedLocInfo 29 }

sm8tat2saLldpMedCivicAddrLocInfoPostalCommunityName OBJECT-TYPE
    SYNTAX DisplayString (SIZE(0..50))
    MAX-ACCESS read-write
    STATUS current
    DESCRIPTION
        "Postal Community Name"
    ::= { sm8tat2saLldpMedLocInfo 30 }

sm8tat2saLldpMedCivicAddrLocInfoPoBox OBJECT-TYPE
    SYNTAX DisplayString (SIZE(0..50))
    MAX-ACCESS read-write
    STATUS current
    DESCRIPTION
        "Post Office Box"
    ::= { sm8tat2saLldpMedLocInfo 31 }

sm8tat2saLldpMedCivicAddrLocInfoAdditionalCode OBJECT-TYPE
    SYNTAX DisplayString (SIZE(0..50))
    MAX-ACCESS read-write
    STATUS current
    DESCRIPTION
        "Addination Code"
    ::= { sm8tat2saLldpMedLocInfo 32 }

-- ************************************************************
-- Start sm8tat2saVLANConf group
-- *************************************************************
sm8tat2saVLANConf OBJECT IDENTIFIER ::= { sm8tat2saSystem 10 }

sm8tat2saVLAN OBJECT IDENTIFIER ::= { sm8tat2saVLANConf 2}

sm8tat2saVlanExistingVLANs OBJECT-TYPE
   SYNTAX DisplayString
   MAX-ACCESS read-write
   STATUS current
   DESCRIPTION
       "This field shows the VLANs that are created on the switch.
        More VLANs may be created by using a
        list syntax where the individual elements are separated by commas.
        Ranges are specified with a
        dash separating the lower and upper bound.
        The following example will create VLANs 1, 10, 11, 12
        , 13, 200, and 300: 1,10-13,200,300.
        default: 1."
   ::= { sm8tat2saVLAN 1 }

sm8tat2saVlanEthertypeforCustomSPorts OBJECT-TYPE
   SYNTAX DisplayString
   MAX-ACCESS read-write
   STATUS current
   DESCRIPTION
       "This field specifies the ethertype/TPID (specified in hexadecimal)
        used for Custom S-ports. The
        setting is in force for all ports whose Port Type
        is set to S-Custom-Port.
        range: 0600-ffff,
        default: 88a8."
   ::= { sm8tat2saVLAN 2 }

sm8tat2saVlanTable OBJECT-TYPE
   SYNTAX SEQUENCE OF SM8TAT2SAVlanEntry
   MAX-ACCESS not-accessible
   STATUS current
   DESCRIPTION
       "Configure Vlan ports Configuration mode.
        INDEX for this table is ifIndex which is
        equivalent to the panel port number."
   ::= { sm8tat2saVLAN 3 }

sm8tat2saVlanEntry OBJECT-TYPE
   SYNTAX SM8TAT2SAVlanEntry
   MAX-ACCESS not-accessible
   STATUS current
   DESCRIPTION
       "The Vlan entry."
   INDEX { ifIndex }
   ::= { sm8tat2saVlanTable 1 }

SM8TAT2SAVlanEntry ::= SEQUENCE {
    sm8tat2saVlanMode INTEGER,
    sm8tat2saVlanPortVLAN Integer32,
    sm8tat2saVlanPortType INTEGER,
    sm8tat2saVlanIngressFiltering AdminMode,
-- sm8tat2saVlanVLANTrunking AdminMode,
    sm8tat2saVlanIngressAcceptance INTEGER,
    sm8tat2saVlanEgressTagging INTEGER,
    sm8tat2saVlanAllowedVLANs DisplayString
-- sm8tat2saVlanForbiddenVLANs DisplayString
    }

sm8tat2saVlanMode OBJECT-TYPE
   SYNTAX INTEGER{access(0), trunk(1), hybrid(2)}
   MAX-ACCESS read-write
   STATUS current
   DESCRIPTION
       "The port mode determines the fundamental
        behavior of the port in question.
        A port can be in one of three modes as described below.
        0: access,
        1: trunk,
        2: hybrid."
   DEFVAL { access }
   ::= { sm8tat2saVlanEntry 2 }

sm8tat2saVlanPortVLAN OBJECT-TYPE
   SYNTAX Integer32(1..4094)
   MAX-ACCESS read-write
   STATUS current
   DESCRIPTION
       "Determines the port's VLAN ID (a.k.a. PVID).
        range: 1-4095,
        default: 1."
   ::= { sm8tat2saVlanEntry 3 }

sm8tat2saVlanPortType OBJECT-TYPE
   SYNTAX INTEGER { unaware(0), cPort(1), sPort(2), sCustomPort(3) }
   MAX-ACCESS read-write
   STATUS current
   DESCRIPTION
       "Ports in hybrid mode allow for changing the port type,
        that is, whether a frame's VLAN tag is
        used to classify the frame on ingress to a particular VLAN,
        and if so, which TPID it reacts on.
        Likewise, on egress, the Port Type determines the
        TPID of the tag, if a tag is required.
        0: unaware,
        1: c-Port,
        2: s-Port,
        3: s-Custom-Port."
    DEFVAL { cPort }
   ::= { sm8tat2saVlanEntry 4 }

sm8tat2saVlanIngressFiltering OBJECT-TYPE
   SYNTAX AdminMode
   MAX-ACCESS read-write
   STATUS current
   DESCRIPTION
       "Hybrid ports allow for changing ingress filtering.
        Access and Trunk ports always have ingress
        filtering enabled.If ingress filtering is enabled,
        frames classified to
        a VLAN that the port is not a member of get discarded."
   ::= { sm8tat2saVlanEntry 5 }

-- sm8tat2saVlanVLANTrunking OBJECT-TYPE
-- SYNTAX AdminMode
-- MAX-ACCESS read-write
-- STATUS current
-- DESCRIPTION
-- "Trunk and Hybrid ports allow for enabling VLAN trunking.
-- When VLAN trunking is enabled, frames
-- classified to unknown VLANs are accepted on the port
-- whether ingress filtering is enabled or not."
-- DEFVAL { disable }
-- ::= { sm8tat2saVlanEntry 6 }

sm8tat2saVlanIngressAcceptance OBJECT-TYPE
   SYNTAX INTEGER { taggedAndUntagged ( 0 ),
                          taggedOnly ( 1 ),
                          untaggedOnly ( 2 )
                        }
   MAX-ACCESS read-write
   STATUS current
   DESCRIPTION
       "Hybrid ports allow for changing the type of frames that are
        accepted on ingress.
        0: Tagged and Untagged,
        1: Tagged Only,
        2: Untagged Only."
   ::= { sm8tat2saVlanEntry 7 }

sm8tat2saVlanEgressTagging OBJECT-TYPE
   SYNTAX INTEGER { untagPortVlan ( 0 ),
                          tagAll ( 1 ),
                          untagAll ( 2 )
                        }
   MAX-ACCESS read-write
   STATUS current
   DESCRIPTION
       "Ports in Trunk and Hybrid mode may control the
        tagging of frames on egress.
        0: Untag Port VLAN,
        1: Tag All,
        2: Untag All."
   ::= { sm8tat2saVlanEntry 8 }

sm8tat2saVlanAllowedVLANs OBJECT-TYPE
   SYNTAX DisplayString
   MAX-ACCESS read-write
   STATUS current
   DESCRIPTION
       "Ports in Trunk and Hybrid mode may control which
        VLANs they are allowed to become members of.
        Access ports can only be member of one VLAN, the Access VLAN.
        range: 1~4095.
        '-': Allowed VLANs is empty."
   ::= { sm8tat2saVlanEntry 9 }

sm8tat2saVlanStatus OBJECT IDENTIFIER ::= { sm8tat2saVLAN 6 }

sm8tat2saVLANPortStatusTable OBJECT-TYPE
   SYNTAX SEQUENCE OF SM8TAT2SAVLANPortStatusEntry
   MAX-ACCESS not-accessible
   STATUS current
   DESCRIPTION
       "The vlan port status table.
        INDEX for this table is ifIndex which is
        equivalent to the panel port number."
   ::= { sm8tat2saVlanStatus 2 }

sm8tat2saVLANPortStatusEntry OBJECT-TYPE
   SYNTAX SM8TAT2SAVLANPortStatusEntry
   MAX-ACCESS not-accessible
   STATUS current
   DESCRIPTION
       "The vlan port status entry."
   INDEX { ifIndex }
   ::= { sm8tat2saVLANPortStatusTable 1 }

SM8TAT2SAVLANPortStatusEntry ::= SEQUENCE {
    sm8tat2saVLANPortStatusPortType DisplayString,
    sm8tat2saVLANPortStatusIngressFiltering AdminMode,
    sm8tat2saVLANPortStatusFrameType DisplayString,
    sm8tat2saVLANPortStatusPortVLANID Integer32,
    sm8tat2saVLANPortStatusTxTag DisplayString
-- sm8tat2saVLANPortStatusUntaggedVLANID Integer32,
-- sm8tat2saVLANPortStatusConflicts DisplayString
    }

sm8tat2saVLANPortStatusPortType OBJECT-TYPE
   SYNTAX DisplayString
   MAX-ACCESS read-only
   STATUS current
   DESCRIPTION
       "Shows the port type (Unaware, C-Port, S-Port,
        S-Custom-Port.) that a given user wants to configure on
        the port.The field is empty if not overridden by the selected user."
   ::= { sm8tat2saVLANPortStatusEntry 2 }

sm8tat2saVLANPortStatusIngressFiltering OBJECT-TYPE
   SYNTAX AdminMode
   MAX-ACCESS read-only
   STATUS current
   DESCRIPTION
       "Shows whether a given user wants ingress filtering enabled or not."
   ::= { sm8tat2saVLANPortStatusEntry 3 }

sm8tat2saVLANPortStatusFrameType OBJECT-TYPE
   SYNTAX DisplayString
   MAX-ACCESS read-only
   STATUS current
   DESCRIPTION
       "Shows the acceptable frame types (All, Taged,
        Untagged) that a given user wants to configure on the port.
        The field is empty if not overridden by the selected user."
   ::= { sm8tat2saVLANPortStatusEntry 4 }

sm8tat2saVLANPortStatusPortVLANID OBJECT-TYPE
   SYNTAX Integer32 (1..4095)
   MAX-ACCESS read-only
   STATUS current
   DESCRIPTION
       "Shows the Port VLAN ID (PVID) that a given user
        wants the port to have.
        The field is 0 if not overridden by the selected user."
   ::= { sm8tat2saVLANPortStatusEntry 5 }

sm8tat2saVLANPortStatusTxTag OBJECT-TYPE
   SYNTAX DisplayString
   MAX-ACCESS read-only
   STATUS current
   DESCRIPTION
       "Shows the Tx Tag requirements (Tag All, Tag PVID,
        Tag UVID, Untag All, Untag PVID, Untag UVID)
        that a given user has on a port.The field is empty
        if not overridden by the selected user."
   ::= { sm8tat2saVLANPortStatusEntry 6 }

sm8tat2saVclConfig OBJECT IDENTIFIER ::= { sm8tat2saVLANConf 3 }

sm8tat2saVclConfigMac OBJECT IDENTIFIER ::= { sm8tat2saVclConfig 1 }

sm8tat2saVclConfigMacBasedTable OBJECT-TYPE
    SYNTAX SEQUENCE OF SM8TAT2SAVclConfigMacBasedEntry
    MAX-ACCESS not-accessible
    STATUS current
    DESCRIPTION
        "This is the MAC address to VLAN ID configuration table."
    ::= { sm8tat2saVclConfigMac 1 }

sm8tat2saVclConfigMacBasedEntry OBJECT-TYPE
    SYNTAX SM8TAT2SAVclConfigMacBasedEntry
    MAX-ACCESS not-accessible
    STATUS current
    DESCRIPTION
        "Each entry in this table represents a configured MAC-based
         classification."
    INDEX { sm8tat2saVclConfigMacIndex }
    ::= { sm8tat2saVclConfigMacBasedTable 1 }

SM8TAT2SAVclConfigMacBasedEntry ::= SEQUENCE {
    sm8tat2saVclConfigMacIndex Integer32,
    sm8tat2saVclConfigMacMacAddress MacAddress,
    sm8tat2saVclConfigMacVlanId Integer32,
    sm8tat2saVclConfigMacRowStatus RowStatus
}

sm8tat2saVclConfigMacIndex OBJECT-TYPE
   SYNTAX Integer32 (1..128)
   MAX-ACCESS not-accessible
   STATUS current
   DESCRIPTION
       "The VclConfigMac Index."
   ::= { sm8tat2saVclConfigMacBasedEntry 1 }

sm8tat2saVclConfigMacMacAddress OBJECT-TYPE
    SYNTAX MacAddress
    MAX-ACCESS read-create
    STATUS current
    DESCRIPTION
        "The MAC address for which this entry is applicable."
    ::= { sm8tat2saVclConfigMacBasedEntry 2 }

sm8tat2saVclConfigMacVlanId OBJECT-TYPE
    SYNTAX Integer32 (1..4095)
    MAX-ACCESS read-create
    STATUS current
    DESCRIPTION
        "Vlan id of the mapping."
    ::= { sm8tat2saVclConfigMacBasedEntry 3 }

sm8tat2saVclConfigMacRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm8tat2saVclConfigMacBasedEntry 4 }

sm8tat2saVclConfigMacStatusTable OBJECT-TYPE
    SYNTAX SEQUENCE OF SM8TAT2SAVclConfigMacStatusEntry
    MAX-ACCESS not-accessible
    STATUS current
    DESCRIPTION
        "This is the MAC address to VLAN ID Status table."
    ::= { sm8tat2saVclConfigMac 2 }

sm8tat2saVclConfigMacStatusEntry OBJECT-TYPE
    SYNTAX SM8TAT2SAVclConfigMacStatusEntry
    MAX-ACCESS not-accessible
    STATUS current
    DESCRIPTION
        "Each entry in this table represents a MAC-based Status
         classification."
    INDEX { sm8tat2saVclMacStatusIndex }
    ::= { sm8tat2saVclConfigMacStatusTable 1 }

SM8TAT2SAVclConfigMacStatusEntry ::= SEQUENCE {
    sm8tat2saVclMacStatusIndex Integer32,
    sm8tat2saVclMacStatusMacAddress MacAddress,
    sm8tat2saVclMacStatusVlanId Integer32,
    sm8tat2saVclMacStatusUser INTEGER
}

sm8tat2saVclMacStatusIndex OBJECT-TYPE
   SYNTAX Integer32 (1..128)
   MAX-ACCESS not-accessible
   STATUS current
   DESCRIPTION
       "The VclConfigMac Index."
   ::= { sm8tat2saVclConfigMacStatusEntry 1 }

sm8tat2saVclMacStatusMacAddress OBJECT-TYPE
    SYNTAX MacAddress
    MAX-ACCESS read-only
    STATUS current
    DESCRIPTION
        "The MAC address for which this entry is applicable."
    ::= { sm8tat2saVclConfigMacStatusEntry 2 }

sm8tat2saVclMacStatusVlanId OBJECT-TYPE
    SYNTAX Integer32 (1..4095)
    MAX-ACCESS read-only
    STATUS current
    DESCRIPTION
        "Vlan id of the mapping."
    ::= { sm8tat2saVclConfigMacStatusEntry 3 }

sm8tat2saVclMacStatusUser OBJECT-TYPE
    SYNTAX INTEGER { static(0), dms(1) }
    MAX-ACCESS read-only
    STATUS current
    DESCRIPTION
        "User of the mapping."
    ::= { sm8tat2saVclConfigMacStatusEntry 4 }

sm8tat2saVclConfigProtocol OBJECT IDENTIFIER
    ::= { sm8tat2saVclConfig 2 }

sm8tat2saVclConfigProtocolProto OBJECT IDENTIFIER
    ::= { sm8tat2saVclConfigProtocol 1 }

sm8tat2saVclConfigProtocolProtoTable OBJECT-TYPE
    SYNTAX SEQUENCE OF SM8TAT2SAVclConfigProtocolProtoEntry
    MAX-ACCESS not-accessible
    STATUS current
    DESCRIPTION
        "This is the Protocol to Protocol Group mapping table."
    ::= { sm8tat2saVclConfigProtocolProto 1 }

sm8tat2saVclConfigProtocolProtoEntry OBJECT-TYPE
    SYNTAX SM8TAT2SAVclConfigProtocolProtoEntry
    MAX-ACCESS not-accessible
    STATUS current
    DESCRIPTION
        "Each entry in this table represents a Protocol to Group mapping."
    INDEX { sm8tat2saVclConfigProtocolProtoProtocolIndex }
    ::= { sm8tat2saVclConfigProtocolProtoTable 1 }

SM8TAT2SAVclConfigProtocolProtoEntry ::= SEQUENCE {
    sm8tat2saVclConfigProtocolProtoProtocolIndex Integer32,
    sm8tat2saVclConfigProtocolProtoProtocolType Integer32,
    sm8tat2saVclConfigProtocolProtoProtocolValue DisplayString,
    sm8tat2saVclConfigProtocolProtoProtocolGroupName DisplayString,
    sm8tat2saVclConfigProtocolProtoRowStatus RowStatus
}

sm8tat2saVclConfigProtocolProtoProtocolIndex OBJECT-TYPE
    SYNTAX Integer32 (1..64)
    MAX-ACCESS not-accessible
    STATUS current
    DESCRIPTION
        "The protocol index of the Protocol to Group mapping."
    ::= { sm8tat2saVclConfigProtocolProtoEntry 1 }

sm8tat2saVclConfigProtocolProtoProtocolType OBJECT-TYPE
   SYNTAX Integer32 (1..3)
   MAX-ACCESS read-create
   STATUS current
   DESCRIPTION
       "1: Ethernet II encapsulation, 2: LLC SNAP encapsulation, 3: LLC Other encapsulation"
   ::= { sm8tat2saVclConfigProtocolProtoEntry 2 }

sm8tat2saVclConfigProtocolProtoProtocolValue OBJECT-TYPE
   SYNTAX DisplayString (SIZE (4..11))
   MAX-ACCESS read-create
   STATUS current
   DESCRIPTION
       "Protocol Type is Ethernet(1), value range: 0x600~0xffff,
        Protocol Type is SNAP(2), OID value is 0x000000, value range: 0x0000~0xffff(pid value),
        Protocol Type is LLC(3), value range: 0x0000~0xffff(dsap value:0x00~0xff, ssap value:0x00~0xff)"
   ::= { sm8tat2saVclConfigProtocolProtoEntry 3 }

sm8tat2saVclConfigProtocolProtoProtocolGroupName OBJECT-TYPE
    SYNTAX DisplayString (SIZE(1..16))
    MAX-ACCESS read-create
    STATUS current
    DESCRIPTION
        "This is a name identifying the protocol group."
    ::= { sm8tat2saVclConfigProtocolProtoEntry 4 }

sm8tat2saVclConfigProtocolProtoRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm8tat2saVclConfigProtocolProtoEntry 5 }

sm8tat2saVclConfigProtocolGroup OBJECT IDENTIFIER
    ::= { sm8tat2saVclConfigProtocol 2 }

sm8tat2saVclConfigProtocolGroupTable OBJECT-TYPE
    SYNTAX SEQUENCE OF SM8TAT2SAVclConfigProtocolGroupEntry
    MAX-ACCESS not-accessible
    STATUS current
    DESCRIPTION
        "This is the Protocol Group to VLAN ID configuration table."
    ::= { sm8tat2saVclConfigProtocolGroup 1 }

sm8tat2saVclConfigProtocolGroupEntry OBJECT-TYPE
    SYNTAX SM8TAT2SAVclConfigProtocolGroupEntry
    MAX-ACCESS not-accessible
    STATUS current
    DESCRIPTION
        "Each entry in this table represents a Protocol Group to VLAN ID
         mapping."
    INDEX { sm8tat2saVclConfigProtocolGroupProtocolIndex }
    ::= { sm8tat2saVclConfigProtocolGroupTable 1 }

SM8TAT2SAVclConfigProtocolGroupEntry ::= SEQUENCE {
    sm8tat2saVclConfigProtocolGroupProtocolIndex Integer32,
    sm8tat2saVclConfigProtocolGroupProtocolGroupName DisplayString,
    sm8tat2saVclConfigProtocolGroupVlanId Integer32,
    sm8tat2saVclConfigProtocolGroupPortList PortSelect,
    sm8tat2saVclConfigProtocolGroupRowStatus RowStatus
}

sm8tat2saVclConfigProtocolGroupProtocolIndex OBJECT-TYPE
    SYNTAX Integer32 (1..64)
    MAX-ACCESS not-accessible
    STATUS current
    DESCRIPTION
        "The protocol index of the Protocol to Group mapping."
    ::= { sm8tat2saVclConfigProtocolGroupEntry 1 }

sm8tat2saVclConfigProtocolGroupProtocolGroupName OBJECT-TYPE
    SYNTAX DisplayString (SIZE(1..16))
    MAX-ACCESS read-create
    STATUS current
    DESCRIPTION
        "This is a name identifying the protocol group."
    ::= { sm8tat2saVclConfigProtocolGroupEntry 2 }

sm8tat2saVclConfigProtocolGroupVlanId OBJECT-TYPE
    SYNTAX Integer32 (1..4095)
    MAX-ACCESS read-create
    STATUS current
    DESCRIPTION
        "Vlan id of the mapping."
    ::= { sm8tat2saVclConfigProtocolGroupEntry 3 }

sm8tat2saVclConfigProtocolGroupPortList OBJECT-TYPE
    SYNTAX PortSelect
    MAX-ACCESS read-create
    STATUS current
    DESCRIPTION
        "List of switch ports on which this entry is active."
    ::= { sm8tat2saVclConfigProtocolGroupEntry 4 }

sm8tat2saVclConfigProtocolGroupRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm8tat2saVclConfigProtocolGroupEntry 5 }

sm8tat2saVclConfigIpTable OBJECT-TYPE
    SYNTAX SEQUENCE OF SM8TAT2SAVclConfigIpEntry
    MAX-ACCESS not-accessible
    STATUS current
    DESCRIPTION
        "This is the IP Subnet to VLAN ID configuration table. The key of this
         table is the IP subnet expressed as x.x.x.x/x, where the first 4 octets
         represent the IPv4 address and the last one is the mask length.

         NOTE#1: Inside the VCL module these entries are actually sorted based
         on a priority defined by the mask length, so that subnets with larger
         mask lengths are first in the list, followed by entries with smaller
         mask lengths. SNMP cannot follow this sorting, therefore the order the
         entries are retrieved by the iterator may not be the same as the
         actually stored order. (This is not an issue, but should be taken into
         consideration when using the SNMP interface to create a user interface.

         NOTE#2: Even though only the subnet address is stored in the table
         (i.e. both 192.168.1.0/4 and 192.168.2.0/4 will end up as 192.0.0.0/4),
         the SNMP iterator will NOT take this into consideration. So, when
         searching the next subnet of 192.168.1.0/4, the result could be
         193.0.0.0/4 but not 192.168.1.0/24 (granted that these entries are
         present)"
    ::= { sm8tat2saVclConfig 3 }

sm8tat2saVclConfigIpEntry OBJECT-TYPE
    SYNTAX SM8TAT2SAVclConfigIpEntry
    MAX-ACCESS not-accessible
    STATUS current
    DESCRIPTION
        "Each entry in this table represents a configured IP Subnet-based
         classification."
    INDEX { sm8tat2saVclConfigIpIndex }
    ::= { sm8tat2saVclConfigIpTable 1 }

SM8TAT2SAVclConfigIpEntry ::= SEQUENCE {
    sm8tat2saVclConfigIpIndex Integer32,
    sm8tat2saVclConfigIpIpSubnetAddress IpAddress,
    sm8tat2saVclConfigIpIpSubnetMaskLength Integer32,
    sm8tat2saVclConfigIpVlanId Integer32,
    sm8tat2saVclConfigIpRowStatus RowStatus
}

sm8tat2saVclConfigIpIndex OBJECT-TYPE
   SYNTAX Integer32 (1..64)
   MAX-ACCESS not-accessible
   STATUS current
   DESCRIPTION
       "The VclConfigIp Index."
   ::= { sm8tat2saVclConfigIpEntry 1 }

sm8tat2saVclConfigIpIpSubnetAddress OBJECT-TYPE
    SYNTAX IpAddress
    MAX-ACCESS read-create
    STATUS current
    DESCRIPTION
        "The IP subnet address for which this entry is applicable."
    ::= { sm8tat2saVclConfigIpEntry 2 }

sm8tat2saVclConfigIpIpSubnetMaskLength OBJECT-TYPE
    SYNTAX Integer32 (1..32)
    MAX-ACCESS read-create
    STATUS current
    DESCRIPTION
        "The IP subnet mask length for which this entry is applicable."
    ::= { sm8tat2saVclConfigIpEntry 3 }

sm8tat2saVclConfigIpVlanId OBJECT-TYPE
    SYNTAX Integer32 (1..4095)
    MAX-ACCESS read-create
    STATUS current
    DESCRIPTION
        "Vlan id of the mapping."
    ::= { sm8tat2saVclConfigIpEntry 4 }

sm8tat2saVclConfigIpRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm8tat2saVclConfigIpEntry 5 }

sm8tat2saVlanSelectiveQinQ OBJECT IDENTIFIER ::= { sm8tat2saVLANConf 4 }

sm8tat2saVlanSelectiveTable OBJECT-TYPE
    SYNTAX SEQUENCE OF SM8TAT2SAVlanSelectiveEntry
    MAX-ACCESS not-accessible
    STATUS current
    DESCRIPTION
        "This is the Vlan Selective QinQ configuration table."
    ::= { sm8tat2saVlanSelectiveQinQ 1 }

sm8tat2saVlanSelectiveEntry OBJECT-TYPE
    SYNTAX SM8TAT2SAVlanSelectiveEntry
    MAX-ACCESS not-accessible
    STATUS current
    DESCRIPTION
        "Each entry in this table represents a configured selective qinq."
    INDEX { sm8tat2saVlanSelectiveIndex }
    ::= { sm8tat2saVlanSelectiveTable 1 }

SM8TAT2SAVlanSelectiveEntry ::= SEQUENCE {
    sm8tat2saVlanSelectiveIndex Integer32,
    sm8tat2saVlanSelectiveCVID Integer32,
    sm8tat2saVlanSelectiveSPID Integer32,
    sm8tat2saVlanSelectivePortList PortSelect,
    sm8tat2saVlanSelectiveRowStatus RowStatus
}

sm8tat2saVlanSelectiveIndex OBJECT-TYPE
   SYNTAX Integer32 (1..128)
   MAX-ACCESS not-accessible
   STATUS current
   DESCRIPTION
       "The Vlan Selective QinQ Index."
   ::= { sm8tat2saVlanSelectiveEntry 1 }

sm8tat2saVlanSelectiveCVID OBJECT-TYPE
    SYNTAX Integer32 (1..4094)
    MAX-ACCESS read-create
    STATUS current
    DESCRIPTION
        "The CVID for which this entry is applicable."
    ::= { sm8tat2saVlanSelectiveEntry 2 }

sm8tat2saVlanSelectiveSPID OBJECT-TYPE
    SYNTAX Integer32 (1..4094)
    MAX-ACCESS read-create
    STATUS current
    DESCRIPTION
        "The SPID for which this entry is applicable."
    ::= { sm8tat2saVlanSelectiveEntry 3 }

sm8tat2saVlanSelectivePortList OBJECT-TYPE
    SYNTAX PortSelect
    MAX-ACCESS read-create
    STATUS current
    DESCRIPTION
        "List of switch ports on which this entry is active."
    ::= { sm8tat2saVlanSelectiveEntry 4 }

sm8tat2saVlanSelectiveRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm8tat2saVlanSelectiveEntry 5 }

sm8tat2saPvlanConfig OBJECT IDENTIFIER ::= { sm8tat2saVLANConf 5 }

sm8tat2saPvlanConfigVlanMembershipTable OBJECT-TYPE
    SYNTAX SEQUENCE OF SM8TAT2SAPvlanConfigVlanMembershipEntry
    MAX-ACCESS not-accessible
    STATUS current
    DESCRIPTION
        "This is a table for managing Private VLAN VLAN membership entries."
    ::= { sm8tat2saPvlanConfig 1 }

sm8tat2saPvlanConfigVlanMembershipEntry OBJECT-TYPE
    SYNTAX SM8TAT2SAPvlanConfigVlanMembershipEntry
    MAX-ACCESS not-accessible
    STATUS current
    DESCRIPTION
        "Each entry has a set of parameters."
    INDEX { sm8tat2saPvlanConfigVlanMembershipPvlanIndex }
    ::= { sm8tat2saPvlanConfigVlanMembershipTable 1 }

SM8TAT2SAPvlanConfigVlanMembershipEntry ::= SEQUENCE {
    sm8tat2saPvlanConfigVlanMembershipPvlanIndex Integer32,
    sm8tat2saPvlanConfigVlanMembershipPvlanId Integer32,
    sm8tat2saPvlanConfigVlanMembershipPortList PortSelect,
    sm8tat2saPvlanConfigVlanMembershipRowStatus RowStatus
}

sm8tat2saPvlanConfigVlanMembershipPvlanIndex OBJECT-TYPE
   SYNTAX Integer32 (1..128)
   MAX-ACCESS not-accessible
   STATUS current
   DESCRIPTION
       "Configuration index of the Private VLAN membership table."
   ::= { sm8tat2saPvlanConfigVlanMembershipEntry 1 }

sm8tat2saPvlanConfigVlanMembershipPvlanId OBJECT-TYPE
    SYNTAX Integer32 (1..128)
    MAX-ACCESS read-create
    STATUS current
    DESCRIPTION
        "Configuration Private vlan Id of the Private VLAN membership table."
    ::= { sm8tat2saPvlanConfigVlanMembershipEntry 2 }

sm8tat2saPvlanConfigVlanMembershipPortList OBJECT-TYPE
    SYNTAX PortSelect
    MAX-ACCESS read-create
    STATUS current
    DESCRIPTION
        "It is used to denote the memberships of the specific Private VLAN configuration."
    ::= { sm8tat2saPvlanConfigVlanMembershipEntry 3 }

sm8tat2saPvlanConfigVlanMembershipRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm8tat2saPvlanConfigVlanMembershipEntry 4 }

sm8tat2saPvlanConfigPortIsolatationTable OBJECT-TYPE
    SYNTAX SEQUENCE OF SM8TAT2SAPvlanConfigPortIsolatationEntry
    MAX-ACCESS not-accessible
    STATUS current
    DESCRIPTION
        "This is a table for managing Private VLAN port isolation entries."
    ::= { sm8tat2saPvlanConfig 2 }

sm8tat2saPvlanConfigPortIsolatationEntry OBJECT-TYPE
    SYNTAX SM8TAT2SAPvlanConfigPortIsolatationEntry
    MAX-ACCESS not-accessible
    STATUS current
    DESCRIPTION
        "Each entry has a set of parameters."
    INDEX { sm8tat2saPvlanConfigPortIsolatationPortIndex }
    ::= { sm8tat2saPvlanConfigPortIsolatationTable 1 }

SM8TAT2SAPvlanConfigPortIsolatationEntry ::= SEQUENCE {
    sm8tat2saPvlanConfigPortIsolatationPortIndex Integer32,
    sm8tat2saPvlanConfigPortIsolatationEnabled INTEGER
}

sm8tat2saPvlanConfigPortIsolatationPortIndex OBJECT-TYPE
    SYNTAX Integer32(1..4095)
    MAX-ACCESS not-accessible
    STATUS current
    DESCRIPTION
        "Logical number of the Private VLAN port isolation."
    ::= { sm8tat2saPvlanConfigPortIsolatationEntry 1 }

sm8tat2saPvlanConfigPortIsolatationEnabled OBJECT-TYPE
    SYNTAX INTEGER { disable(0), enable(1) }
    MAX-ACCESS read-write
    STATUS current
    DESCRIPTION
        "Enable/Disable the Private VLAN isolation functionality."
    ::= { sm8tat2saPvlanConfigPortIsolatationEntry 2 }

sm8tat2saVoiceVlanConfig OBJECT IDENTIFIER ::= { sm8tat2saVLANConf 6 }

sm8tat2saVoiceVlanGlobalConfig OBJECT IDENTIFIER ::= { sm8tat2saVoiceVlanConfig 1 }

sm8tat2saVoiceVlanConfigTable OBJECT-TYPE
    SYNTAX SEQUENCE OF SM8TAT2SAVoiceVlanConfigEntry
    MAX-ACCESS not-accessible
    STATUS current
    DESCRIPTION
        "This is the Voice Vlan configuration table."
    ::= { sm8tat2saVoiceVlanGlobalConfig 1 }

sm8tat2saVoiceVlanConfigEntry OBJECT-TYPE
    SYNTAX SM8TAT2SAVoiceVlanConfigEntry
    MAX-ACCESS not-accessible
    STATUS current
    DESCRIPTION
        "Each entry in this table represents a configured Voice Vlan
         classification."
    INDEX { sm8tat2saVoiceVlanConfigGlobalsMgmtIndex }
    ::= { sm8tat2saVoiceVlanConfigTable 1 }

SM8TAT2SAVoiceVlanConfigEntry ::= SEQUENCE {
    sm8tat2saVoiceVlanConfigGlobalsMgmtIndex Integer32,
    sm8tat2saVoiceVlanConfigGlobalsMgmtVlanId Integer32,
    sm8tat2saVoiceVlanConfigGlobalsMgmtAgingTime Integer32,
    sm8tat2saVoiceVlanConfigGlobalsMgmtTrafficClass Integer32,
    sm8tat2saVoiceVlanConfigGlobalsMgmtPortList PortSelect,
    sm8tat2saVoiceVlanConfigGlobalsMgmtRowStatus RowStatus
}

sm8tat2saVoiceVlanConfigGlobalsMgmtIndex OBJECT-TYPE
   SYNTAX Integer32 (1..4)
   MAX-ACCESS not-accessible
   STATUS current
   DESCRIPTION
       "The Voice Vlan Config Global Management Index."
   ::= { sm8tat2saVoiceVlanConfigEntry 1 }

sm8tat2saVoiceVlanConfigGlobalsMgmtVlanId OBJECT-TYPE
    SYNTAX Integer32 (1..4095)
    MAX-ACCESS read-create
    STATUS current
    DESCRIPTION
        "Voice Vlan VlanId."
    ::= { sm8tat2saVoiceVlanConfigEntry 2 }

sm8tat2saVoiceVlanConfigGlobalsMgmtAgingTime OBJECT-TYPE
    SYNTAX Integer32 (10..10000000)
    MAX-ACCESS read-create
    STATUS current
    DESCRIPTION
        "Voice Vlan Vlan Age Time."
    ::= { sm8tat2saVoiceVlanConfigEntry 3 }

sm8tat2saVoiceVlanConfigGlobalsMgmtTrafficClass OBJECT-TYPE
    SYNTAX Integer32 (0..7)
    MAX-ACCESS read-create
    STATUS current
    DESCRIPTION
        "Voice Vlan Vlan Traffic Class."
    ::= { sm8tat2saVoiceVlanConfigEntry 4 }

sm8tat2saVoiceVlanConfigGlobalsMgmtPortList OBJECT-TYPE
    SYNTAX PortSelect
    MAX-ACCESS read-create
    STATUS current
    DESCRIPTION
        "List of switch ports on which this entry is active."
    ::= { sm8tat2saVoiceVlanConfigEntry 5 }

sm8tat2saVoiceVlanConfigGlobalsMgmtRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm8tat2saVoiceVlanConfigEntry 6 }

sm8tat2saVoiceVlanConfigInterface OBJECT IDENTIFIER
    ::= { sm8tat2saVoiceVlanConfig 2 }

sm8tat2saVoiceVlanConfigInterfacePortTable OBJECT-TYPE
    SYNTAX SEQUENCE OF SM8TAT2SAVoiceVlanConfigInterfacePortEntry
    MAX-ACCESS not-accessible
    STATUS current
    DESCRIPTION
        "This is a table for managing per port voice VLAN functions."
    ::= { sm8tat2saVoiceVlanConfigInterface 1 }

sm8tat2saVoiceVlanConfigInterfacePortEntry OBJECT-TYPE
    SYNTAX SM8TAT2SAVoiceVlanConfigInterfacePortEntry
    MAX-ACCESS not-accessible
    STATUS current
    DESCRIPTION
        "Each entry has a set of parameters."
    INDEX { sm8tat2saVoiceVlanConfigInterfacePortIfIndex }
    ::= { sm8tat2saVoiceVlanConfigInterfacePortTable 1 }

SM8TAT2SAVoiceVlanConfigInterfacePortEntry ::= SEQUENCE {
    sm8tat2saVoiceVlanConfigInterfacePortIfIndex Integer32,
    sm8tat2saVoiceVlanConfigInterfacePortMode VoiceVlanPortManagementType,
    sm8tat2saVoiceVlanConfigInterfacePortSecured INTEGER,
    sm8tat2saVoiceVlanConfigInterfacePortDiscoveryProtocol VoiceVlanPortDiscoveryProtocol
}

sm8tat2saVoiceVlanConfigInterfacePortIfIndex OBJECT-TYPE
    SYNTAX Integer32(1..1024)
    MAX-ACCESS not-accessible
    STATUS current
    DESCRIPTION
        "Logical interface number of the Voice VLAN port."
    ::= { sm8tat2saVoiceVlanConfigInterfacePortEntry 1 }

sm8tat2saVoiceVlanConfigInterfacePortMode OBJECT-TYPE
    SYNTAX VoiceVlanPortManagementType
    MAX-ACCESS read-write
    STATUS current
    DESCRIPTION
        "Management mode of the specific port in voice VLAN.
         'forced' will force the port to join voice VLAN.
         'automatic' will join the port in voice VLAN upon detecting
         attached VoIP devices by using DiscoveryProtocol parameter."
    ::= { sm8tat2saVoiceVlanConfigInterfacePortEntry 2 }

sm8tat2saVoiceVlanConfigInterfacePortSecured OBJECT-TYPE
    SYNTAX INTEGER { disable(0), enable(1) }
    MAX-ACCESS read-write
    STATUS current
    DESCRIPTION
        "Manage the security control of this port interface in voice VLAN, TRUE
         is to enable the security control and FALSE is to disable it. When it
         is disabled, all the traffic in voice VLAN will be permit. When it is
         enabled, all non-telephonic MAC addresses in the voice VLAN will be
         blocked for 10 seconds and thus the traffic from these senders will be
         deny."
    ::= { sm8tat2saVoiceVlanConfigInterfacePortEntry 3 }

sm8tat2saVoiceVlanConfigInterfacePortDiscoveryProtocol OBJECT-TYPE
    SYNTAX VoiceVlanPortDiscoveryProtocol
    MAX-ACCESS read-write
    STATUS current
    DESCRIPTION
        "Specify the protocol for detecting attached VoIP devices. It only works
         when 'automatic' is set in Mode parameter, and voice VLAN will restart
         automatic detecting process upon changing the protocol. When 'oui' is
         given, voice VLAN performs VoIP device detection based on checking
         telephony OUI settings via new MAC address notification. When 'lldp' is
         given, voice VLAN performs VoIP device detection based on LLDP
         notifications.When 'both' is given, voice VLAN performs VoIP device
         detection based on either new MAC address notification or LLDP
         notifications.

         In addition, the first come notification will be first served."
    ::= { sm8tat2saVoiceVlanConfigInterfacePortEntry 4 }

sm8tat2saVoiceVlanConfigOui OBJECT IDENTIFIER
    ::= { sm8tat2saVoiceVlanConfig 3 }

sm8tat2saVoiceVlanConfigOuiTable OBJECT-TYPE
    SYNTAX SEQUENCE OF SM8TAT2SAVoiceVlanConfigOuiEntry
    MAX-ACCESS not-accessible
    STATUS current
    DESCRIPTION
        "This is a table for managing the telephony OUI settings that will be
         used for voice VLAN functions."
    ::= { sm8tat2saVoiceVlanConfigOui 1 }

sm8tat2saVoiceVlanConfigOuiEntry OBJECT-TYPE
    SYNTAX SM8TAT2SAVoiceVlanConfigOuiEntry
    MAX-ACCESS not-accessible
    STATUS current
    DESCRIPTION
        "Each entry has a set of parameters."
    INDEX { sm8tat2saVoiceVlanConfigOuiIndex }
    ::= { sm8tat2saVoiceVlanConfigOuiTable 1 }

SM8TAT2SAVoiceVlanConfigOuiEntry ::= SEQUENCE {
    sm8tat2saVoiceVlanConfigOuiIndex Integer32,
    sm8tat2saVoiceVlanConfigOuiPrefix OCTET STRING,
    sm8tat2saVoiceVlanConfigOuiDescription DisplayString,
    sm8tat2saVoiceVlanConfigOuiRowStatus RowStatus
}

sm8tat2saVoiceVlanConfigOuiIndex OBJECT-TYPE
   SYNTAX Integer32 (1..32)
   MAX-ACCESS not-accessible
   STATUS current
   DESCRIPTION
       "The Voice Vlan Config Oui Index."
   ::= { sm8tat2saVoiceVlanConfigOuiEntry 1 }

sm8tat2saVoiceVlanConfigOuiPrefix OBJECT-TYPE
    SYNTAX OCTET STRING (SIZE(3..3))
    MAX-ACCESS read-create
    STATUS current
    DESCRIPTION
        "Address prefix of the telephony OUI. A leading 3 bytes index used to
         denote whether specific MAC address is presenting a voice device."
    ::= { sm8tat2saVoiceVlanConfigOuiEntry 2 }

sm8tat2saVoiceVlanConfigOuiDescription OBJECT-TYPE
    SYNTAX DisplayString (SIZE(0..32))
    MAX-ACCESS read-create
    STATUS current
    DESCRIPTION
        "The description for the specific telephony OUI."
    ::= { sm8tat2saVoiceVlanConfigOuiEntry 3 }

sm8tat2saVoiceVlanConfigOuiRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm8tat2saVoiceVlanConfigOuiEntry 4 }

-- *************************************************************
-- Start sm8tat2saUpnpConfigGlobals group
-- *************************************************************
sm8tat2saUpnpConfigGlobals OBJECT IDENTIFIER ::= { sm8tat2saSystem 11 }

sm8tat2saUpnpConfigGlobalsMode OBJECT-TYPE
    SYNTAX INTEGER { disable(0), enable(1) }
    MAX-ACCESS read-write
    STATUS current
    DESCRIPTION
        "Global mode of UPnP. true is to enable the functions of HTTPS and false
         is to disable it."
    ::= { sm8tat2saUpnpConfigGlobals 1 }

sm8tat2saUpnpConfigGlobalsInterfaceVlan OBJECT-TYPE
    SYNTAX Integer32 (1..4095)
    MAX-ACCESS read-write
    STATUS current
    DESCRIPTION
        "The Interface Vlan is used by UPnP to send SSDP advertisement messages in the Interface.
         Valid values are in the range 1 to 4095. "
    ::= { sm8tat2saUpnpConfigGlobals 2 }

sm8tat2saUpnpConfigGlobalsTtl OBJECT-TYPE
    SYNTAX Integer32 (1..255)
    MAX-ACCESS read-write
    STATUS current
    DESCRIPTION
        "The TTL value is used by UPnP to send SSDP advertisement messages.Valid
         values are in the range 1 to 255. "
    ::= { sm8tat2saUpnpConfigGlobals 3 }

sm8tat2saUpnpConfigGlobalsAdvertisingDuration OBJECT-TYPE
    SYNTAX Integer32 (66..86400)
    MAX-ACCESS read-write
    STATUS current
    DESCRIPTION
        "The duration, carried in SSDP packets, is used to inform a control
         point or control points how often it or they should receive an SSDP
         advertisement message from this switch. If a control point does not
         receive any message within the duration, it will think that the switch
         no longer exists. Due to the unreliable nature of UDP, in the standard
         it is recommended that such refreshing of advertisements to be done at
         less than one-half of the advertising duration. In the implementation,
         the switch sends SSDP messages periodically at the interval one-half of
         the advertising duration minus 30 seconds. Valid values are in the
         range 66 to 86400. "
    ::= { sm8tat2saUpnpConfigGlobals 4 }

-- *************************************************************
-- Start sm8tat2saSystemConformance group
-- *************************************************************
sm8tat2saSystemConformance OBJECT IDENTIFIER ::= { sm8tat2saSystem 200 }
sm8tat2saSystemCompliances OBJECT IDENTIFIER ::= { sm8tat2saSystemConformance 1 }
sm8tat2saSystemGroups OBJECT IDENTIFIER ::= { sm8tat2saSystemConformance 2 }

sm8tat2saSystemInformationGroup OBJECT-GROUP
    OBJECTS {
    --sm8tat2saSystemInformation
        sm8tat2saSystemInfoModelName,
        sm8tat2saSystemInfoSystemDescript,
        sm8tat2saSystemInfoHardwareVersion,
        sm8tat2saSystemInfoMechanicalVersion,
        sm8tat2saSystemInfoFirmwareVersion,
        sm8tat2saSystemInfoHostMACAddress,
        sm8tat2saSystemInfoSeriesNumber,
        sm8tat2saSystemInfoSystemName,
        sm8tat2saSystemInfoLocation,
        sm8tat2saSystemInfoContact,
        sm8tat2saSystemInfoSystemDate,
        sm8tat2saSystemInfoSystemUptime

        ,sm8tat2saSystemInfoPoEFirmwareVersion

    }
    STATUS current
    DESCRIPTION
        "The collection of objects which are used to
        indicate system information."
    ::= { sm8tat2saSystemGroups 1 }

sm8tat2saSystemTimeConfGroup OBJECT-GROUP
    OBJECTS {
    --sm8tat2saSystemTimeConf
      --sm8tat2saSystemTimeManual
        sm8tat2saSystemTimeManualClockSource,
        sm8tat2saSystemTimeManualLocaltime,
        sm8tat2saSystemTimeManualTimeZoneOffset,
        sm8tat2saSystemTimeManualTimeZoneAcronym,
        sm8tat2saSystemTimeManualDaylightSavings,
        sm8tat2saSystemTimeManualTimeSetOffset,
        sm8tat2saSystemTimeManualDaylightSavingsMonthFrom,
        sm8tat2saSystemTimeManualDaylightSavingsWeekFrom,
        sm8tat2saSystemTimeManualDaylightSavingsDayFrom,
        sm8tat2saSystemTimeManualDaylightSavingsHourFrom,
        sm8tat2saSystemTimeManualDaylightSavingsMonthTo,
        sm8tat2saSystemTimeManualDaylightSavingsWeekTo,
        sm8tat2saSystemTimeManualDaylightSavingsDayTo,
        sm8tat2saSystemTimeManualDaylightSavingsHourTo,

      --sm8tat2saSystemTimeNTP
        sm8tat2saSystemTimeNTPInterval,

        --sm8tat2saSystemTimeNTPTable
        sm8tat2saSystemTimeNTPServer
    }
    STATUS current
    DESCRIPTION
        "The collection of objects which are used to
        indicate system time information."
    ::= { sm8tat2saSystemGroups 2 }

sm8tat2saSystemAccountGroup OBJECT-GROUP
    OBJECTS {
    --sm8tat2saSystemAccount
      --sm8tat2saSystemUsersTable
        sm8tat2saUserName,
        sm8tat2saPassword,
        sm8tat2saUserPrivilegeLevel,
        sm8tat2saAccountUserRowStatus
    }
    STATUS current
    DESCRIPTION
        "The collection of objects which are used to
        indicate system account information."
    ::= { sm8tat2saSystemGroups 3 }

sm8tat2saIPGroup OBJECT-GROUP
    OBJECTS {
    --sm8tat2saIP
      --sm8tat2saIPConfiguration
        sm8tat2saDNSServerMode,
        sm8tat2saDNSServerIPAddress,
        sm8tat2saDNSServerVLAN,

        --sm8tat2saIPInterfacesTable
        sm8tat2saIPInterfacesVLAN,
        sm8tat2saIPInterfacesIPv4DHCPEnable,
        sm8tat2saIPInterfacesIPv4DHCPFallback,
        sm8tat2saIPInterfacesIPv4DHCPCurrentLease,
        sm8tat2saIPInterfacesIPv4Address,
        sm8tat2saIPInterfacesIPv4Mask,
        sm8tat2saIPInterfacesIPv6Address,
        sm8tat2saIPInterfacesIPv6Mask,
        sm8tat2saIPInterfacesRowStatus,

        --sm8tat2saIPRoutesTable
        sm8tat2saIPRoutesNetwork,
        sm8tat2saIPRoutesMaskLength,
        sm8tat2saIPRoutesGateway,
        sm8tat2saIPRoutesNextHopVLAN,
        sm8tat2saIPRoutesRowStatus,

        --sm8tat2saIPStatusInterfaceTable
        sm8tat2saIPStatusInterfaceName,
        sm8tat2saIPStatusInterfaceType,
        sm8tat2saIPStatusInterfaceAddress,
        sm8tat2saIPStatusInterfaceStatus,

        --sm8tat2saIPStatusRouteTable
        sm8tat2saIPStatusRouteNetwork,
        sm8tat2saIPStatusRouteGateway,
        sm8tat2saIPStatusRouteStatus,
        sm8tat2saIPStatusRouteInterface,

        --sm8tat2saIPStatusNeighborCacheTable
        sm8tat2saIPStatusNeighborCacheIPAddress,
        sm8tat2saIPStatusNeighborCacheLinkAddress,

      --sm8tat2saIPInterfaces
        --sm8tat2saIPInterfacesDHCPPerPort
        sm8tat2saIPInterfacesDHCPPerPortMode,
        sm8tat2saIPInterfacesDHCPPerPortVlan,
        sm8tat2saIPInterfacesDHCPPerPortIPRangeLow,
        sm8tat2saIPInterfacesDHCPPerPortIPRangeHigh,
        sm8tat2saIPInterfacesDHCPPerPortRowStatus
    }
    STATUS current
    DESCRIPTION
        "The collection of objects which are used to
        indicate IP information."
    ::= { sm8tat2saSystemGroups 4 }

sm8tat2saSyslogGroup OBJECT-GROUP
    OBJECTS {
    --sm8tat2saSyslog
      --sm8tat2saSyslogConf
        sm8tat2saSystemLogServerMode,
        --sm8tat2saSystemLogServerTable
        sm8tat2saSystemLogServerAddress,

      --sm8tat2saSysLogInfo
        sm8tat2saSystemLogInfoClear,
        --sm8tat2saSystemLogDetailedInfoTable
        sm8tat2saSystemLogDetailedInfoLevel,
        sm8tat2saSystemLogDetailedInfoTime,
        sm8tat2saSystemLogDetailedInfoMessage
    }
    STATUS current
    DESCRIPTION
        "The collection of objects which are used to
        indicate syslog information."
    ::= { sm8tat2saSystemGroups 5 }

sm8tat2saSnmpGroup OBJECT-GROUP
    OBJECTS {
    --sm8tat2saSnmp
        sm8tat2saSnmpGetCommunity,
        sm8tat2saSnmpSetCommunityMode,
        sm8tat2saSnmpSetCommunity,
        sm8tat2saSnmpVersion,

      --sm8tat2saSnmpCommunityTable
        sm8tat2saSnmpCommunityName,
        sm8tat2saSnmpCommunityIP,
        sm8tat2saSnmpCommunityMask,
        sm8tat2saSnmpCommunityRowStatus,

      --sm8tat2saTrapHostConfTable
        sm8tat2saTrapHostConfVersion,
        sm8tat2saTrapHostConfMode,
        sm8tat2saTrapHostConfIP,
        sm8tat2saTrapHostConfPort,
        sm8tat2saTrapHostConfCommunity,
        sm8tat2saTrapHostConfSeverityLevel,
        sm8tat2saTrapHostConfCurrentMode
    }
    STATUS current
    DESCRIPTION
        "The collection of objects which are used to
        indicate SNMP information."
    ::= { sm8tat2saSystemGroups 6 }

sm8tat2saPrivilegeLevelGroup OBJECT-GROUP
    OBJECTS {
    --sm8tat2saPrivilegeLevel
      --sm8tat2saPrivilegeLevelConfigTable
        sm8tat2saPrivilegeLevelGroupName,
        sm8tat2saPrivilegeLevelConfigReadOnly,
        sm8tat2saPrivilegeLevelConfigReadWrite
    }
    STATUS current
    DESCRIPTION
        "The collection of objects which are used to
        indicate privilege level information."
    ::= { sm8tat2saSystemGroups 7 }

sm8tat2saLldpConfigGroup OBJECT-GROUP
    OBJECTS {
    --sm8tat2saLldpConfig
      --sm8tat2saLldpConfigTable
        sm8tat2saLldpConfigCdpAware,

      --sm8tat2saLldpMedLocInfo
        sm8tat2saLldpMedLatitude,
        sm8tat2saLldpMedLatitudeDirection,
        sm8tat2saLldpMedLongitude,
        sm8tat2saLldpMedLongitudeDirection,
        sm8tat2saLldpMedAltitude,
        sm8tat2saLldpMedAltitudeType,
        sm8tat2saLldpMedDatum,
        sm8tat2saLldpMedElinAddr,
        sm8tat2saLldpMedCivicAddrLocInfoCountryCode,
        sm8tat2saLldpMedCivicAddrLocInfoState,
        sm8tat2saLldpMedCivicAddrLocInfoCounty,
        sm8tat2saLldpMedCivicAddrLocInfoCity,
        sm8tat2saLldpMedCivicAddrLocInfoDistrict,
        sm8tat2saLldpMedCivicAddrLocInfoBlock,
        sm8tat2saLldpMedCivicAddrLocInfoStreet,
        sm8tat2saLldpMedCivicAddrLocInfoLeadingStreetDirection,
        sm8tat2saLldpMedCivicAddrLocInfoTrailingStreetSuffix,
        sm8tat2saLldpMedCivicAddrLocInfoStreetSuffix,
        sm8tat2saLldpMedCivicAddrLocInfoHouseNo,
        sm8tat2saLldpMedCivicAddrLocInfoHouseNoSuffix,
        sm8tat2saLldpMedCivicAddrLocInfoLandmark,
        sm8tat2saLldpMedCivicAddrLocInfoAdditionalInfo,
        sm8tat2saLldpMedCivicAddrLocInfoName,
        sm8tat2saLldpMedCivicAddrLocInfoZipCode,
        sm8tat2saLldpMedCivicAddrLocInfoBuilding,
        sm8tat2saLldpMedCivicAddrLocInfoApartment,
        sm8tat2saLldpMedCivicAddrLocInfoFloor,
        sm8tat2saLldpMedCivicAddrLocInfoRoomNumber,
        sm8tat2saLldpMedCivicAddrLocInfoPlaceType,
        sm8tat2saLldpMedCivicAddrLocInfoPostalCommunityName,
        sm8tat2saLldpMedCivicAddrLocInfoPoBox,
        sm8tat2saLldpMedCivicAddrLocInfoAdditionalCode
    }
    STATUS current
    DESCRIPTION
        "The collection of objects which are used to
        indicate lldp config information."
    ::= { sm8tat2saSystemGroups 8 }

sm8tat2saVLANConfGroup OBJECT-GROUP
    OBJECTS {
    --sm8tat2saVLANConf
      --sm8tat2saVLAN
        sm8tat2saVlanExistingVLANs,
        sm8tat2saVlanEthertypeforCustomSPorts,

        -- sm8tat2saVlanTable
        sm8tat2saVlanMode,
        sm8tat2saVlanPortVLAN,
        sm8tat2saVlanPortType,
        sm8tat2saVlanIngressFiltering,
        sm8tat2saVlanIngressAcceptance,
        sm8tat2saVlanEgressTagging,
        sm8tat2saVlanAllowedVLANs,

      --sm8tat2saVlanStatus
        --sm8tat2saVLANPortStatusTable
        sm8tat2saVLANPortStatusPortType,
        sm8tat2saVLANPortStatusIngressFiltering,
        sm8tat2saVLANPortStatusFrameType,
        sm8tat2saVLANPortStatusPortVLANID,
        sm8tat2saVLANPortStatusTxTag,

      --sm8tat2saVclConfig
        --sm8tat2saVclConfigMac
          --sm8tat2saVclConfigMacBasedTable
        sm8tat2saVclConfigMacMacAddress,
        sm8tat2saVclConfigMacVlanId,
        sm8tat2saVclConfigMacRowStatus,
          --sm8tat2saVclConfigMacStatusTable
        sm8tat2saVclMacStatusMacAddress,
        sm8tat2saVclMacStatusVlanId,
        sm8tat2saVclMacStatusUser,

        --sm8tat2saVclConfigProtocol
          --sm8tat2saVclConfigProtocolProto
            --sm8tat2saVclConfigProtocolProtoTable
        sm8tat2saVclConfigProtocolProtoProtocolType,
        sm8tat2saVclConfigProtocolProtoProtocolValue,
        sm8tat2saVclConfigProtocolProtoProtocolGroupName,
        sm8tat2saVclConfigProtocolProtoRowStatus,
          --sm8tat2saVclConfigProtocolGroup
            --sm8tat2saVclConfigProtocolGroupTable
        sm8tat2saVclConfigProtocolGroupProtocolGroupName,
        sm8tat2saVclConfigProtocolGroupVlanId,
        sm8tat2saVclConfigProtocolGroupPortList,
        sm8tat2saVclConfigProtocolGroupRowStatus,

        --sm8tat2saVclConfigIpTable
        sm8tat2saVclConfigIpIpSubnetAddress,
        sm8tat2saVclConfigIpIpSubnetMaskLength,
        sm8tat2saVclConfigIpVlanId,
        sm8tat2saVclConfigIpRowStatus,

        --sm8tat2saVlanSelectiveQinQ
          --sm8tat2saVlanSelectiveTable
        sm8tat2saVlanSelectiveCVID,
        sm8tat2saVlanSelectiveSPID,
        sm8tat2saVlanSelectivePortList,
        sm8tat2saVlanSelectiveRowStatus,

        --sm8tat2saPvlanConfig
          --sm8tat2saPvlanConfigVlanMembershipTable
        sm8tat2saPvlanConfigVlanMembershipPvlanId,
        sm8tat2saPvlanConfigVlanMembershipPortList,
        sm8tat2saPvlanConfigVlanMembershipRowStatus,
          --sm8tat2saPvlanConfigPortIsolatationTable
        sm8tat2saPvlanConfigPortIsolatationEnabled,

        --sm8tat2saVoiceVlanConfig
          --sm8tat2saVoiceVlanGlobalConfig
            --sm8tat2saVoiceVlanConfigTable
        sm8tat2saVoiceVlanConfigGlobalsMgmtVlanId,
        sm8tat2saVoiceVlanConfigGlobalsMgmtAgingTime,
        sm8tat2saVoiceVlanConfigGlobalsMgmtTrafficClass,
        sm8tat2saVoiceVlanConfigGlobalsMgmtPortList,
        sm8tat2saVoiceVlanConfigGlobalsMgmtRowStatus,
          --sm8tat2saVoiceVlanConfigInterface
            --sm8tat2saVoiceVlanConfigInterfacePortTable
        sm8tat2saVoiceVlanConfigInterfacePortMode,
        sm8tat2saVoiceVlanConfigInterfacePortSecured,
        sm8tat2saVoiceVlanConfigInterfacePortDiscoveryProtocol,
          --sm8tat2saVoiceVlanConfigOui
            --sm8tat2saVoiceVlanConfigOuiTable
        sm8tat2saVoiceVlanConfigOuiPrefix,
        sm8tat2saVoiceVlanConfigOuiDescription,
        sm8tat2saVoiceVlanConfigOuiRowStatus
    }
    STATUS current
    DESCRIPTION
        "The collection of objects which are used to
        indicate vlan information."
    ::= { sm8tat2saSystemGroups 10 }

sm8tat2saUpnpConfigGroup OBJECT-GROUP
    OBJECTS {
    --sm8tat2saUpnpConfigGlobals
        sm8tat2saUpnpConfigGlobalsMode,
        sm8tat2saUpnpConfigGlobalsInterfaceVlan,
        sm8tat2saUpnpConfigGlobalsTtl,
        sm8tat2saUpnpConfigGlobalsAdvertisingDuration
    }
    STATUS current
    DESCRIPTION
        "The collection of objects which are used to
        indicate upnp config information."
    ::= { sm8tat2saSystemGroups 11 }

sm8tat2saSystemCompliance MODULE-COMPLIANCE
    STATUS current
    DESCRIPTION
        "The compliance statement for devices supporting system."
    MODULE
        MANDATORY-GROUPS {
            sm8tat2saSystemInformationGroup,
            sm8tat2saSystemTimeConfGroup,
            sm8tat2saSystemAccountGroup,
            sm8tat2saIPGroup,
            sm8tat2saSyslogGroup,
            sm8tat2saSnmpGroup,
            sm8tat2saPrivilegeLevelGroup,
            sm8tat2saLldpConfigGroup,
            sm8tat2saVLANConfGroup,
            sm8tat2saUpnpConfigGroup
        }
    ::= { sm8tat2saSystemCompliances 1 }

-- ================================================================================================================

sm8tat2saConfiguration OBJECT IDENTIFIER ::= { sm8tat2saProductId 2 }

-- *************************************************************
-- Start sm8tat2saPort group
-- *************************************************************
sm8tat2saPort OBJECT IDENTIFIER ::= { sm8tat2saConfiguration 1 }

sm8tat2saPortConfigurationTable OBJECT-TYPE
   SYNTAX SEQUENCE OF SM8TAT2SAPortConfigurationEntry
   MAX-ACCESS not-accessible
   STATUS current
   DESCRIPTION
       " Show port configurations. "
   ::= { sm8tat2saPort 1 }

sm8tat2saPortConfigurationEntry OBJECT-TYPE
   SYNTAX SM8TAT2SAPortConfigurationEntry
   MAX-ACCESS not-accessible
   STATUS current
   DESCRIPTION
       " "
   INDEX { sm8tat2saPortConfPort }
   ::= { sm8tat2saPortConfigurationTable 1 }

SM8TAT2SAPortConfigurationEntry ::= SEQUENCE {
   sm8tat2saPortConfPort Integer32,
   sm8tat2saPortConfPortMedia DisplayString,
   sm8tat2saPortConfLink DisplayString,
   sm8tat2saPortConfCurrentSpeed DisplayString,
   sm8tat2saPortConfSpeed INTEGER,
   sm8tat2saPortConfCurrentFlowControlRx INTEGER,
   sm8tat2saPortConfCurrentFlowControlTx INTEGER,
   sm8tat2saPortConfFlowControl INTEGER,
   sm8tat2saPortConfDescription DisplayString
}

sm8tat2saPortConfPort OBJECT-TYPE
   SYNTAX Integer32(1..4095)
   MAX-ACCESS not-accessible
   STATUS current
   DESCRIPTION
       " port, range : 1 - port number. "
   ::= { sm8tat2saPortConfigurationEntry 1 }

sm8tat2saPortConfPortMedia OBJECT-TYPE
   SYNTAX DisplayString(SIZE (1..6))
   MAX-ACCESS read-only
   STATUS current
   DESCRIPTION
       " Show port media. "
   ::= { sm8tat2saPortConfigurationEntry 2 }

sm8tat2saPortConfLink OBJECT-TYPE
   SYNTAX DisplayString(SIZE (2..4))
   MAX-ACCESS read-only
   STATUS current
   DESCRIPTION
       " The current link state. "
   ::= { sm8tat2saPortConfigurationEntry 3 }

sm8tat2saPortConfCurrentSpeed OBJECT-TYPE
   SYNTAX DisplayString(SIZE (6..12))
   MAX-ACCESS read-only
   STATUS current
   DESCRIPTION
       " The current link speed of the port. "
   ::= { sm8tat2saPortConfigurationEntry 4 }

sm8tat2saPortConfSpeed OBJECT-TYPE
   SYNTAX INTEGER {
                    disable(0),
                    auto(1),
                    speed10Half(2),
                    speed10Full(3),
                    speed100Half(4),
                    speed100Full(5),
                    speed1Gfull(6)
                }
   MAX-ACCESS read-write
   STATUS current
   DESCRIPTION
       "default: 1,
        0: disable state,
        1: auto,
        2: 10 Half,
        3: 10 Full,
        4: 100 Half,
        5: 100 Full,
        6: 1G full"
   ::= { sm8tat2saPortConfigurationEntry 5 }

sm8tat2saPortConfCurrentFlowControlRx OBJECT-TYPE
   SYNTAX INTEGER { disable(0), enable(1), noSupport(2) }
   MAX-ACCESS read-only
   STATUS current
   DESCRIPTION
       "0: disable
        1: enable
        2: no support. "
   ::= { sm8tat2saPortConfigurationEntry 6 }

sm8tat2saPortConfCurrentFlowControlTx OBJECT-TYPE
   SYNTAX INTEGER { disable(0), enable(1), noSupport(2) }
   MAX-ACCESS read-only
   STATUS current
   DESCRIPTION
       "0: disable
        1: enable
        2: no support. "
   ::= { sm8tat2saPortConfigurationEntry 7 }

sm8tat2saPortConfFlowControl OBJECT-TYPE
   SYNTAX INTEGER { disable(0), enable(1), noSupport(2) }
   MAX-ACCESS read-write
   STATUS current
   DESCRIPTION
       "default: 0,
        0: disable
        1: enable
        2: no support. (set:not include)"
   ::= { sm8tat2saPortConfigurationEntry 8 }

sm8tat2saPortConfDescription OBJECT-TYPE
   SYNTAX DisplayString
   MAX-ACCESS read-write
   STATUS current
   DESCRIPTION
       " Interface specific description.
         Up to 47 characters describing this interface. "
   ::= { sm8tat2saPortConfigurationEntry 9 }

sm8tat2saSFPInfoTable OBJECT-TYPE
   SYNTAX SEQUENCE OF SM8TAT2SASFPInfoEntry
   MAX-ACCESS not-accessible
   STATUS current
   DESCRIPTION
       " "
   ::= { sm8tat2saPort 4 }

sm8tat2saSFPInfoEntry OBJECT-TYPE
   SYNTAX SM8TAT2SASFPInfoEntry
   MAX-ACCESS not-accessible
   STATUS current
   DESCRIPTION
       " "
   INDEX { sm8tat2saSFPInfoIndex }
   ::= { sm8tat2saSFPInfoTable 1 }

SM8TAT2SASFPInfoEntry ::= SEQUENCE {
   sm8tat2saSFPInfoIndex Integer32,
   sm8tat2saSFPInfoPort DisplayString,
   sm8tat2saSFPConnectorType DisplayString,
   sm8tat2saSFPFiberType DisplayString,
   sm8tat2saSFPTxCentralWavelength DisplayString,
   sm8tat2saSFPBitRate DisplayString,
   sm8tat2saSFPVendorOUI DisplayString,
   sm8tat2saSFPVendorName DisplayString,
   sm8tat2saSFPVendorPN DisplayString,
   sm8tat2saSFPVendorRev DisplayString,
   sm8tat2saSFPVendorSN DisplayString,
   sm8tat2saSFPDateCode DisplayString,
   sm8tat2saSFPTemperature DisplayString,
   sm8tat2saSFPVcc DisplayString,
   sm8tat2saSFPMon1Bias DisplayString,
   sm8tat2saSFPMon2TxPWR DisplayString,
   sm8tat2saSFPMon3RxPWR DisplayString
}

sm8tat2saSFPInfoIndex OBJECT-TYPE
   SYNTAX Integer32(1..4095)
   MAX-ACCESS not-accessible
   STATUS current
   DESCRIPTION
       " "
   ::= { sm8tat2saSFPInfoEntry 1 }

sm8tat2saSFPInfoPort OBJECT-TYPE
   SYNTAX DisplayString
   MAX-ACCESS read-only
   STATUS current
   DESCRIPTION
       " "
   ::= { sm8tat2saSFPInfoEntry 2 }

sm8tat2saSFPConnectorType OBJECT-TYPE
   SYNTAX DisplayString
   MAX-ACCESS read-only
   STATUS current
   DESCRIPTION
       " "
   ::= { sm8tat2saSFPInfoEntry 3 }

sm8tat2saSFPFiberType OBJECT-TYPE
   SYNTAX DisplayString
   MAX-ACCESS read-only
   STATUS current
   DESCRIPTION
       " "
   ::= { sm8tat2saSFPInfoEntry 4 }

sm8tat2saSFPTxCentralWavelength OBJECT-TYPE
   SYNTAX DisplayString
   MAX-ACCESS read-only
   STATUS current
   DESCRIPTION
       " "
   ::= { sm8tat2saSFPInfoEntry 5 }

sm8tat2saSFPBitRate OBJECT-TYPE
   SYNTAX DisplayString
   MAX-ACCESS read-only
   STATUS current
   DESCRIPTION
       " "
   ::= { sm8tat2saSFPInfoEntry 6 }

sm8tat2saSFPVendorOUI OBJECT-TYPE
   SYNTAX DisplayString
   MAX-ACCESS read-only
   STATUS current
   DESCRIPTION
       " "
   ::= { sm8tat2saSFPInfoEntry 7 }

sm8tat2saSFPVendorName OBJECT-TYPE
   SYNTAX DisplayString
   MAX-ACCESS read-only
   STATUS current
   DESCRIPTION
       " "
   ::= { sm8tat2saSFPInfoEntry 8 }

sm8tat2saSFPVendorPN OBJECT-TYPE
   SYNTAX DisplayString
   MAX-ACCESS read-only
   STATUS current
   DESCRIPTION
       " "
   ::= { sm8tat2saSFPInfoEntry 9 }

sm8tat2saSFPVendorRev OBJECT-TYPE
   SYNTAX DisplayString
   MAX-ACCESS read-only
   STATUS current
   DESCRIPTION
       " "
   ::= { sm8tat2saSFPInfoEntry 10 }

sm8tat2saSFPVendorSN OBJECT-TYPE
   SYNTAX DisplayString
   MAX-ACCESS read-only
   STATUS current
   DESCRIPTION
       " "
   ::= { sm8tat2saSFPInfoEntry 11 }

sm8tat2saSFPDateCode OBJECT-TYPE
   SYNTAX DisplayString
   MAX-ACCESS read-only
   STATUS current
   DESCRIPTION
       " "
   ::= { sm8tat2saSFPInfoEntry 12 }

sm8tat2saSFPTemperature OBJECT-TYPE
   SYNTAX DisplayString
   MAX-ACCESS read-only
   STATUS current
   DESCRIPTION
       " "
   ::= { sm8tat2saSFPInfoEntry 13 }

sm8tat2saSFPVcc OBJECT-TYPE
   SYNTAX DisplayString
   MAX-ACCESS read-only
   STATUS current
   DESCRIPTION
       " "
   ::= { sm8tat2saSFPInfoEntry 14 }

sm8tat2saSFPMon1Bias OBJECT-TYPE
   SYNTAX DisplayString
   MAX-ACCESS read-only
   STATUS current
   DESCRIPTION
       " "
   ::= { sm8tat2saSFPInfoEntry 15 }

sm8tat2saSFPMon2TxPWR OBJECT-TYPE
   SYNTAX DisplayString
   MAX-ACCESS read-only
   STATUS current
   DESCRIPTION
       " "
   ::= { sm8tat2saSFPInfoEntry 16 }

sm8tat2saSFPMon3RxPWR OBJECT-TYPE
   SYNTAX DisplayString
   MAX-ACCESS read-only
   STATUS current
   DESCRIPTION
       " "
   ::= { sm8tat2saSFPInfoEntry 17 }

sm8tat2saPortEnergyEfficientTable OBJECT-TYPE
   SYNTAX SEQUENCE OF SM8TAT2SAPortEnergyEfficientEntry
   MAX-ACCESS not-accessible
   STATUS current
   DESCRIPTION
       " "
   ::= { sm8tat2saPort 5 }

sm8tat2saPortEnergyEfficientEntry OBJECT-TYPE
   SYNTAX SM8TAT2SAPortEnergyEfficientEntry
   MAX-ACCESS not-accessible
   STATUS current
   DESCRIPTION
       " "
   INDEX { sm8tat2saPortEnergyEfficientPort }
   ::= { sm8tat2saPortEnergyEfficientTable 1 }

SM8TAT2SAPortEnergyEfficientEntry ::= SEQUENCE {
   sm8tat2saPortEnergyEfficientPort Integer32,
   sm8tat2saPortEnergyEfficientMode INTEGER
}

sm8tat2saPortEnergyEfficientPort OBJECT-TYPE
   SYNTAX Integer32 (1..4095)
   MAX-ACCESS not-accessible
   STATUS current
   DESCRIPTION
       " "
   ::= { sm8tat2saPortEnergyEfficientEntry 1 }

sm8tat2saPortEnergyEfficientMode OBJECT-TYPE
   SYNTAX INTEGER { disable(0), enable(1) }
   MAX-ACCESS read-write
   STATUS current
   DESCRIPTION
       "default: 0
       0: disable
       1: enable"
   ::= { sm8tat2saPortEnergyEfficientEntry 2 }

sm8tat2saPortGlobalConfig
                                                      OBJECT IDENTIFIER ::= { sm8tat2saPort 6 }
sm8tat2saPortMaximumFrameSize OBJECT-TYPE
   SYNTAX Integer32 (1518..10000)
   MAX-ACCESS read-write
   STATUS current
   DESCRIPTION
       "Maximum packet length filtering is examined on both receiving and transmitting ports."
   ::= { sm8tat2saPortGlobalConfig 1 }

-- *************************************************************
-- Start sm8tat2saEventConfig group
-- *************************************************************
sm8tat2saEventConfig OBJECT IDENTIFIER ::= { sm8tat2saConfiguration 7 }

sm8tat2saEventConfigTable OBJECT-TYPE
   SYNTAX SEQUENCE OF SM8TAT2SAEventConfigEntry
   MAX-ACCESS not-accessible
   STATUS current
   DESCRIPTION
       "A list of event configuration entry."
   ::= { sm8tat2saEventConfig 1 }

sm8tat2saEventConfigEntry OBJECT-TYPE
   SYNTAX SM8TAT2SAEventConfigEntry
   MAX-ACCESS not-accessible
   STATUS current
   DESCRIPTION
       "This is the entry information for event configuration."
   INDEX { sm8tat2saEventConfigIndex }
   ::= { sm8tat2saEventConfigTable 1 }

SM8TAT2SAEventConfigEntry ::= SEQUENCE {
    sm8tat2saEventConfigIndex Integer32,
    sm8tat2saEventConfigGroupName DisplayString,
    sm8tat2saEventConfigSeverityLevel SeverityLevel,
    sm8tat2saEventConfigSyslog AdminMode,
    sm8tat2saEventConfigTrap AdminMode,
    sm8tat2saEventConfigSMTP AdminMode
}

sm8tat2saEventConfigIndex OBJECT-TYPE
   SYNTAX Integer32 (1..1024)
   MAX-ACCESS not-accessible
   STATUS current
   DESCRIPTION
       " The index of the event configuration group name entry. "
   ::= { sm8tat2saEventConfigEntry 1 }

sm8tat2saEventConfigGroupName OBJECT-TYPE
   SYNTAX DisplayString
   MAX-ACCESS read-only
   STATUS current
   DESCRIPTION
       "The name identifying the severity group. "
   ::= { sm8tat2saEventConfigEntry 2 }

sm8tat2saEventConfigSeverityLevel OBJECT-TYPE
   SYNTAX SeverityLevel
   MAX-ACCESS read-write
   STATUS current
   DESCRIPTION
       "The severity level. "
   ::= { sm8tat2saEventConfigEntry 3 }

sm8tat2saEventConfigSyslog OBJECT-TYPE
   SYNTAX AdminMode
   MAX-ACCESS read-write
   STATUS current
   DESCRIPTION
       "Enable - Select this Group Name in Syslog. "
   ::= { sm8tat2saEventConfigEntry 4 }

sm8tat2saEventConfigTrap OBJECT-TYPE
   SYNTAX AdminMode
   MAX-ACCESS read-write
   STATUS current
   DESCRIPTION
       "Enable - Select this Group Name in Trap. "
   ::= { sm8tat2saEventConfigEntry 5 }

sm8tat2saEventConfigSMTP OBJECT-TYPE
   SYNTAX AdminMode
   MAX-ACCESS read-write
   STATUS current
   DESCRIPTION
       "Enable - Select this Group Name in SMTP. "
   ::= { sm8tat2saEventConfigEntry 6 }

-- *************************************************************
-- Start sm8tat2saSMTP group
-- *************************************************************
sm8tat2saSMTP OBJECT IDENTIFIER ::= { sm8tat2saConfiguration 8 }

sm8tat2saSMTPMailServer OBJECT-TYPE
   SYNTAX DisplayString
   MAX-ACCESS read-write
   STATUS current
   DESCRIPTION
       " Up to 48 characters describing email server. "
   ::= { sm8tat2saSMTP 1 }

sm8tat2saSMTPUserName OBJECT-TYPE
   SYNTAX DisplayString
   MAX-ACCESS read-write
   STATUS current
   DESCRIPTION
       " Up to 32 characters describing user name. "
   ::= { sm8tat2saSMTP 2 }

sm8tat2saSMTPPassword OBJECT-TYPE
   SYNTAX DisplayString
   MAX-ACCESS read-write
   STATUS current
   DESCRIPTION
       " Up to 32 characters describing password. "
   ::= { sm8tat2saSMTP 3 }

sm8tat2saSMTPSender OBJECT-TYPE
   SYNTAX DisplayString
   MAX-ACCESS read-write
   STATUS current
   DESCRIPTION
       " Up to 48 characters describing sender. "
   ::= { sm8tat2saSMTP 5 }

sm8tat2saSMTPReturnPath OBJECT-TYPE
   SYNTAX DisplayString
   MAX-ACCESS read-write
   STATUS current
   DESCRIPTION
       " Up to 48 characters describing return path. "
   ::= { sm8tat2saSMTP 6 }

sm8tat2saSMTPEmailAddress1 OBJECT-TYPE
   SYNTAX DisplayString
   MAX-ACCESS read-write
   STATUS current
   DESCRIPTION
       " Up to 48 characters describing mail address. "
   ::= { sm8tat2saSMTP 7 }

sm8tat2saSMTPEmailAddress2 OBJECT-TYPE
   SYNTAX DisplayString
   MAX-ACCESS read-write
   STATUS current
   DESCRIPTION
       " Up to 48 characters describing mail address. "
   ::= { sm8tat2saSMTP 8 }

sm8tat2saSMTPEmailAddress3 OBJECT-TYPE
   SYNTAX DisplayString
   MAX-ACCESS read-write
   STATUS current
   DESCRIPTION
       " Up to 48 characters describing mail address. "
   ::= { sm8tat2saSMTP 9 }

sm8tat2saSMTPEmailAddress4 OBJECT-TYPE
   SYNTAX DisplayString
   MAX-ACCESS read-write
   STATUS current
   DESCRIPTION
       " Up to 48 characters describing mail address. "
   ::= { sm8tat2saSMTP 10 }

sm8tat2saSMTPEmailAddress5 OBJECT-TYPE
   SYNTAX DisplayString
   MAX-ACCESS read-write
   STATUS current
   DESCRIPTION
       " Up to 48 characters describing mail address. "
   ::= { sm8tat2saSMTP 11 }

sm8tat2saSMTPEmailAddress6 OBJECT-TYPE
   SYNTAX DisplayString
   MAX-ACCESS read-write
   STATUS current
   DESCRIPTION
       " Up to 48 characters describing mail address. "
   ::= { sm8tat2saSMTP 12 }

-- *************************************************************
-- Start sm8tat2saQosConf group
-- *************************************************************
sm8tat2saQosConf OBJECT IDENTIFIER ::= { sm8tat2saConfiguration 10 }

sm8tat2saQosGobalSettings OBJECT IDENTIFIER ::= { sm8tat2saQosConf 1 }
sm8tat2saQosPortSettings OBJECT IDENTIFIER ::= { sm8tat2saQosConf 2 }
sm8tat2saQosPortPolicing OBJECT IDENTIFIER ::= { sm8tat2saQosConf 3 }
sm8tat2saQosPortShaper OBJECT IDENTIFIER ::= { sm8tat2saQosConf 4 }
sm8tat2saQosStormControl OBJECT IDENTIFIER ::= { sm8tat2saQosConf 5 }
sm8tat2saQosPortScheduler OBJECT IDENTIFIER ::= { sm8tat2saQosConf 6 }
sm8tat2saQosCoS8021pMapping OBJECT IDENTIFIER ::= { sm8tat2saQosConf 7 }
sm8tat2saQosCoS8021pRemarking OBJECT IDENTIFIER ::= { sm8tat2saQosConf 8 }
sm8tat2saQosIPPrecedenceMapping OBJECT IDENTIFIER ::= { sm8tat2saQosConf 9 }
sm8tat2saQosIPPrecedenceRemarking OBJECT IDENTIFIER ::= { sm8tat2saQosConf 10 }
sm8tat2saQosDSCPMapping OBJECT IDENTIFIER ::= { sm8tat2saQosConf 11 }
sm8tat2saQosDSCPRemarking OBJECT IDENTIFIER ::= { sm8tat2saQosConf 12 }

sm8tat2saQosGobalSettingsTrustMode OBJECT-TYPE
    SYNTAX INTEGER { cos8021p(0), dscp(1), ipPrecedence(2), cos8021pdscp(3) }
    MAX-ACCESS read-write
    STATUS current
    DESCRIPTION
        "0: Cos/802.1p,
         1: DSCP,
         2: IP Precedence,
         3: Cos/802.1p-DSCP."
    ::= { sm8tat2saQosGobalSettings 1 }

sm8tat2saQosPortSettingsTable OBJECT-TYPE
    SYNTAX SEQUENCE OF SM8TAT2SAQosPortSettingsEntry
    MAX-ACCESS not-accessible
    STATUS current
    DESCRIPTION
        "The Port Settings."
    ::= { sm8tat2saQosPortSettings 1 }

sm8tat2saQosPortSettingsEntry OBJECT-TYPE
    SYNTAX SM8TAT2SAQosPortSettingsEntry
    MAX-ACCESS not-accessible
    STATUS current
    DESCRIPTION
         "The Port Settings Entry."
    INDEX { ifIndex }
    ::= { sm8tat2saQosPortSettingsTable 1 }

SM8TAT2SAQosPortSettingsEntry ::=
    SEQUENCE {
        sm8tat2saQosPortSettingsMode INTEGER,
        sm8tat2saQosPortSettingsDefaultCoS Integer32,
        sm8tat2saQosPortSettingsSourceCoS INTEGER,
        sm8tat2saQosPortSettingsRemarkCoS AdminMode,
        sm8tat2saQosPortSettingsRemarkDSCP AdminMode,
        sm8tat2saQosPortSettingsRemarkIPPrecedence AdminMode
    }

sm8tat2saQosPortSettingsMode OBJECT-TYPE
    SYNTAX INTEGER { untrust(0), trust(1) }
    MAX-ACCESS read-write
    STATUS current
    DESCRIPTION
        "0: untrust,
         1: trust."
    ::= { sm8tat2saQosPortSettingsEntry 1 }

sm8tat2saQosPortSettingsDefaultCoS OBJECT-TYPE
    SYNTAX Integer32(0..7)
    MAX-ACCESS read-write
    STATUS current
    DESCRIPTION
        "range: 0~7,
         default: 0."
    ::= { sm8tat2saQosPortSettingsEntry 2 }

sm8tat2saQosPortSettingsSourceCoS OBJECT-TYPE
    SYNTAX INTEGER { cTag(0), sTag(1) }
    MAX-ACCESS read-write
    STATUS current
    DESCRIPTION
        "0: cTag,
         1: sTag."
    ::= { sm8tat2saQosPortSettingsEntry 3 }

sm8tat2saQosPortSettingsRemarkCoS OBJECT-TYPE
    SYNTAX AdminMode
    MAX-ACCESS read-write
    STATUS current
    DESCRIPTION
        "Controls whether the remark CoS is enabled on this switch port settings."
    DEFVAL { disable }
    ::= { sm8tat2saQosPortSettingsEntry 4 }

sm8tat2saQosPortSettingsRemarkDSCP OBJECT-TYPE
    SYNTAX AdminMode
    MAX-ACCESS read-write
    STATUS current
    DESCRIPTION
        "Controls whether the remark DSCP is enabled on this switch port settings."
    DEFVAL { disable }
    ::= { sm8tat2saQosPortSettingsEntry 5 }

sm8tat2saQosPortSettingsRemarkIPPrecedence OBJECT-TYPE
    SYNTAX AdminMode
    MAX-ACCESS read-write
    STATUS current
    DESCRIPTION
        "Controls whether the remark IP precedence is enabled on this switch port settings."
    DEFVAL { disable }
    ::= { sm8tat2saQosPortSettingsEntry 6 }

sm8tat2saQosPortPolicingTable OBJECT-TYPE
    SYNTAX SEQUENCE OF SM8TAT2SAQosPortPolicingEntry
    MAX-ACCESS not-accessible
    STATUS current
    DESCRIPTION
        "The Policer settings.
         INDEX for this table is ifIndex which is
         equivalent to the panel port number."
    ::= { sm8tat2saQosPortPolicing 1 }

sm8tat2saQosPortPolicingEntry OBJECT-TYPE
    SYNTAX SM8TAT2SAQosPortPolicingEntry
    MAX-ACCESS not-accessible
    STATUS current
    DESCRIPTION
         "The Policer setting entry."
    INDEX { ifIndex }
    ::= { sm8tat2saQosPortPolicingTable 1 }

SM8TAT2SAQosPortPolicingEntry ::=
    SEQUENCE {
        sm8tat2saQosPortPolicingEnabled AdminMode,
        sm8tat2saQosPortPolicingRate Integer32
    }

sm8tat2saQosPortPolicingEnabled OBJECT-TYPE
    SYNTAX AdminMode
    MAX-ACCESS read-write
    STATUS current
    DESCRIPTION
        "Controls whether the policer is enabled on this switch port."
    DEFVAL { disable }
    ::= { sm8tat2saQosPortPolicingEntry 1 }

sm8tat2saQosPortPolicingRate OBJECT-TYPE
    SYNTAX Integer32(100..10000000)
    MAX-ACCESS read-write
    STATUS current
    DESCRIPTION
        "Controls the rate for the policer.
         range: 100-10000000(kbps/fps),
         default: 10000000(kbps)."
    ::= { sm8tat2saQosPortPolicingEntry 2 }

sm8tat2saQosQueueShaperTable OBJECT-TYPE
    SYNTAX SEQUENCE OF SM8TAT2SAQosQueueShaperEntry
    MAX-ACCESS not-accessible
    STATUS current
    DESCRIPTION
        "The table of QoS Queue Shaper"
    ::= { sm8tat2saQosPortShaper 1 }

sm8tat2saQosQueueShaperEntry OBJECT-TYPE
    SYNTAX SM8TAT2SAQosQueueShaperEntry
    MAX-ACCESS not-accessible
    STATUS current
    DESCRIPTION
        "The entry of QoS Queue Shaper"
    INDEX { ifIndex, sm8tat2saQosQueueShaperQueue }
    ::= { sm8tat2saQosQueueShaperTable 1 }

SM8TAT2SAQosQueueShaperEntry ::=
    SEQUENCE {
        sm8tat2saQosQueueShaperQueue Integer32,
        sm8tat2saQosQueueShaperEnabled AdminMode,
        sm8tat2saQosQueueShaperRate Integer32
    }

sm8tat2saQosQueueShaperQueue OBJECT-TYPE
    SYNTAX Integer32 (1..8)
    MAX-ACCESS not-accessible
    STATUS current
    DESCRIPTION
         "The index of QoS Queue Shaper"
    ::= { sm8tat2saQosQueueShaperEntry 1 }

sm8tat2saQosQueueShaperEnabled OBJECT-TYPE
    SYNTAX AdminMode
    MAX-ACCESS read-write
    STATUS current
    DESCRIPTION
        "Control whether QoS Queue Shaper is enabled."
    DEFVAL { disable }
    ::= { sm8tat2saQosQueueShaperEntry 2 }

sm8tat2saQosQueueShaperRate OBJECT-TYPE
    SYNTAX Integer32 (64..10000000)
    MAX-ACCESS read-write
    STATUS current
    DESCRIPTION
         " The rate of QoS Queue Shaper"
    ::= { sm8tat2saQosQueueShaperEntry 3 }

sm8tat2saQosPortShaperTable OBJECT-TYPE
    SYNTAX SEQUENCE OF SM8TAT2SAQosPortShaperEntry
    MAX-ACCESS not-accessible
    STATUS current
    DESCRIPTION
        "The table of QoS Port Shaper."
    ::= { sm8tat2saQosPortShaper 2 }

sm8tat2saQosPortShaperEntry OBJECT-TYPE
    SYNTAX SM8TAT2SAQosPortShaperEntry
    MAX-ACCESS not-accessible
    STATUS current
    DESCRIPTION
        "The entry of QoS Port Shaper"
    INDEX { ifIndex }
    ::= { sm8tat2saQosPortShaperTable 1 }

SM8TAT2SAQosPortShaperEntry ::=
    SEQUENCE {
        sm8tat2saQosPortShaperEnabled AdminMode,
        sm8tat2saQosPortShaperRate Integer32
    }

sm8tat2saQosPortShaperEnabled OBJECT-TYPE
    SYNTAX AdminMode
    MAX-ACCESS read-write
    STATUS current
    DESCRIPTION
        "Control whether QoS Port Shaper is enable."
    DEFVAL { disable }
    ::= { sm8tat2saQosPortShaperEntry 1 }

sm8tat2saQosPortShaperRate OBJECT-TYPE
    SYNTAX Integer32 (64..10000000)
    MAX-ACCESS read-write
    STATUS current
    DESCRIPTION
         "The rate of QoS Port Shaper"
    ::= { sm8tat2saQosPortShaperEntry 2 }

sm8tat2saQosStormControlTable OBJECT-TYPE
    SYNTAX SEQUENCE OF SM8TAT2SAQosStormControlEntry
    MAX-ACCESS not-accessible
    STATUS current
    DESCRIPTION
        "The basic QoS DSCP Translation settings for all switches."
    ::= { sm8tat2saQosStormControl 1 }

sm8tat2saQosStormControlEntry OBJECT-TYPE
    SYNTAX SM8TAT2SAQosStormControlEntry
    MAX-ACCESS not-accessible
    STATUS current
    DESCRIPTION
        "The Qos Storm Control Entry."
    INDEX { ifIndex }
    ::= { sm8tat2saQosStormControlTable 1 }

SM8TAT2SAQosStormControlEntry ::=
    SEQUENCE {
        sm8tat2saQosStormControlBroadcastEnabled AdminMode,
        sm8tat2saQosStormControlBraoadcastRate Integer32,
        sm8tat2saQosStormControlUnknownMulticastEnabled AdminMode,
        sm8tat2saQosStormControlUnknownMulticastRate Integer32,
        sm8tat2saQosStormControlUnknownUnicastEnabled AdminMode,
        sm8tat2saQosStormControlUnknownUnicastRate Integer32
    }

sm8tat2saQosStormControlBroadcastEnabled OBJECT-TYPE
    SYNTAX AdminMode
    MAX-ACCESS read-write
    STATUS current
    DESCRIPTION
        "Enable or disable the storm control status for the given frame type."
    DEFVAL { disable }
    ::= { sm8tat2saQosStormControlEntry 1 }

sm8tat2saQosStormControlBraoadcastRate OBJECT-TYPE
    SYNTAX Integer32
    MAX-ACCESS read-write
    STATUS current
    DESCRIPTION
        "The rate unit is packets per second (pps).
         default: 500(pps)."
    ::= { sm8tat2saQosStormControlEntry 2 }

sm8tat2saQosStormControlUnknownMulticastEnabled OBJECT-TYPE
    SYNTAX AdminMode
    MAX-ACCESS read-write
    STATUS current
    DESCRIPTION
        "Enable or disable the storm control status for the given frame type."
    DEFVAL { disable }
    ::= { sm8tat2saQosStormControlEntry 3 }

sm8tat2saQosStormControlUnknownMulticastRate OBJECT-TYPE
    SYNTAX Integer32
    MAX-ACCESS read-write
    STATUS current
    DESCRIPTION
        "The rate unit is packets per second (pps).
         default: 500(pps)."
    ::= { sm8tat2saQosStormControlEntry 4 }

sm8tat2saQosStormControlUnknownUnicastEnabled OBJECT-TYPE
    SYNTAX AdminMode
    MAX-ACCESS read-write
    STATUS current
    DESCRIPTION
        "Enable or disable the storm control status for the given frame type."
    DEFVAL { disable }
    ::= { sm8tat2saQosStormControlEntry 5 }

sm8tat2saQosStormControlUnknownUnicastRate OBJECT-TYPE
    SYNTAX Integer32
    MAX-ACCESS read-write
    STATUS current
    DESCRIPTION
        "The rate unit is packets per second (pps).
         default: 500(pps)."
    ::= { sm8tat2saQosStormControlEntry 6 }

sm8tat2saQosPortSchedulerTable OBJECT-TYPE
    SYNTAX SEQUENCE OF SM8TAT2SAQosPortSchedulerEntry
    MAX-ACCESS not-accessible
    STATUS current
    DESCRIPTION
        "The basic QoS Port Scheduler Mode settings.
         INDEX for this table is ifIndex which is
         equivalent to the panel port number."
    ::= { sm8tat2saQosPortScheduler 1 }

sm8tat2saQosPortSchedulerEntry OBJECT-TYPE
    SYNTAX SM8TAT2SAQosPortSchedulerEntry
    MAX-ACCESS not-accessible
    STATUS current
    DESCRIPTION
        "The Qos Port Scheduler Mode entry."
    INDEX { ifIndex, sm8tat2saQosSchedulerWeightIndex }
    ::= { sm8tat2saQosPortSchedulerTable 1 }

SM8TAT2SAQosPortSchedulerEntry ::=
    SEQUENCE {
        sm8tat2saQosSchedulerMode INTEGER,
        sm8tat2saQosSchedulerWeightIndex Integer32,
        sm8tat2saQosSchedulerWeight Integer32
    }

sm8tat2saQosSchedulerMode OBJECT-TYPE
    SYNTAX INTEGER { strictPriority(0), wrr(1), wfq(2) }
    MAX-ACCESS read-write
    STATUS current
    DESCRIPTION
        "Controls whether the scheduler mode is Strict Priority or Weighted on this switch port.
          0: Strict Priority,
          1: WRR,
          2: WFQ."
    DEFVAL { strictPriority }
    ::= { sm8tat2saQosPortSchedulerEntry 1 }

sm8tat2saQosSchedulerWeightIndex OBJECT-TYPE
     SYNTAX Integer32 (1..8)
     MAX-ACCESS not-accessible
     STATUS current
     DESCRIPTION
         "The index of Qos Scheduler Weight"
     ::= { sm8tat2saQosPortSchedulerEntry 2 }

sm8tat2saQosSchedulerWeight OBJECT-TYPE
     SYNTAX Integer32 (1..100)
     MAX-ACCESS read-write
     STATUS current
     DESCRIPTION
         "The weight of Qos Scheduler"
     ::= { sm8tat2saQosPortSchedulerEntry 3 }

sm8tat2saQosCoS8021pMappingTable OBJECT-TYPE
    SYNTAX SEQUENCE OF SM8TAT2SAQosCoS8021pMappingEntry
    MAX-ACCESS not-accessible
    STATUS current
    DESCRIPTION
        "The basic Qos CoS802.1p  Mapping settings for all switches."
    ::= { sm8tat2saQosCoS8021pMapping 1 }

sm8tat2saQosCoS8021pMappingEntry OBJECT-TYPE
    SYNTAX SM8TAT2SAQosCoS8021pMappingEntry
    MAX-ACCESS not-accessible
    STATUS current
    DESCRIPTION
        "The Qos CoS802.1p Mapping Entry."
    INDEX { sm8tat2saQosCoS8021pMappingCoS8021p }
    ::= { sm8tat2saQosCoS8021pMappingTable 1 }

SM8TAT2SAQosCoS8021pMappingEntry ::=
    SEQUENCE {
        sm8tat2saQosCoS8021pMappingCoS8021p Integer32,
        sm8tat2saQosCoS8021pMappingQueueID Integer32
    }

sm8tat2saQosCoS8021pMappingCoS8021p OBJECT-TYPE
    SYNTAX Integer32 (1..8)
    MAX-ACCESS not-accessible
    STATUS current
    DESCRIPTION
         "The index of QoS CoS802.1p Mapping"
    ::= { sm8tat2saQosCoS8021pMappingEntry 1 }

sm8tat2saQosCoS8021pMappingQueueID OBJECT-TYPE
    SYNTAX Integer32 (0..7)
    MAX-ACCESS read-write
    STATUS current
    DESCRIPTION
         "Queue ID of QoS CoS802.1p Mapping"
    ::= { sm8tat2saQosCoS8021pMappingEntry 2 }

sm8tat2saQosCoS8021pRemarkingTable OBJECT-TYPE
    SYNTAX SEQUENCE OF SM8TAT2SAQosCoS8021pRemarkingEntry
    MAX-ACCESS not-accessible
    STATUS current
    DESCRIPTION
        "The basic Qos CoS802.1p  Remarking settings for all switches."
    ::= { sm8tat2saQosCoS8021pRemarking 1 }

sm8tat2saQosCoS8021pRemarkingEntry OBJECT-TYPE
    SYNTAX SM8TAT2SAQosCoS8021pRemarkingEntry
    MAX-ACCESS not-accessible
    STATUS current
    DESCRIPTION
        "The Qos CoS802.1p Remarking Entry."
    INDEX { sm8tat2saQosCoS8021pRemarkingQueueID }
    ::= { sm8tat2saQosCoS8021pRemarkingTable 1 }

SM8TAT2SAQosCoS8021pRemarkingEntry ::=
    SEQUENCE {
        sm8tat2saQosCoS8021pRemarkingQueueID Integer32,
        sm8tat2saQosCoS8021pRemarkingCoS8021p Integer32
    }

sm8tat2saQosCoS8021pRemarkingQueueID OBJECT-TYPE
    SYNTAX Integer32 (1..8)
    MAX-ACCESS not-accessible
    STATUS current
    DESCRIPTION
         "The index of QoS CoS802.1p Remarking"
    ::= { sm8tat2saQosCoS8021pRemarkingEntry 1 }

sm8tat2saQosCoS8021pRemarkingCoS8021p OBJECT-TYPE
    SYNTAX Integer32(0..7)
    MAX-ACCESS read-write
    STATUS current
    DESCRIPTION
         "CoS802.1p of QoS CoS802.1p Remarking"
    ::= { sm8tat2saQosCoS8021pRemarkingEntry 2 }

sm8tat2saQosIPPrecedenceMappingTable OBJECT-TYPE
    SYNTAX SEQUENCE OF SM8TAT2SAQosIPPrecedenceMappingEntry
    MAX-ACCESS not-accessible
    STATUS current
    DESCRIPTION
        "The basic QoS IP Precedence Mapping settings for all switches."
    ::= { sm8tat2saQosIPPrecedenceMapping 1 }

sm8tat2saQosIPPrecedenceMappingEntry OBJECT-TYPE
    SYNTAX SM8TAT2SAQosIPPrecedenceMappingEntry
    MAX-ACCESS not-accessible
    STATUS current
    DESCRIPTION
        "The Qos IP Precedence Mapping Entry."
    INDEX { sm8tat2saQosIPPrecedenceMappingIPPrecedence }
    ::= { sm8tat2saQosIPPrecedenceMappingTable 1 }

SM8TAT2SAQosIPPrecedenceMappingEntry ::=
    SEQUENCE {
        sm8tat2saQosIPPrecedenceMappingIPPrecedence Integer32,
        sm8tat2saQosIPPrecedenceMappingQueueID Integer32
    }

sm8tat2saQosIPPrecedenceMappingIPPrecedence OBJECT-TYPE
    SYNTAX Integer32 (1..8)
    MAX-ACCESS not-accessible
    STATUS current
    DESCRIPTION
         "The index of QoS IP Precedence"
    ::= { sm8tat2saQosIPPrecedenceMappingEntry 1 }

sm8tat2saQosIPPrecedenceMappingQueueID OBJECT-TYPE
    SYNTAX Integer32 (0..7)
    MAX-ACCESS read-write
    STATUS current
    DESCRIPTION
         "Queue ID of QoS IP Precedence"
    ::= { sm8tat2saQosIPPrecedenceMappingEntry 2 }

sm8tat2saQosIPPrecedenceRemarkingTable OBJECT-TYPE
    SYNTAX SEQUENCE OF SM8TAT2SAQosIPPrecedenceRemarkingEntry
    MAX-ACCESS not-accessible
    STATUS current
    DESCRIPTION
        "The basic QoS IP Precedence Remarking settings for all switches."
    ::= { sm8tat2saQosIPPrecedenceRemarking 1 }

sm8tat2saQosIPPrecedenceRemarkingEntry OBJECT-TYPE
    SYNTAX SM8TAT2SAQosIPPrecedenceRemarkingEntry
    MAX-ACCESS not-accessible
    STATUS current
    DESCRIPTION
        "The Qos IP Precedence Remarking Entry."
    INDEX { sm8tat2saQosIPPrecedenceRemarkingQueueID }
    ::= { sm8tat2saQosIPPrecedenceRemarkingTable 1 }

SM8TAT2SAQosIPPrecedenceRemarkingEntry ::=
    SEQUENCE {
        sm8tat2saQosIPPrecedenceRemarkingQueueID Integer32,
        sm8tat2saQosIPPrecedenceRemarkingIPPrecedence Integer32
    }

sm8tat2saQosIPPrecedenceRemarkingQueueID OBJECT-TYPE
    SYNTAX Integer32 (1..8)
    MAX-ACCESS not-accessible
    STATUS current
    DESCRIPTION
         "The index of QoS IP Predence Remarking"
    ::= { sm8tat2saQosIPPrecedenceRemarkingEntry 1 }

sm8tat2saQosIPPrecedenceRemarkingIPPrecedence OBJECT-TYPE
    SYNTAX Integer32 (0..7)
    MAX-ACCESS read-write
    STATUS current
    DESCRIPTION
         "IP Precedence of QoS IP Precedence Remarking"
    ::= { sm8tat2saQosIPPrecedenceRemarkingEntry 2 }

sm8tat2saQosDSCPMappingTable OBJECT-TYPE
    SYNTAX SEQUENCE OF SM8TAT2SAQosDSCPMappingEntry
    MAX-ACCESS not-accessible
    STATUS current
    DESCRIPTION
        "The basic QoS DSCP Mapping settings for all switches."
    ::= { sm8tat2saQosDSCPMapping 1 }

sm8tat2saQosDSCPMappingEntry OBJECT-TYPE
    SYNTAX SM8TAT2SAQosDSCPMappingEntry
    MAX-ACCESS not-accessible
    STATUS current
    DESCRIPTION
        "The Qos DSCP Mapping Entry."
    INDEX { sm8tat2saQosDSCPMappingDSCPBasedId }
    ::= { sm8tat2saQosDSCPMappingTable 1 }

SM8TAT2SAQosDSCPMappingEntry ::=
    SEQUENCE {
        sm8tat2saQosDSCPMappingDSCPBasedId Integer32,
        sm8tat2saQosDSCPMappingQueueID Integer32
    }

sm8tat2saQosDSCPMappingDSCPBasedId OBJECT-TYPE
    SYNTAX Integer32 (1..64)
    MAX-ACCESS not-accessible
    STATUS current
    DESCRIPTION
         "The index of QoS DSCP Mapping"
    ::= { sm8tat2saQosDSCPMappingEntry 1 }

sm8tat2saQosDSCPMappingQueueID OBJECT-TYPE
    SYNTAX Integer32 (0..7)
    MAX-ACCESS read-write
    STATUS current
    DESCRIPTION
        "Queue ID of QoS DSCP Mapping"
    ::= { sm8tat2saQosDSCPMappingEntry 2 }

sm8tat2saQosDSCPRemarkingTable OBJECT-TYPE
    SYNTAX SEQUENCE OF SM8TAT2SAQosDSCPRemarkingEntry
    MAX-ACCESS not-accessible
    STATUS current
    DESCRIPTION
        "The basic QoS DSCP Remarking settings for all switches."
    ::= { sm8tat2saQosDSCPRemarking 1 }

sm8tat2saQosDSCPRemarkingEntry OBJECT-TYPE
    SYNTAX SM8TAT2SAQosDSCPRemarkingEntry
    MAX-ACCESS not-accessible
    STATUS current
    DESCRIPTION
        "The Qos DSCP Remarking Entry."
    INDEX { sm8tat2saQosDSCPRemarkingQueueID }
    ::= { sm8tat2saQosDSCPRemarkingTable 1 }

SM8TAT2SAQosDSCPRemarkingEntry ::=
    SEQUENCE {
        sm8tat2saQosDSCPRemarkingQueueID Integer32,
        sm8tat2saQosDSCPRemarkingDSCP Integer32
    }

sm8tat2saQosDSCPRemarkingQueueID OBJECT-TYPE
    SYNTAX Integer32 (1..8)
    MAX-ACCESS not-accessible
    STATUS current
    DESCRIPTION
         "The index of QoS DSCP Remarking"
    ::= { sm8tat2saQosDSCPRemarkingEntry 1 }

sm8tat2saQosDSCPRemarkingDSCP OBJECT-TYPE
    SYNTAX Integer32 (0..63)
    MAX-ACCESS read-write
    STATUS current
    DESCRIPTION
        "DSCP of QoS DSCP Remarking"
    ::= { sm8tat2saQosDSCPRemarkingEntry 2 }

-- *************************************************************
-- Start sm8tat2saLoopProtection group
-- *************************************************************
sm8tat2saLoopProtection OBJECT IDENTIFIER ::= { sm8tat2saConfiguration 12 }

sm8tat2saLoopProtectionConfig OBJECT IDENTIFIER ::= { sm8tat2saLoopProtection 1 }

sm8tat2saLoopProtectionGlobalEnable OBJECT-TYPE
   SYNTAX INTEGER { disable(0), enable(1) }
   MAX-ACCESS read-write
   STATUS current
   DESCRIPTION
       "Configure loop protection mode.
        0: disable,
        1: enable. "
   ::= { sm8tat2saLoopProtectionConfig 1 }

sm8tat2saLoopProtectionTranmisstionTime OBJECT-TYPE
   SYNTAX Integer32(1..10)
   MAX-ACCESS read-write
   STATUS current
   DESCRIPTION
       "Configure loop protection transmit interval.
        range: 1-10. "
   ::= { sm8tat2saLoopProtectionConfig 2 }

sm8tat2saLoopProtectionShutdownTime OBJECT-TYPE
   SYNTAX Integer32(10..604800)
   MAX-ACCESS read-write
   STATUS current
   DESCRIPTION
       "Configure loop protection shutdown time.
        range: 10-604800. "
   ::= { sm8tat2saLoopProtectionConfig 3 }

sm8tat2saLoopProtectionConfigurationTable OBJECT-TYPE
   SYNTAX SEQUENCE OF SM8TAT2SALoopProtectionConfigurationEntry
   MAX-ACCESS not-accessible
   STATUS current
   DESCRIPTION
       " Show Loop Protection configurations. "
   ::= { sm8tat2saLoopProtectionConfig 4 }

sm8tat2saLoopProtectionConfigurationEntry OBJECT-TYPE
   SYNTAX SM8TAT2SALoopProtectionConfigurationEntry
   MAX-ACCESS not-accessible
   STATUS current
   DESCRIPTION
       " "
   INDEX { sm8tat2saLoopProtectionConfPort }
   ::= { sm8tat2saLoopProtectionConfigurationTable 1 }

SM8TAT2SALoopProtectionConfigurationEntry ::= SEQUENCE {
   sm8tat2saLoopProtectionConfPort Integer32,
   sm8tat2saLoopProtectionConfEnable INTEGER,
   sm8tat2saLoopProtectionConfAction INTEGER,
   sm8tat2saLoopProtectionConfTxmode INTEGER
}

sm8tat2saLoopProtectionConfPort OBJECT-TYPE
   SYNTAX Integer32(1..255)
   MAX-ACCESS not-accessible
   STATUS current
   DESCRIPTION
       " port, range : 1 - port number. "
   ::= { sm8tat2saLoopProtectionConfigurationEntry 1 }

sm8tat2saLoopProtectionConfEnable OBJECT-TYPE
   SYNTAX INTEGER { disable(0), enable(1) }
   MAX-ACCESS read-write
   STATUS current
   DESCRIPTION
       " Configure loop protection port mode.
         0: disable,
         1: enable. "
   ::= { sm8tat2saLoopProtectionConfigurationEntry 2 }

sm8tat2saLoopProtectionConfAction OBJECT-TYPE
   SYNTAX INTEGER { shutdown(0), shutdownLog(1), log(2) }
   MAX-ACCESS read-write
   STATUS current
   DESCRIPTION
       " Configure loop protection port action.
         0: Shutdown port,
         1: Shutdown port and Log,
         2: Log Only. "
   ::= { sm8tat2saLoopProtectionConfigurationEntry 3 }

sm8tat2saLoopProtectionConfTxmode OBJECT-TYPE
   SYNTAX INTEGER { disable(0), enable(1) }
   MAX-ACCESS read-write
   STATUS current
   DESCRIPTION
       " Configure loop protection port transmit mode.
         0: disable,
         1: enable. "
   ::= { sm8tat2saLoopProtectionConfigurationEntry 4 }

sm8tat2saLoopProtectionStatusTable OBJECT-TYPE
   SYNTAX SEQUENCE OF SM8TAT2SALoopProtectionStatusEntry
   MAX-ACCESS not-accessible
   STATUS current
   DESCRIPTION
       " Show Loop Protection Status. "
   ::= { sm8tat2saLoopProtection 2 }

sm8tat2saLoopProtectionStatusEntry OBJECT-TYPE
   SYNTAX SM8TAT2SALoopProtectionStatusEntry
   MAX-ACCESS not-accessible
   STATUS current
   DESCRIPTION
       " "
   INDEX { sm8tat2saLoopProtectionStatusPort }
   ::= { sm8tat2saLoopProtectionStatusTable 1 }

SM8TAT2SALoopProtectionStatusEntry ::= SEQUENCE {
   sm8tat2saLoopProtectionStatusPort Integer32,
   sm8tat2saLoopProtectionStatusLoops Counter32,
   sm8tat2saLoopProtectionStatusStatus DisplayString,
   sm8tat2saLoopProtectionStatusLoop DisplayString,
   sm8tat2saLoopProtectionStatusTimeLastLoop DisplayString
}

sm8tat2saLoopProtectionStatusPort OBJECT-TYPE
   SYNTAX Integer32(1..255)
   MAX-ACCESS not-accessible
   STATUS current
   DESCRIPTION
       " port, range : 1 - port number. "
   ::= { sm8tat2saLoopProtectionStatusEntry 1 }

sm8tat2saLoopProtectionStatusLoops OBJECT-TYPE
   SYNTAX Counter32
   MAX-ACCESS read-only
   STATUS current
   DESCRIPTION
       " The number of loops detected on this port. "
   ::= { sm8tat2saLoopProtectionStatusEntry 2 }

sm8tat2saLoopProtectionStatusStatus OBJECT-TYPE
   SYNTAX DisplayString
   MAX-ACCESS read-only
   STATUS current
   DESCRIPTION
       " The current loop protection status of the port. "
   ::= { sm8tat2saLoopProtectionStatusEntry 3 }

sm8tat2saLoopProtectionStatusLoop OBJECT-TYPE
   SYNTAX DisplayString
   MAX-ACCESS read-only
   STATUS current
   DESCRIPTION
       " Whether a loop is currently detected on the port. "
   ::= { sm8tat2saLoopProtectionStatusEntry 4 }

sm8tat2saLoopProtectionStatusTimeLastLoop OBJECT-TYPE
   SYNTAX DisplayString
   MAX-ACCESS read-only
   STATUS current
   DESCRIPTION
       " The time of the last loop event detected. "
   ::= { sm8tat2saLoopProtectionStatusEntry 5 }

-- *************************************************************
-- Start sm8tat2saPoe group
-- *************************************************************
sm8tat2saPoe OBJECT IDENTIFIER ::= { sm8tat2saConfiguration 13 }

sm8tat2saPoeConfiguration OBJECT IDENTIFIER ::= { sm8tat2saPoe 1 }

sm8tat2saPrimaryPowerSupply OBJECT-TYPE
   SYNTAX Integer32 (0..2000)
   MAX-ACCESS read-only
   STATUS current
   DESCRIPTION
       "It must be defined what amount of power the primary and backup power sources can deliver. "
   ::= { sm8tat2saPoeConfiguration 1 }

sm8tat2saCapacitorDetection OBJECT-TYPE
   SYNTAX AdminMode
   MAX-ACCESS read-write
   STATUS current
   DESCRIPTION
       "The Detection represents the PoE capacitor detection.
         0: disable(default), 1: enable. "
   ::= { sm8tat2saPoeConfiguration 2 }

sm8tat2saPoePortConfigTable OBJECT-TYPE
   SYNTAX SEQUENCE OF SM8TAT2SAPoePortConfigEntry
   MAX-ACCESS not-accessible
   STATUS current
   DESCRIPTION
       "The table of the PoE Port Configuration. "
   ::= { sm8tat2saPoeConfiguration 3 }

sm8tat2saPoePortConfigEntry OBJECT-TYPE
   SYNTAX SM8TAT2SAPoePortConfigEntry
   MAX-ACCESS not-accessible
   STATUS current
   DESCRIPTION
       "The entry of the PoE Port Configuration. "
   INDEX { ifIndex }
   ::= { sm8tat2saPoePortConfigTable 1 }

SM8TAT2SAPoePortConfigEntry ::=
SEQUENCE {
   sm8tat2saPoePortConfigPoeMode INTEGER,
   sm8tat2saPoePortConfigPoeSchedule Integer32,
   sm8tat2saPoePortConfigPriority INTEGER,
   sm8tat2saPoePortConfigMaximumPower Integer32
}

sm8tat2saPoePortConfigPoeMode OBJECT-TYPE

   SYNTAX INTEGER {disable(0), enable(2), force(3)}

   MAX-ACCESS read-write
   STATUS current
   DESCRIPTION

       "The PoE Mode represents the PoE operating mode for the port.
         0: disable, 2: enable(default), 3: force."

   ::= { sm8tat2saPoePortConfigEntry 1 }

sm8tat2saPoePortConfigPoeSchedule OBJECT-TYPE
   SYNTAX Integer32 (-1..16)
   MAX-ACCESS read-write
   STATUS current
   DESCRIPTION
       "Specify a valid PoE schedule profile by profile id. -1: disable(default), 0-15: profile 1~16. "
   ::= { sm8tat2saPoePortConfigEntry 2 }

sm8tat2saPoePortConfigPriority OBJECT-TYPE
   SYNTAX INTEGER {low(0), high(1), critical(2)}
   MAX-ACCESS read-write
   STATUS current
   DESCRIPTION
       "The Priority represents the ports priority. There are three levels of power priority named Low, High and Critical.
         0: Low(default), 1: High, 2: Critical. "
   ::= { sm8tat2saPoePortConfigEntry 3 }

sm8tat2saPoePortConfigMaximumPower OBJECT-TYPE
   SYNTAX Integer32 (1..30)
   MAX-ACCESS read-write
   STATUS current
   DESCRIPTION
       "The Maximum Power value contains a numerical value that indicates the maximum power in watts that can be delivered to a remote device.
         default: 30"
   ::= { sm8tat2saPoePortConfigEntry 4 }
sm8tat2saPoEManagementMode OBJECT-TYPE
   SYNTAX INTEGER {classConsump(1), allocatedConsump(3), lldpmedConsump(5)}
   MAX-ACCESS read-write
   STATUS current
   DESCRIPTION
       "The power management mode for PoE port.
        1: Class consumption,
        3: Allocated consumption,
        5: LLDP-Med consumption. "
   ::= { sm8tat2saPoeConfiguration 5 }

sm8tat2saPoEAlwaysOnPoE OBJECT-TYPE

   SYNTAX ActivateCmd
   MAX-ACCESS read-write
   STATUS current
   DESCRIPTION
       "When the switch restart, it will retain PoE sourcing."
   ::= { sm8tat2saPoeConfiguration 8 }

sm8tat2saPoeStatus OBJECT IDENTIFIER ::= { sm8tat2saPoe 2 }

sm8tat2saPoeStatusTable OBJECT-TYPE
   SYNTAX SEQUENCE OF SM8TAT2SAPoeStatusEntry
   MAX-ACCESS not-accessible
   STATUS current
   DESCRIPTION
       "Configure PoE Scheduling Table. "
   ::= { sm8tat2saPoeStatus 1 }

sm8tat2saPoeStatusEntry OBJECT-TYPE
   SYNTAX SM8TAT2SAPoeStatusEntry
   MAX-ACCESS not-accessible
   STATUS current
   DESCRIPTION
       " "
   INDEX { ifIndex }
   ::= { sm8tat2saPoeStatusTable 1 }

SM8TAT2SAPoeStatusEntry ::= SEQUENCE {
   sm8tat2saPoeStatusPDClass DisplayString,
   sm8tat2saPoeStatusPowerAllocated DisplayString,
   sm8tat2saPoeStatusPowerUsed DisplayString,
   sm8tat2saPoeStatusCurrentUsed DisplayString,
   sm8tat2saPoeStatusPriority DisplayString,
   sm8tat2saPoeStatusPortStatus DisplayString
}

sm8tat2saPoeStatusPDClass OBJECT-TYPE
   SYNTAX DisplayString
   MAX-ACCESS read-only
   STATUS current
   DESCRIPTION
       "Indicates the QCL user."
   ::= { sm8tat2saPoeStatusEntry 1 }

sm8tat2saPoeStatusPowerAllocated OBJECT-TYPE
   SYNTAX DisplayString
   MAX-ACCESS read-only
   STATUS current
   DESCRIPTION
      "The Power Allocated shows the amount of power the switch has allocated for the PD."
   ::= { sm8tat2saPoeStatusEntry 2 }

sm8tat2saPoeStatusPowerUsed OBJECT-TYPE
   SYNTAX DisplayString
   MAX-ACCESS read-only
   STATUS current
   DESCRIPTION
      "The Power Used shows how much power the PD currently is using. "
   ::= { sm8tat2saPoeStatusEntry 3 }

sm8tat2saPoeStatusCurrentUsed OBJECT-TYPE
   SYNTAX DisplayString
   MAX-ACCESS read-only
   STATUS current
   DESCRIPTION
      "The Power Used shows how much current the PD currently is using. "
   ::= { sm8tat2saPoeStatusEntry 4 }

sm8tat2saPoeStatusPriority OBJECT-TYPE
   SYNTAX DisplayString
   MAX-ACCESS read-only
   STATUS current
   DESCRIPTION
      "The Priority shows the port's priority configured by the user. "
   ::= { sm8tat2saPoeStatusEntry 5 }

sm8tat2saPoeStatusPortStatus OBJECT-TYPE
   SYNTAX DisplayString
   MAX-ACCESS read-only
   STATUS current
   DESCRIPTION
      "The Port Status shows the port's status. "
   ::= { sm8tat2saPoeStatusEntry 6 }

sm8tat2saPoePowerDelay OBJECT IDENTIFIER ::= { sm8tat2saPoe 3 }

sm8tat2saPoePowerDelayTable OBJECT-TYPE
   SYNTAX SEQUENCE OF SM8TAT2SAPoePowerDelayEntry
   MAX-ACCESS not-accessible
   STATUS current
   DESCRIPTION
       "Configure PoE Power Delay mode. "
   ::= { sm8tat2saPoePowerDelay 1 }

sm8tat2saPoePowerDelayEntry OBJECT-TYPE
   SYNTAX SM8TAT2SAPoePowerDelayEntry
   MAX-ACCESS not-accessible
   STATUS current
   DESCRIPTION
       " "
   INDEX { ifIndex }
   ::= { sm8tat2saPoePowerDelayTable 1 }

SM8TAT2SAPoePowerDelayEntry ::=
SEQUENCE {
   sm8tat2saPoePowerDelayMode AdminMode,
   sm8tat2saPoePowerDelayTime Integer32
}

sm8tat2saPoePowerDelayMode OBJECT-TYPE
   SYNTAX AdminMode
   MAX-ACCESS read-write
   STATUS current
   DESCRIPTION
       "Turn on / off the power delay function,
         0: disable(default), 1: enable. "
   ::= { sm8tat2saPoePowerDelayEntry 1 }

sm8tat2saPoePowerDelayTime OBJECT-TYPE
   SYNTAX Integer32 (0..300)
   MAX-ACCESS read-write
   STATUS current
   DESCRIPTION
       "set Delay Time,
         default: 0,
         range: 0-300 sec. "
   ::= { sm8tat2saPoePowerDelayEntry 2 }

sm8tat2saPoeAutoCheck OBJECT IDENTIFIER ::= { sm8tat2saPoe 4 }

sm8tat2saPoeAutoCheckPingCheck OBJECT-TYPE
   SYNTAX INTEGER {off(0), on(1)}
   MAX-ACCESS read-write
   STATUS current
   DESCRIPTION
       "connection between PoE port and power device.
         0: off(default), 1: on. "
   ::= { sm8tat2saPoeAutoCheck 1 }

sm8tat2saPoeAutoCheckTable OBJECT-TYPE
   SYNTAX SEQUENCE OF SM8TAT2SAPoeAutoCheckEntry
   MAX-ACCESS not-accessible
   STATUS current
   DESCRIPTION
       " Configure PoE Auto check mode. "
   ::= { sm8tat2saPoeAutoCheck 2 }

sm8tat2saPoeAutoCheckEntry OBJECT-TYPE
   SYNTAX SM8TAT2SAPoeAutoCheckEntry
   MAX-ACCESS not-accessible
   STATUS current
   DESCRIPTION
       " "
   INDEX { ifIndex }
   ::= { sm8tat2saPoeAutoCheckTable 1 }

SM8TAT2SAPoeAutoCheckEntry ::=
SEQUENCE {
   sm8tat2saPoeAutoCheckPingIPAddress DisplayString,
   sm8tat2saPoeAutoCheckStartupTime Integer32,
   sm8tat2saPoeAutoCheckIntervalTime Integer32,
   sm8tat2saPoeAutoCheckRetryTime Integer32,
   sm8tat2saPoeAutoCheckFailureLog DisplayString,
   sm8tat2saPoeAutoCheckFailureAction INTEGER,
   sm8tat2saPoeAutoCheckRebootTime Integer32,
   sm8tat2saPoeAutoCheckMaxRebootTimes Integer32
}

sm8tat2saPoeAutoCheckPingIPAddress OBJECT-TYPE
   SYNTAX DisplayString
   MAX-ACCESS read-write
   STATUS current
   DESCRIPTION
       "IP Address the system should ping.
         default: 0.0.0.0 . "
   ::= { sm8tat2saPoeAutoCheckEntry 1 }

sm8tat2saPoeAutoCheckStartupTime OBJECT-TYPE
   SYNTAX Integer32 (30..600)
   MAX-ACCESS read-write
   STATUS current
   DESCRIPTION
       "When PD has been start up, the Switch will wait Start up time to do PoE Auto Checking.
         default: 60, range: 30-600 sec. "
   ::= { sm8tat2saPoeAutoCheckEntry 2 }

sm8tat2saPoeAutoCheckIntervalTime OBJECT-TYPE
   SYNTAX Integer32 (10..120)
   MAX-ACCESS read-write
   STATUS current
   DESCRIPTION
       "Device will send checking message to PD each interval time.
         default: 30, range: 10-120 sec. "
   ::= { sm8tat2saPoeAutoCheckEntry 3 }

sm8tat2saPoeAutoCheckRetryTime OBJECT-TYPE
   SYNTAX Integer32 (1..5)
   MAX-ACCESS read-write
   STATUS current
   DESCRIPTION
       "It will retry to send detection again.
         default: 3, range: 1-5. "
   ::= { sm8tat2saPoeAutoCheckEntry 4 }

sm8tat2saPoeAutoCheckFailureLog OBJECT-TYPE
   SYNTAX DisplayString
   MAX-ACCESS read-only
   STATUS current
   DESCRIPTION
       "Failure loggings counter. "
   ::= { sm8tat2saPoeAutoCheckEntry 5 }

sm8tat2saPoeAutoCheckFailureAction OBJECT-TYPE
   SYNTAX INTEGER {nothing(0), reboot(1)}
   MAX-ACCESS read-write
   STATUS current
   DESCRIPTION
       "It will retry to send detection again,
         0: Nothing(default), 1: Reboot Remote PD. "
   ::= { sm8tat2saPoeAutoCheckEntry 6 }

sm8tat2saPoeAutoCheckRebootTime OBJECT-TYPE
   SYNTAX Integer32 (3..120)
   MAX-ACCESS read-write
   STATUS current
   DESCRIPTION
       "When PD has been rebooted, the PoE port restored power after the specified time.
         default: 15, range: 3-120 sec. "
   ::= { sm8tat2saPoeAutoCheckEntry 7 }

sm8tat2saPoeAutoCheckMaxRebootTimes OBJECT-TYPE
   SYNTAX Integer32 (0..10)
   MAX-ACCESS read-write
   STATUS current
   DESCRIPTION
       "When action happen reboot times over max reboot times,
       auto checking will stop on this port until user change
       PoE mode without disable in PoE configurtion.
       If max reboot times is 0, auto checking will not stop.
       Default: 0, range: 0-10 times."
   ::= { sm8tat2saPoeAutoCheckEntry 8 }

sm8tat2saPoeSchedulingProfile OBJECT IDENTIFIER ::= { sm8tat2saPoe 5 }

sm8tat2saPoeSchedulingNameTable OBJECT-TYPE
   SYNTAX SEQUENCE OF SM8TAT2SAPoeSchedulingNameEntry
   MAX-ACCESS not-accessible
   STATUS current
   DESCRIPTION
       " Show Poe Scheduling Name Config. "
   ::= { sm8tat2saPoeSchedulingProfile 1 }

sm8tat2saPoeSchedulingNameEntry OBJECT-TYPE
   SYNTAX SM8TAT2SAPoeSchedulingNameEntry
   MAX-ACCESS not-accessible
   STATUS current
   DESCRIPTION
       " "
   INDEX { sm8tat2saPoeSchedulingNumberIndex }
   ::= { sm8tat2saPoeSchedulingNameTable 1 }

SM8TAT2SAPoeSchedulingNameEntry ::=
SEQUENCE {
   sm8tat2saPoeSchedulingNumberIndex Integer32,
   sm8tat2saPoeSchedulingName DisplayString
}

sm8tat2saPoeSchedulingNumberIndex OBJECT-TYPE
   SYNTAX Integer32 (1..16)
   MAX-ACCESS not-accessible
   STATUS current
   DESCRIPTION
       "The index of the PoE Profile Number. number 1~16 "
   ::= { sm8tat2saPoeSchedulingNameEntry 1 }

sm8tat2saPoeSchedulingName OBJECT-TYPE
   SYNTAX DisplayString
   MAX-ACCESS read-write
   STATUS current
   DESCRIPTION
       "Profile Name. maximum length:32. profile 1~16"
   ::= { sm8tat2saPoeSchedulingNameEntry 2 }

sm8tat2saPoeSchedulingTimeTable OBJECT-TYPE
   SYNTAX SEQUENCE OF SM8TAT2SAPoeSchedulingTimeEntry
   MAX-ACCESS not-accessible
   STATUS current
   DESCRIPTION
       " Show Poe Scheduling Time Config. "
   ::= { sm8tat2saPoeSchedulingProfile 2 }

sm8tat2saPoeSchedulingTimeEntry OBJECT-TYPE
   SYNTAX SM8TAT2SAPoeSchedulingTimeEntry
   MAX-ACCESS not-accessible
   STATUS current
   DESCRIPTION
       " "
   INDEX { sm8tat2saPoeSchedulingNumberIndex, sm8tat2saPoeSchedulingTimeWeekIndex }
   ::= { sm8tat2saPoeSchedulingTimeTable 1 }

SM8TAT2SAPoeSchedulingTimeEntry ::=
SEQUENCE {
   sm8tat2saPoeSchedulingTimeWeekIndex Integer32,
   sm8tat2saPoeSchedulingTimeStartTimeHour Integer32,
   sm8tat2saPoeSchedulingTimeStartTimeMinute Integer32,
   sm8tat2saPoeSchedulingTimeEndTimeHour Integer32,
   sm8tat2saPoeSchedulingTimeEndTimeMinute Integer32
}

sm8tat2saPoeSchedulingTimeWeekIndex OBJECT-TYPE
   SYNTAX Integer32 (1..7)
   MAX-ACCESS not-accessible
   STATUS current
   DESCRIPTION
       "Week Index.
     1: Mon, 2:Tue, 3: Wed, 4: Thu, 5: Fri, 6: Sat, 7: Sun "
   ::= { sm8tat2saPoeSchedulingTimeEntry 1 }

sm8tat2saPoeSchedulingTimeStartTimeHour OBJECT-TYPE
   SYNTAX Integer32
   MAX-ACCESS read-write
   STATUS current
   DESCRIPTION
       "PoE Scheduling Start Hour. Range: 0-23. "
   ::= { sm8tat2saPoeSchedulingTimeEntry 2 }

sm8tat2saPoeSchedulingTimeStartTimeMinute OBJECT-TYPE
   SYNTAX Integer32
   MAX-ACCESS read-write
   STATUS current
   DESCRIPTION
       "PoE Scheduling Start Minute. Range:0,5,10,...,55. "
   ::= { sm8tat2saPoeSchedulingTimeEntry 3 }

sm8tat2saPoeSchedulingTimeEndTimeHour OBJECT-TYPE
   SYNTAX Integer32
   MAX-ACCESS read-write
   STATUS current
   DESCRIPTION
       "PoE Scheduling End Hour. Range: 0-23. "
   ::= { sm8tat2saPoeSchedulingTimeEntry 4 }

sm8tat2saPoeSchedulingTimeEndTimeMinute OBJECT-TYPE
   SYNTAX Integer32
   MAX-ACCESS read-write
   STATUS current
   DESCRIPTION
       "PoE Scheduling End Minute. Range:0,5,10,...,55. "
   ::= { sm8tat2saPoeSchedulingTimeEntry 5 }

-- *************************************************************
-- Start sm8tat2saMstp group
-- *************************************************************
sm8tat2saMstpGroup OBJECT IDENTIFIER ::= { sm8tat2saConfiguration 18 }

sm8tat2saMstpMiscellaneousConfig OBJECT IDENTIFIER ::= { sm8tat2saMstpGroup 1 }

sm8tat2saMstpMibGlobalEnable OBJECT-TYPE
   SYNTAX INTEGER { disable(0), enable(1) }
   MAX-ACCESS read-write
   STATUS current
   DESCRIPTION
       "This variable is used to start or stop the spanning tree protocol.
        0: disable,
        1: enable. "
   ::= { sm8tat2saMstpMiscellaneousConfig 1 }

sm8tat2saMstpMstiAddVlans OBJECT-TYPE
   SYNTAX DisplayString (SIZE (0..200))
   MAX-ACCESS read-write
   STATUS current
   DESCRIPTION
       "This DisplayString represents a vid list to be mapped to an MSTI instance.
        ieee8021MstpRowStatus in the ieee8021MstpTable of IEEE8021-MSTP-MIB is used
        to add a new MSTI instance. Only legal VID numbers (1-4094) are allowed.
        Consecutive VIDs can be represented as for example 31-40(Between Vlan 31 and 40 is hyphen).
        The other legal symbol is comma.
        for example: 1,3,4,5,31-40,4094 "
   ::= { sm8tat2saMstpMiscellaneousConfig 2 }

-- *************************************************************
-- Start sm8tat2saLinkAggregation group
-- *************************************************************
sm8tat2saLinkAggregationGroup OBJECT IDENTIFIER ::= { sm8tat2saConfiguration 23 }

sm8tat2saLagMiscellaneousConfig OBJECT IDENTIFIER ::= { sm8tat2saLinkAggregationGroup 1 }

sm8tat2saLagTrafficDistributionMode OBJECT-TYPE
   SYNTAX INTEGER { srcmac(1), dstmac(2), srcdstmac(3),srcip(4), dstip(5), srcdstip(6) }
   MAX-ACCESS read-write
   STATUS current
   DESCRIPTION
       "This variable is used to specify the port selection hash algorithm
       for traffic distribution."
   ::= { sm8tat2saLagMiscellaneousConfig 1 }

sm8tat2saLagLacpSystemPriority OBJECT-TYPE
   SYNTAX Integer32 (1..65535)
   MAX-ACCESS read-write
   STATUS current
   DESCRIPTION
        "A 2-octet read-write value indicating the priority value
        associated with the Actor's System ID."
   ::= { sm8tat2saLagMiscellaneousConfig 2 }

sm8tat2saLagPortTable OBJECT-TYPE
    SYNTAX SEQUENCE OF SM8TAT2SALagPortEntry
    MAX-ACCESS not-accessible
    STATUS current
    DESCRIPTION
        "A table that contains Link Aggregation Control
        configuration information about every
        Aggregation Port associated with this device.
        A row appears in this table for each physical port."
    ::= { sm8tat2saLinkAggregationGroup 2 }

sm8tat2saLagPortEntry OBJECT-TYPE
    SYNTAX SM8TAT2SALagPortEntry
    MAX-ACCESS not-accessible
    STATUS current
    DESCRIPTION
        "A list of Link Aggregation Control configuration
        parameters for each Aggregation Port on this device."
    INDEX { sm8tat2saLagPortIndex }
    ::= { sm8tat2saLagPortTable 1 }

SM8TAT2SALagPortEntry ::=
    SEQUENCE {
        sm8tat2saLagPortIndex Integer32,
        sm8tat2saLagPortLacpAggAdminKey Integer32,
        sm8tat2saLagPortStaticAggAdminKey Integer32,
        sm8tat2saLagPortLacpActivity INTEGER,
        sm8tat2saLagPortLacpTimeout INTEGER,
        sm8tat2saLagPortAggregatorPort Integer32,
        sm8tat2saLagPortReadyState INTEGER
    }

sm8tat2saLagPortIndex OBJECT-TYPE
    SYNTAX Integer32 (1..52)
    MAX-ACCESS not-accessible
    STATUS current
    DESCRIPTION
        "The switch port number"
    ::= { sm8tat2saLagPortEntry 1 }

sm8tat2saLagPortLacpAggAdminKey OBJECT-TYPE
    SYNTAX Integer32 (0..8)
    MAX-ACCESS read-write
    STATUS current
    DESCRIPTION
        "The current administrative value of the Key for a LACP aggregation port.
        A non-zero value will force the port to participate in a LACP aggregation
        group and force the value of LagPortStaticAggAdminKey to be 0.
        A zero value setting will let the port turn to be an Individual port and
        force the value of LagPortStaticAggAdminKey to be 0 at the same time."
    ::= { sm8tat2saLagPortEntry 2 }

sm8tat2saLagPortStaticAggAdminKey OBJECT-TYPE
    SYNTAX Integer32 (0..8)
    MAX-ACCESS read-write
    STATUS current
    DESCRIPTION
        "The current administrative value of the key for a Static aggregation port.
        A non-zero value will force the port to participate in a Static aggregation
        group and force the value of LagPortLacpAggAdminKey to be 0.
        A zero value setting will let the port turn to be an Individual port and
        force the value of LagPortLacpAggAdminKey to be 0 at the same time."
    ::= { sm8tat2saLagPortEntry 3 }

sm8tat2saLagPortLacpActivity OBJECT-TYPE
    SYNTAX INTEGER { passive(0), active(1)}
    MAX-ACCESS read-write
    STATUS current
    DESCRIPTION
        "The LACP Activity value locally assigned to a LACP Aggregation Port.
        This value has effect only on ports whose aggregation method is LACP"
    ::= { sm8tat2saLagPortEntry 4 }

sm8tat2saLagPortLacpTimeout OBJECT-TYPE
    SYNTAX INTEGER { slowtimeout(0), fasttimeout(1)}
    MAX-ACCESS read-write
    STATUS current
    DESCRIPTION
        "The LACP Timeout value locally assigned to a LACP Aggregation Port.
        This value has effect only on ports whose aggregation method is LACP"
    ::= { sm8tat2saLagPortEntry 5 }

sm8tat2saLagPortAggregatorPort OBJECT-TYPE
    SYNTAX Integer32(1..52)
    MAX-ACCESS read-only
    STATUS current
    DESCRIPTION
        "The identifier value of the Aggregator that this Aggregation
        Port is currently attached to."
    ::= { sm8tat2saLagPortEntry 6 }

sm8tat2saLagPortReadyState OBJECT-TYPE
    SYNTAX INTEGER { notready(0), ready(1)}
    MAX-ACCESS read-only
    STATUS current
    DESCRIPTION
        "A status value indicating whether the Aggregation Port
         is ready for packet forwarding (1) or not ready (0)."
    ::= { sm8tat2saLagPortEntry 7 }

sm8tat2saLagAggregatorTable OBJECT-TYPE
    SYNTAX SEQUENCE OF SM8TAT2SALagAggregatorEntry
    MAX-ACCESS not-accessible
    STATUS current
    DESCRIPTION
        "A table that contains status information about every aggregator
        associated with this device. Each physical port can be deemed as
        an aggregator."
    ::= { sm8tat2saLinkAggregationGroup 3 }

sm8tat2saLagAggregatorEntry OBJECT-TYPE
    SYNTAX SM8TAT2SALagAggregatorEntry
    MAX-ACCESS not-accessible
    STATUS current
    DESCRIPTION
        "A list of aggregator status information for each aggregator on this device."
    INDEX { sm8tat2saLagAggregatorPortIndex }
    ::= { sm8tat2saLagAggregatorTable 1 }

SM8TAT2SALagAggregatorEntry ::=
    SEQUENCE {
        sm8tat2saLagAggregatorPortIndex Integer32,
        sm8tat2saLagPortAggregationMethod INTEGER,
        sm8tat2saLagAggregatorMemberPorts DisplayString,
        sm8tat2saLagAggregatorReadyPorts DisplayString
    }

sm8tat2saLagAggregatorPortIndex OBJECT-TYPE
    SYNTAX Integer32 (1..52)
    MAX-ACCESS not-accessible
    STATUS current
    DESCRIPTION
        "The aggregator port number"
    ::= { sm8tat2saLagAggregatorEntry 1 }

sm8tat2saLagPortAggregationMethod OBJECT-TYPE
    SYNTAX INTEGER { none(0), lacp(1), static(2)}
    MAX-ACCESS read-only
    STATUS current
    DESCRIPTION
        "The method the aggrgator uses to aggregate physical Port.
        In the LagPortTable if both LagPortLacpAggAdminKey and LagPortStaticAggAdminKey
        are zero for a port then the field will be 0 (none) for this corresponding
        aggregator port."
    ::= { sm8tat2saLagAggregatorEntry 2 }

sm8tat2saLagAggregatorMemberPorts OBJECT-TYPE
    SYNTAX DisplayString
    MAX-ACCESS read-only
    STATUS current
    DESCRIPTION
        "The port members that are attached to this aggregator port"
    ::= { sm8tat2saLagAggregatorEntry 3 }

sm8tat2saLagAggregatorReadyPorts OBJECT-TYPE
    SYNTAX DisplayString
    MAX-ACCESS read-only
    STATUS current
    DESCRIPTION
        "The ready-to-service port members that are attached to
        this aggregator port"
    ::= { sm8tat2saLagAggregatorEntry 4 }

sm8tat2saLagLacpPortTable OBJECT-TYPE
    SYNTAX SEQUENCE OF SM8TAT2SALagLacpPortEntry
    MAX-ACCESS not-accessible
    STATUS current
    DESCRIPTION
        "A table that contains additional aggregation status information
        about every LACP Aggregation Port associated with this device."
    ::= { sm8tat2saLinkAggregationGroup 4 }

sm8tat2saLagLacpPortEntry OBJECT-TYPE
    SYNTAX SM8TAT2SALagLacpPortEntry
    MAX-ACCESS not-accessible
    STATUS current
    DESCRIPTION
        "A list of Link Aggregation Control configuration
        parameters for each Aggregation Port on this device."
    INDEX { sm8tat2saLagLacpAggregator, sm8tat2saLagLacpActorPort}
    ::= { sm8tat2saLagLacpPortTable 1 }

SM8TAT2SALagLacpPortEntry ::=
    SEQUENCE {
        sm8tat2saLagLacpAggregator Integer32,
        sm8tat2saLagLacpActorPort Integer32,
        sm8tat2saLagLacpActorOperKey Integer32,
        sm8tat2saLagLacpPartnerPort Integer32,
        sm8tat2saLagLacpPartnerOperKey Integer32,
        sm8tat2saLagLacpActorSystemPriority Integer32,
        sm8tat2saLagLacpActorSystemID MacAddress,
        sm8tat2saLagLacpPartnerSystemPriority Integer32,
        sm8tat2saLagLacpPartnerSystemID MacAddress,
        sm8tat2saLagLacpPortReadyState INTEGER
    }

sm8tat2saLagLacpAggregator OBJECT-TYPE
    SYNTAX Integer32 (1..1024)
    MAX-ACCESS not-accessible
    STATUS current
    DESCRIPTION
        "The identifier value of the Aggregator that this Aggregation
        Port is currently attached to."
    ::= { sm8tat2saLagLacpPortEntry 1 }

sm8tat2saLagLacpActorPort OBJECT-TYPE
    SYNTAX Integer32 (1..52)
    MAX-ACCESS not-accessible
    STATUS current
    DESCRIPTION
        "The switch port number of the LACP port"
    ::= { sm8tat2saLagLacpPortEntry 2 }

sm8tat2saLagLacpActorOperKey OBJECT-TYPE
    SYNTAX Integer32 (1..16)
    MAX-ACCESS read-only
    STATUS current
    DESCRIPTION
        "The current operational value of the Key for the
        Aggregation Port. This is a 16-bit, read-only value."
    ::= { sm8tat2saLagLacpPortEntry 3 }

sm8tat2saLagLacpPartnerPort OBJECT-TYPE
    SYNTAX Integer32 (1..52)
    MAX-ACCESS read-only
    STATUS current
    DESCRIPTION
        "The switch port number of the LACP port"
    ::= { sm8tat2saLagLacpPortEntry 4 }

sm8tat2saLagLacpPartnerOperKey OBJECT-TYPE
    SYNTAX Integer32 (1..16)
    MAX-ACCESS read-only
    STATUS current
    DESCRIPTION
        "The current operational value of the Key for the
        protocol Partner. The value of this attribute may contain
        the manually configured value if there is no protocol Partner.
        This is a 16-bit, read-only value."
    ::= { sm8tat2saLagLacpPortEntry 5 }

sm8tat2saLagLacpActorSystemPriority OBJECT-TYPE
    SYNTAX Integer32 (1..65535)
    MAX-ACCESS read-only
    STATUS current
    DESCRIPTION
        "A 2-octet value representing the priority value associated
        with the Actor's System ID."
    ::= { sm8tat2saLagLacpPortEntry 6 }

sm8tat2saLagLacpActorSystemID OBJECT-TYPE
    SYNTAX MacAddress
    MAX-ACCESS read-only
    STATUS current
    DESCRIPTION
        "A 6-octet read-only MAC address value that defines
        the value of the System ID for the System that contains this
        Aggregation Port."
    ::= { sm8tat2saLagLacpPortEntry 7 }

sm8tat2saLagLacpPartnerSystemPriority OBJECT-TYPE
    SYNTAX Integer32 (1..65535)
    MAX-ACCESS read-only
    STATUS current
    DESCRIPTION
        "A 2-octet read-only value indicating the operational value
        of priority associated with the Partner's System ID. The
        value of this attribute may contain the manually configured value
        if there is no protocol Partner."
    ::= { sm8tat2saLagLacpPortEntry 8 }

sm8tat2saLagLacpPartnerSystemID OBJECT-TYPE
    SYNTAX MacAddress
    MAX-ACCESS read-only
    STATUS current
    DESCRIPTION
        "A 6-octet read-only MACAddress value representing
        the current value of the Aggregation Port's protocol Partner's
        System ID. A value of zero indicates that there is no known
        protocol Partner. The value of this attribute may contain the
        manually configured value if there is no protocol Partner."
    ::= { sm8tat2saLagLacpPortEntry 9 }

sm8tat2saLagLacpPortReadyState OBJECT-TYPE
    SYNTAX INTEGER { notready(0), ready(1)}
    MAX-ACCESS read-only
    STATUS current
    DESCRIPTION
        "A status value indicating whether the Aggregation Port
         is ready for packet forwarding (1) or not ready (0)."
    ::= { sm8tat2saLagLacpPortEntry 10 }

-- *************************************************************
-- Start sm8tat2saIpmc group
-- *************************************************************
sm8tat2saIpmc OBJECT IDENTIFIER ::= { sm8tat2saConfiguration 24 }

sm8tat2saIgmpConfig OBJECT IDENTIFIER ::= { sm8tat2saIpmc 1 }

sm8tat2saIgmpSnoopingEnable OBJECT-TYPE
   SYNTAX INTEGER { disable(0), enable(1) }
   MAX-ACCESS read-write
   STATUS current
   DESCRIPTION
       "Configure igmp mode.
        0: disable,
        1: enable. "
   ::= { sm8tat2saIgmpConfig 1 }

sm8tat2saIgmpUnkownFlooding OBJECT-TYPE
   SYNTAX INTEGER { disable(0), enable(1) }
   MAX-ACCESS read-write
   STATUS current
   DESCRIPTION
       "Configure Unregistered IPMCv4 Flooding Enabled.
        0: disable,
        1: enable. "
   ::= { sm8tat2saIgmpConfig 2 }

sm8tat2saIgmpSsmRangeAddress OBJECT-TYPE
   SYNTAX IpAddress
   MAX-ACCESS read-write
   STATUS current
   DESCRIPTION
       "Configure IGMP SSM Range Address.
        range: 224.0.0.0 - 239.255.255.255. "
   ::= { sm8tat2saIgmpConfig 3 }

sm8tat2saIgmpSsmRangeLen OBJECT-TYPE
   SYNTAX Integer32 (4..32)
   MAX-ACCESS read-write
   STATUS current
   DESCRIPTION
       "Configure IGMP SSM Range Length.
        range: 4 - 32. "
   ::= { sm8tat2saIgmpConfig 4 }

sm8tat2saIgmpProxyEnable OBJECT-TYPE
   SYNTAX INTEGER { disable(0), enable(1) }
   MAX-ACCESS read-write
   STATUS current
   DESCRIPTION
       "Configure IGMP Proxy Enabled.
        0: disable,
        1: enable. "
   ::= { sm8tat2saIgmpConfig 5 }

sm8tat2saIgmpConfigurationTable OBJECT-TYPE
   SYNTAX SEQUENCE OF SM8TAT2SAIgmpConfigurationEntry
   MAX-ACCESS not-accessible
   STATUS current
   DESCRIPTION
       " Show IPMC port configurations. "
   ::= { sm8tat2saIgmpConfig 6 }

sm8tat2saIgmpConfigurationEntry OBJECT-TYPE
   SYNTAX SM8TAT2SAIgmpConfigurationEntry
   MAX-ACCESS not-accessible
   STATUS current
   DESCRIPTION
       " "
   INDEX { sm8tat2saIgmpConfPort }
   ::= { sm8tat2saIgmpConfigurationTable 1 }

SM8TAT2SAIgmpConfigurationEntry ::= SEQUENCE {
   sm8tat2saIgmpConfPort Integer32,
   sm8tat2saIgmpConfRouterPort INTEGER,
   sm8tat2saIgmpConfFastLeave INTEGER,
   sm8tat2saIgmpConfThrottling Integer32,
   sm8tat2saIgmpConfProfile DisplayString
}

sm8tat2saIgmpConfPort OBJECT-TYPE
   SYNTAX Integer32(1..255)
   MAX-ACCESS not-accessible
   STATUS current
   DESCRIPTION
       " port, range : 1 - port number. "
   ::= { sm8tat2saIgmpConfigurationEntry 1 }

sm8tat2saIgmpConfRouterPort OBJECT-TYPE
   SYNTAX INTEGER { disable(0), enable(1) }
   MAX-ACCESS read-write
   STATUS current
   DESCRIPTION
       " Configure IPMC router port mode.
         0: disable,
         1: enable. "
   ::= { sm8tat2saIgmpConfigurationEntry 2 }

sm8tat2saIgmpConfFastLeave OBJECT-TYPE
   SYNTAX INTEGER { disable(0), enable(1) }
   MAX-ACCESS read-write
   STATUS current
   DESCRIPTION
       " Configure IPMC fast leave mode.
         0: disable,
         1: enable. "
   ::= { sm8tat2saIgmpConfigurationEntry 3 }

sm8tat2saIgmpConfThrottling OBJECT-TYPE
   SYNTAX Integer32(0..10)
   MAX-ACCESS read-write
   STATUS current
   DESCRIPTION
       " Configure IPMC throttling numbers .
         0: unlimited. "
   ::= { sm8tat2saIgmpConfigurationEntry 4 }

sm8tat2saIgmpConfProfile OBJECT-TYPE
   SYNTAX DisplayString
   MAX-ACCESS read-write
   STATUS current
   DESCRIPTION
       " Configure IPMC Profile . "
   ::= { sm8tat2saIgmpConfigurationEntry 5 }

sm8tat2saIgmpVlanConfiguration OBJECT IDENTIFIER ::= { sm8tat2saIpmc 2 }

sm8tat2saIgmpVlanConfigTable OBJECT-TYPE
   SYNTAX SEQUENCE OF SM8TAT2SAIgmpVlanConfigEntry
   MAX-ACCESS not-accessible
   STATUS current
   DESCRIPTION
       " "
   ::= { sm8tat2saIgmpVlanConfiguration 1 }

sm8tat2saIgmpVlanConfigEntry OBJECT-TYPE
   SYNTAX SM8TAT2SAIgmpVlanConfigEntry
   MAX-ACCESS not-accessible
   STATUS current
   DESCRIPTION
       " "
   INDEX { sm8tat2saIgmpVlanIndex }
   ::= { sm8tat2saIgmpVlanConfigTable 1 }

SM8TAT2SAIgmpVlanConfigEntry ::= SEQUENCE {
   sm8tat2saIgmpVlanIndex Integer32,
   sm8tat2saIgmpVlanVid Integer32,
   sm8tat2saIgmpVlanSnoopingMode INTEGER,
   sm8tat2saIgmpVlanQuerier INTEGER,
   sm8tat2saIgmpVlanCompatibility INTEGER,
   sm8tat2saIgmpVlanRV Integer32,
   sm8tat2saIgmpVlanQI Integer32,
   sm8tat2saIgmpVlanQRI Integer32,
   sm8tat2saIgmpVlanLLQI Integer32,
   sm8tat2saIgmpVlanURI Integer32,
   sm8tat2saIgmpVlanRowStatus RowStatus
}

sm8tat2saIgmpVlanIndex OBJECT-TYPE
   SYNTAX Integer32 (1..32)
   MAX-ACCESS not-accessible
   STATUS current
   DESCRIPTION
       "The Igmp Vlan Config Index."
   ::= { sm8tat2saIgmpVlanConfigEntry 1 }

sm8tat2saIgmpVlanVid OBJECT-TYPE
   SYNTAX Integer32 (1..4094)
   MAX-ACCESS read-create
   STATUS current
   DESCRIPTION
       "Igmp vlan config's vid.
        range: 1-4094. "
   ::= { sm8tat2saIgmpVlanConfigEntry 2 }

sm8tat2saIgmpVlanSnoopingMode OBJECT-TYPE
   SYNTAX INTEGER { disable(0), enable(1) }
   MAX-ACCESS read-create
   STATUS current
   DESCRIPTION
       "Igmp vlan config's snooping mode.
        0: disable,
        1: enable. "
   ::= { sm8tat2saIgmpVlanConfigEntry 3 }

sm8tat2saIgmpVlanQuerier OBJECT-TYPE
   SYNTAX INTEGER { disable(0), enable(1) }
   MAX-ACCESS read-create
   STATUS current
   DESCRIPTION
       "Igmp vlan config's querier mode.
        0: disable,
        1: enable. "
   ::= { sm8tat2saIgmpVlanConfigEntry 4 }

sm8tat2saIgmpVlanCompatibility OBJECT-TYPE
   SYNTAX INTEGER { igmpauto(0), forcedigmpv1(1), forcedigmpv2(2), forcedigmpv3(3) }
   MAX-ACCESS read-create
   STATUS current
   DESCRIPTION
       "Igmp vlan config's Compatibility.
        0: IGMP-Auto,
        1: Forced IGMPv1,
        2: Forced IGMPv2,
        3: Forced IGMPv3. "
   ::= { sm8tat2saIgmpVlanConfigEntry 5 }

sm8tat2saIgmpVlanRV OBJECT-TYPE
   SYNTAX Integer32 (1..255)
   MAX-ACCESS read-create
   STATUS current
   DESCRIPTION
       "Igmp vlan config's RV.
        default: 2, range: 1-255. "
   ::= { sm8tat2saIgmpVlanConfigEntry 6 }

sm8tat2saIgmpVlanQI OBJECT-TYPE
   SYNTAX Integer32 (1..31744)
   MAX-ACCESS read-create
   STATUS current
   DESCRIPTION
       "Igmp vlan config's QI.
        default: 125, range: 1-31744. "
   ::= { sm8tat2saIgmpVlanConfigEntry 7 }

sm8tat2saIgmpVlanQRI OBJECT-TYPE
   SYNTAX Integer32 (0..31744)
   MAX-ACCESS read-create
   STATUS current
   DESCRIPTION
       "Igmp vlan config's QRI.
        default: 100, range: 0-31744. "
   ::= { sm8tat2saIgmpVlanConfigEntry 8 }

sm8tat2saIgmpVlanLLQI OBJECT-TYPE
   SYNTAX Integer32 (0..31744)
   MAX-ACCESS read-create
   STATUS current
   DESCRIPTION
       "Igmp vlan config's LLQI.
        default: 10, range: 0-31744. "
   ::= { sm8tat2saIgmpVlanConfigEntry 9 }

sm8tat2saIgmpVlanURI OBJECT-TYPE
   SYNTAX Integer32 (0..31744)
   MAX-ACCESS read-create
   STATUS current
   DESCRIPTION
       "Igmp vlan config's URI.
        default: 1, range: 0-31744. "
   ::= { sm8tat2saIgmpVlanConfigEntry 10 }

sm8tat2saIgmpVlanRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm8tat2saIgmpVlanConfigEntry 11 }

sm8tat2saIgmpVlanStatus OBJECT IDENTIFIER ::= { sm8tat2saIpmc 3 }

sm8tat2saIgmpVlanStatusTable OBJECT-TYPE
   SYNTAX SEQUENCE OF SM8TAT2SAIgmpVlanStatusEntry
   MAX-ACCESS not-accessible
   STATUS current
   DESCRIPTION
       " "
   ::= { sm8tat2saIgmpVlanStatus 1 }

sm8tat2saIgmpVlanStatusEntry OBJECT-TYPE
   SYNTAX SM8TAT2SAIgmpVlanStatusEntry
   MAX-ACCESS not-accessible
   STATUS current
   DESCRIPTION
       " "
   INDEX { sm8tat2saIgmpVlanStatusIndex }
   ::= { sm8tat2saIgmpVlanStatusTable 1 }

SM8TAT2SAIgmpVlanStatusEntry ::= SEQUENCE {
   sm8tat2saIgmpVlanStatusIndex Integer32,
   sm8tat2saIgmpVlanStatusVid Integer32,
   sm8tat2saIgmpVlanStatusQuerierVersion DisplayString,
   sm8tat2saIgmpVlanStatusHostVersion DisplayString,
   sm8tat2saIgmpVlanStatusQuerierStatus DisplayString,
   sm8tat2saIgmpVlanStatusQuerierTransmitted Integer32,
   sm8tat2saIgmpVlanStatusQuerierReceived Integer32,
   sm8tat2saIgmpVlanStatusV1ReportsReceived Integer32,
   sm8tat2saIgmpVlanStatusV2ReportsReceived Integer32,
   sm8tat2saIgmpVlanStatusV3ReportsReceived Integer32,
   sm8tat2saIgmpVlanStatusV2LeavesReceived Integer32
}

sm8tat2saIgmpVlanStatusIndex OBJECT-TYPE
   SYNTAX Integer32 (1..64)
   MAX-ACCESS not-accessible
   STATUS current
   DESCRIPTION
       "The Igmp Vlan Status Index."
   ::= { sm8tat2saIgmpVlanStatusEntry 1 }

sm8tat2saIgmpVlanStatusVid OBJECT-TYPE
   SYNTAX Integer32 (1..4094)
   MAX-ACCESS read-only
   STATUS current
   DESCRIPTION
       "Igmp vlan status's vid.
        range: 1-4094. "
   ::= { sm8tat2saIgmpVlanStatusEntry 2 }

sm8tat2saIgmpVlanStatusQuerierVersion OBJECT-TYPE
   SYNTAX DisplayString
   MAX-ACCESS read-only
   STATUS current
   DESCRIPTION
       "Igmp vlan status's querier version. "
   ::= { sm8tat2saIgmpVlanStatusEntry 3 }

sm8tat2saIgmpVlanStatusHostVersion OBJECT-TYPE
   SYNTAX DisplayString
   MAX-ACCESS read-only
   STATUS current
   DESCRIPTION
       "Igmp vlan status's host version. "
   ::= { sm8tat2saIgmpVlanStatusEntry 4 }

sm8tat2saIgmpVlanStatusQuerierStatus OBJECT-TYPE
   SYNTAX DisplayString
   MAX-ACCESS read-only
   STATUS current
   DESCRIPTION
       "Igmp vlan status's querier status. "
   ::= { sm8tat2saIgmpVlanStatusEntry 5 }

sm8tat2saIgmpVlanStatusQuerierTransmitted OBJECT-TYPE
   SYNTAX Integer32 (0..2147483647)
   MAX-ACCESS read-only
   STATUS current
   DESCRIPTION
       "Igmp vlan status's querier transmitted packets. "
   ::= { sm8tat2saIgmpVlanStatusEntry 6 }

sm8tat2saIgmpVlanStatusQuerierReceived OBJECT-TYPE
   SYNTAX Integer32 (0..2147483647)
   MAX-ACCESS read-only
   STATUS current
   DESCRIPTION
       "Igmp vlan status's querier received packets. "
   ::= { sm8tat2saIgmpVlanStatusEntry 7 }

sm8tat2saIgmpVlanStatusV1ReportsReceived OBJECT-TYPE
   SYNTAX Integer32 (0..2147483647)
   MAX-ACCESS read-only
   STATUS current
   DESCRIPTION
       "Igmp vlan status's v1 report received packets. "
   ::= { sm8tat2saIgmpVlanStatusEntry 8 }

sm8tat2saIgmpVlanStatusV2ReportsReceived OBJECT-TYPE
   SYNTAX Integer32 (0..2147483647)
   MAX-ACCESS read-only
   STATUS current
   DESCRIPTION
       "Igmp vlan status's v2 report received packets. "
   ::= { sm8tat2saIgmpVlanStatusEntry 9 }

sm8tat2saIgmpVlanStatusV3ReportsReceived OBJECT-TYPE
   SYNTAX Integer32 (0..2147483647)
   MAX-ACCESS read-only
   STATUS current
   DESCRIPTION
       "Igmp vlan status's V3 report received packets. "
   ::= { sm8tat2saIgmpVlanStatusEntry 10 }

sm8tat2saIgmpVlanStatusV2LeavesReceived OBJECT-TYPE
   SYNTAX Integer32 (0..2147483647)
   MAX-ACCESS read-only
   STATUS current
   DESCRIPTION
       "Igmp vlan status's v2 leave received packets. "
   ::= { sm8tat2saIgmpVlanStatusEntry 11 }

sm8tat2saIgmpRouterPortStatusTable OBJECT-TYPE
   SYNTAX SEQUENCE OF SM8TAT2SAIgmpRouterPortStatusEntry
   MAX-ACCESS not-accessible
   STATUS current
   DESCRIPTION
       " "
   ::= { sm8tat2saIgmpVlanStatus 2 }

sm8tat2saIgmpRouterPortStatusEntry OBJECT-TYPE
   SYNTAX SM8TAT2SAIgmpRouterPortStatusEntry
   MAX-ACCESS not-accessible
   STATUS current
   DESCRIPTION
       " "
   INDEX { sm8tat2saIgmpRouterPort }
   ::= { sm8tat2saIgmpRouterPortStatusTable 1 }

SM8TAT2SAIgmpRouterPortStatusEntry ::= SEQUENCE {
   sm8tat2saIgmpRouterPort Integer32,
   sm8tat2saIgmpRouterPortStatus DisplayString
}

sm8tat2saIgmpRouterPort OBJECT-TYPE
   SYNTAX Integer32(1..255)
   MAX-ACCESS not-accessible
   STATUS current
   DESCRIPTION
       " port, range : 1 - port number. "
   ::= { sm8tat2saIgmpRouterPortStatusEntry 1 }

sm8tat2saIgmpRouterPortStatus OBJECT-TYPE
   SYNTAX DisplayString
   MAX-ACCESS read-only
   STATUS current
   DESCRIPTION
       " Router Port Status. "
   ::= { sm8tat2saIgmpRouterPortStatusEntry 2 }

sm8tat2saIgmpGroupsInformation OBJECT IDENTIFIER ::= { sm8tat2saIpmc 4 }

sm8tat2saIgmpGroupsTable OBJECT-TYPE
   SYNTAX SEQUENCE OF SM8TAT2SAIgmpGroupsEntry
   MAX-ACCESS not-accessible
   STATUS current
   DESCRIPTION
       " "
   ::= { sm8tat2saIgmpGroupsInformation 1 }

sm8tat2saIgmpGroupsEntry OBJECT-TYPE
   SYNTAX SM8TAT2SAIgmpGroupsEntry
   MAX-ACCESS not-accessible
   STATUS current
   DESCRIPTION
       " "
   INDEX { sm8tat2saIgmpGroupsIndex }
   ::= { sm8tat2saIgmpGroupsTable 1 }

SM8TAT2SAIgmpGroupsEntry ::= SEQUENCE {
   sm8tat2saIgmpGroupsIndex Integer32,
   sm8tat2saIgmpGroupsVid Integer32,
   sm8tat2saIgmpGroupsAddress IpAddress,
   sm8tat2saIgmpGroupsPort DisplayString
}

sm8tat2saIgmpGroupsIndex OBJECT-TYPE
   SYNTAX Integer32 (1..4094)
   MAX-ACCESS not-accessible
   STATUS current
   DESCRIPTION
       "The Igmp Group Index."
   ::= { sm8tat2saIgmpGroupsEntry 1 }

sm8tat2saIgmpGroupsVid OBJECT-TYPE
   SYNTAX Integer32 (1..4094)
   MAX-ACCESS read-only
   STATUS current
   DESCRIPTION
       "Igmp group's vid.
        range: 1-4094. "
   ::= { sm8tat2saIgmpGroupsEntry 2 }

sm8tat2saIgmpGroupsAddress OBJECT-TYPE
   SYNTAX IpAddress
   MAX-ACCESS read-only
   STATUS current
   DESCRIPTION
       "Igmp group's address. "
   ::= { sm8tat2saIgmpGroupsEntry 3 }

sm8tat2saIgmpGroupsPort OBJECT-TYPE
   SYNTAX DisplayString
   MAX-ACCESS read-only
   STATUS current
   DESCRIPTION
       "Igmp group's port member. "
   ::= { sm8tat2saIgmpGroupsEntry 4 }

sm8tat2saIgmpSFMInformation OBJECT IDENTIFIER ::= { sm8tat2saIpmc 5 }

sm8tat2saIgmpSFMTable OBJECT-TYPE
   SYNTAX SEQUENCE OF SM8TAT2SAIgmpSFMEntry
   MAX-ACCESS not-accessible
   STATUS current
   DESCRIPTION
       " "
   ::= { sm8tat2saIgmpSFMInformation 1 }

sm8tat2saIgmpSFMEntry OBJECT-TYPE
   SYNTAX SM8TAT2SAIgmpSFMEntry
   MAX-ACCESS not-accessible
   STATUS current
   DESCRIPTION
       " "
   INDEX { sm8tat2saIgmpSFMIndex }
   ::= { sm8tat2saIgmpSFMTable 1 }

SM8TAT2SAIgmpSFMEntry ::= SEQUENCE {
   sm8tat2saIgmpSFMIndex Integer32,
   sm8tat2saIgmpSFMVid Integer32,
   sm8tat2saIgmpSFMAddress IpAddress,
   sm8tat2saIgmpSFMPort Integer32,
   sm8tat2saIgmpSFMMode DisplayString,
   sm8tat2saIgmpSFMSourceAddress IpAddress,
   sm8tat2saIgmpSFMType DisplayString
}

sm8tat2saIgmpSFMIndex OBJECT-TYPE
   SYNTAX Integer32 (1..4094)
   MAX-ACCESS not-accessible
   STATUS current
   DESCRIPTION
       "The Igmp SFM Index."
   ::= { sm8tat2saIgmpSFMEntry 1 }

sm8tat2saIgmpSFMVid OBJECT-TYPE
   SYNTAX Integer32 (1..4094)
   MAX-ACCESS read-only
   STATUS current
   DESCRIPTION
       "Igmp SFM's vid.
        range: 1-4094. "
   ::= { sm8tat2saIgmpSFMEntry 2 }

sm8tat2saIgmpSFMAddress OBJECT-TYPE
   SYNTAX IpAddress
   MAX-ACCESS read-only
   STATUS current
   DESCRIPTION
       "Igmp SFM's group address. "
   ::= { sm8tat2saIgmpSFMEntry 3 }

sm8tat2saIgmpSFMPort OBJECT-TYPE
   SYNTAX Integer32 (1..100)
   MAX-ACCESS read-only
   STATUS current
   DESCRIPTION
       "Igmp group's port member. "
   ::= { sm8tat2saIgmpSFMEntry 4 }

sm8tat2saIgmpSFMMode OBJECT-TYPE
   SYNTAX DisplayString
   MAX-ACCESS read-only
   STATUS current
   DESCRIPTION
       "Igmp SFM's mode. "
   ::= { sm8tat2saIgmpSFMEntry 5 }

sm8tat2saIgmpSFMSourceAddress OBJECT-TYPE
   SYNTAX IpAddress
   MAX-ACCESS read-only
   STATUS current
   DESCRIPTION
       "Igmp SFM's source address. "
   ::= { sm8tat2saIgmpSFMEntry 6 }

sm8tat2saIgmpSFMType OBJECT-TYPE
   SYNTAX DisplayString
   MAX-ACCESS read-only
   STATUS current
   DESCRIPTION
       "Igmp SFM's type. "
   ::= { sm8tat2saIgmpSFMEntry 7 }

sm8tat2saMldConfig OBJECT IDENTIFIER ::= { sm8tat2saIpmc 6 }

sm8tat2saMldSnoopingEnable OBJECT-TYPE
   SYNTAX INTEGER { disable(0), enable(1) }
   MAX-ACCESS read-write
   STATUS current
   DESCRIPTION
       "Configure igmp mode.
        0: disable,
        1: enable. "
   ::= { sm8tat2saMldConfig 1 }

sm8tat2saMldUnkownFlooding OBJECT-TYPE
   SYNTAX INTEGER { disable(0), enable(1) }
   MAX-ACCESS read-write
   STATUS current
   DESCRIPTION
       "Configure Unregistered IPMCv6  Flooding Enabled.
        0: disable,
        1: enable. "
   ::= { sm8tat2saMldConfig 2 }

sm8tat2saMldSsmRangeAddress OBJECT-TYPE
   SYNTAX DisplayString
   MAX-ACCESS read-write
   STATUS current
   DESCRIPTION
       " Configure MLD SSM Range Address. "
   ::= { sm8tat2saMldConfig 3 }

sm8tat2saMldSsmRangeLen OBJECT-TYPE
   SYNTAX Integer32 (8..128)
   MAX-ACCESS read-write
   STATUS current
   DESCRIPTION
       "Configure MLD SSM Range Length.
        range: 8 - 128. "
   ::= { sm8tat2saMldConfig 4 }

sm8tat2saMldProxyEnable OBJECT-TYPE
   SYNTAX INTEGER { disable(0), enable(1) }
   MAX-ACCESS read-write
   STATUS current
   DESCRIPTION
       "Configure MLD Proxy Enabled.
        0: disable,
        1: enable. "
   ::= { sm8tat2saMldConfig 5 }

sm8tat2saMldConfigurationTable OBJECT-TYPE
   SYNTAX SEQUENCE OF SM8TAT2SAMldConfigurationEntry
   MAX-ACCESS not-accessible
   STATUS current
   DESCRIPTION
       " Show MLD port configurations. "
   ::= { sm8tat2saMldConfig 6 }

sm8tat2saMldConfigurationEntry OBJECT-TYPE
   SYNTAX SM8TAT2SAMldConfigurationEntry
   MAX-ACCESS not-accessible
   STATUS current
   DESCRIPTION
       " "
   INDEX { sm8tat2saMldConfPort }
   ::= { sm8tat2saMldConfigurationTable 1 }

SM8TAT2SAMldConfigurationEntry ::= SEQUENCE {
   sm8tat2saMldConfPort Integer32,
   sm8tat2saMldConfRouterPort INTEGER,
   sm8tat2saMldConfFastLeave INTEGER,
   sm8tat2saMldConfThrottling Integer32,
   sm8tat2saMldConfProfile DisplayString
}

sm8tat2saMldConfPort OBJECT-TYPE
   SYNTAX Integer32(1..255)
   MAX-ACCESS not-accessible
   STATUS current
   DESCRIPTION
       " port, range : 1 - port number. "
   ::= { sm8tat2saMldConfigurationEntry 1 }

sm8tat2saMldConfRouterPort OBJECT-TYPE
   SYNTAX INTEGER { disable(0), enable(1) }
   MAX-ACCESS read-write
   STATUS current
   DESCRIPTION
       " Configure IPMC router port mode.
         0: disable,
         1: enable. "
   ::= { sm8tat2saMldConfigurationEntry 2 }

sm8tat2saMldConfFastLeave OBJECT-TYPE
   SYNTAX INTEGER { disable(0), enable(1) }
   MAX-ACCESS read-write
   STATUS current
   DESCRIPTION
       " Configure IPMC fast leave mode.
         0: disable,
         1: enable. "
   ::= { sm8tat2saMldConfigurationEntry 3 }

sm8tat2saMldConfThrottling OBJECT-TYPE
   SYNTAX Integer32(0..10)
   MAX-ACCESS read-write
   STATUS current
   DESCRIPTION
       " Configure MLD throttling numbers .
         0: unlimited. "
   ::= { sm8tat2saMldConfigurationEntry 4 }

sm8tat2saMldConfProfile OBJECT-TYPE
   SYNTAX DisplayString
   MAX-ACCESS read-write
   STATUS current
   DESCRIPTION
       " Configure MLD Profile . "
   ::= { sm8tat2saMldConfigurationEntry 5 }

sm8tat2saMldVlanConfiguration OBJECT IDENTIFIER ::= { sm8tat2saIpmc 7 }

sm8tat2saMldVlanConfigTable OBJECT-TYPE
   SYNTAX SEQUENCE OF SM8TAT2SAMldVlanConfigEntry
   MAX-ACCESS not-accessible
   STATUS current
   DESCRIPTION
       " "
   ::= { sm8tat2saMldVlanConfiguration 1 }

sm8tat2saMldVlanConfigEntry OBJECT-TYPE
   SYNTAX SM8TAT2SAMldVlanConfigEntry
   MAX-ACCESS not-accessible
   STATUS current
   DESCRIPTION
       " "
   INDEX { sm8tat2saMldVlanIndex }
   ::= { sm8tat2saMldVlanConfigTable 1 }

SM8TAT2SAMldVlanConfigEntry ::= SEQUENCE {
   sm8tat2saMldVlanIndex Integer32,
   sm8tat2saMldVlanVid Integer32,
   sm8tat2saMldVlanSnoopingMode INTEGER,
   sm8tat2saMldVlanQuerier INTEGER,
   sm8tat2saMldVlanCompatibility INTEGER,
   sm8tat2saMldVlanRV Integer32,
   sm8tat2saMldVlanQI Integer32,
   sm8tat2saMldVlanQRI Integer32,
   sm8tat2saMldVlanLLQI Integer32,
   sm8tat2saMldVlanURI Integer32,
   sm8tat2saMldVlanRowStatus RowStatus
}

sm8tat2saMldVlanIndex OBJECT-TYPE
   SYNTAX Integer32 (1..32)
   MAX-ACCESS not-accessible
   STATUS current
   DESCRIPTION
       "The Mld Vlan Config Index."
   ::= { sm8tat2saMldVlanConfigEntry 1 }

sm8tat2saMldVlanVid OBJECT-TYPE
   SYNTAX Integer32 (1..4094)
   MAX-ACCESS read-create
   STATUS current
   DESCRIPTION
       "Mld vlan config's vid.
        range: 1-4094. "
   ::= { sm8tat2saMldVlanConfigEntry 2 }

sm8tat2saMldVlanSnoopingMode OBJECT-TYPE
   SYNTAX INTEGER { disable(0), enable(1) }
   MAX-ACCESS read-create
   STATUS current
   DESCRIPTION
       "Mld vlan config's snooping mode.
        0: disable,
        1: enable. "
   ::= { sm8tat2saMldVlanConfigEntry 3 }

sm8tat2saMldVlanQuerier OBJECT-TYPE
   SYNTAX INTEGER { disable(0), enable(1) }
   MAX-ACCESS read-create
   STATUS current
   DESCRIPTION
       "Mld vlan config's querier mode.
        0: disable,
        1: enable. "
   ::= { sm8tat2saMldVlanConfigEntry 4 }

sm8tat2saMldVlanCompatibility OBJECT-TYPE
   SYNTAX INTEGER { igmpauto(0), forcedigmpv1(1), forcedigmpv2(2), forcedigmpv3(3) }
   MAX-ACCESS read-create
   STATUS current
   DESCRIPTION
       "Mld vlan config's Compatibility.
        0: IGMP-Auto,
        1: Forced IGMPv1,
        2: Forced IGMPv2,
        3: Forced IGMPv3. "
   ::= { sm8tat2saMldVlanConfigEntry 5 }

sm8tat2saMldVlanRV OBJECT-TYPE
   SYNTAX Integer32 (1..255)
   MAX-ACCESS read-create
   STATUS current
   DESCRIPTION
       "Mld vlan config's RV.
        default: 2, range: 1-255. "
   ::= { sm8tat2saMldVlanConfigEntry 6 }

sm8tat2saMldVlanQI OBJECT-TYPE
   SYNTAX Integer32 (1..31744)
   MAX-ACCESS read-create
   STATUS current
   DESCRIPTION
       "Mld vlan config's QI.
        default: 125, range: 1-31744. "
   ::= { sm8tat2saMldVlanConfigEntry 7 }

sm8tat2saMldVlanQRI OBJECT-TYPE
   SYNTAX Integer32 (0..31744)
   MAX-ACCESS read-create
   STATUS current
   DESCRIPTION
       "Mld vlan config's QRI.
        default: 100, range: 0-31744. "
   ::= { sm8tat2saMldVlanConfigEntry 8 }

sm8tat2saMldVlanLLQI OBJECT-TYPE
   SYNTAX Integer32 (0..31744)
   MAX-ACCESS read-create
   STATUS current
   DESCRIPTION
       "Mld vlan config's LLQI.
        default: 10, range: 0-31744. "
   ::= { sm8tat2saMldVlanConfigEntry 9 }

sm8tat2saMldVlanURI OBJECT-TYPE
   SYNTAX Integer32 (0..31744)
   MAX-ACCESS read-create
   STATUS current
   DESCRIPTION
       "Mld vlan config's URI.
        default: 1, range: 0-31744. "
   ::= { sm8tat2saMldVlanConfigEntry 10 }

sm8tat2saMldVlanRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm8tat2saMldVlanConfigEntry 11 }

sm8tat2saMldVlanStatus OBJECT IDENTIFIER ::= { sm8tat2saIpmc 8 }

sm8tat2saMldVlanStatusTable OBJECT-TYPE
   SYNTAX SEQUENCE OF SM8TAT2SAMldVlanStatusEntry
   MAX-ACCESS not-accessible
   STATUS current
   DESCRIPTION
       " "
   ::= { sm8tat2saMldVlanStatus 1 }

sm8tat2saMldVlanStatusEntry OBJECT-TYPE
   SYNTAX SM8TAT2SAMldVlanStatusEntry
   MAX-ACCESS not-accessible
   STATUS current
   DESCRIPTION
       " "
   INDEX { sm8tat2saMldVlanStatusIndex }
   ::= { sm8tat2saMldVlanStatusTable 1 }

SM8TAT2SAMldVlanStatusEntry ::= SEQUENCE {
   sm8tat2saMldVlanStatusIndex Integer32,
   sm8tat2saMldVlanStatusVid Integer32,
   sm8tat2saMldVlanStatusQuerierVersion DisplayString,
   sm8tat2saMldVlanStatusHostVersion DisplayString,
   sm8tat2saMldVlanStatusQuerierStatus DisplayString,
   sm8tat2saMldVlanStatusQuerierTransmitted Integer32,
   sm8tat2saMldVlanStatusQuerierReceived Integer32,
   sm8tat2saMldVlanStatusV1ReportsReceived Integer32,
   sm8tat2saMldVlanStatusV2ReportsReceived Integer32,
   sm8tat2saMldVlanStatusV1LeavesReceived Integer32
}

sm8tat2saMldVlanStatusIndex OBJECT-TYPE
   SYNTAX Integer32 (1..64)
   MAX-ACCESS not-accessible
   STATUS current
   DESCRIPTION
       "The Mld Vlan Status Index."
   ::= { sm8tat2saMldVlanStatusEntry 1 }

sm8tat2saMldVlanStatusVid OBJECT-TYPE
   SYNTAX Integer32 (1..4094)
   MAX-ACCESS read-only
   STATUS current
   DESCRIPTION
       "Mld vlan status's vid.
        range: 1-4094. "
   ::= { sm8tat2saMldVlanStatusEntry 2 }

sm8tat2saMldVlanStatusQuerierVersion OBJECT-TYPE
   SYNTAX DisplayString
   MAX-ACCESS read-only
   STATUS current
   DESCRIPTION
       "Mld vlan status's querier version. "
   ::= { sm8tat2saMldVlanStatusEntry 3 }

sm8tat2saMldVlanStatusHostVersion OBJECT-TYPE
   SYNTAX DisplayString
   MAX-ACCESS read-only
   STATUS current
   DESCRIPTION
       "Mld vlan status's host version. "
   ::= { sm8tat2saMldVlanStatusEntry 4 }

sm8tat2saMldVlanStatusQuerierStatus OBJECT-TYPE
   SYNTAX DisplayString
   MAX-ACCESS read-only
   STATUS current
   DESCRIPTION
       "Mld vlan status's querier status. "
   ::= { sm8tat2saMldVlanStatusEntry 5 }

sm8tat2saMldVlanStatusQuerierTransmitted OBJECT-TYPE
   SYNTAX Integer32 (0..2147483647)
   MAX-ACCESS read-only
   STATUS current
   DESCRIPTION
       "Mld vlan status's querier transmitted packets. "
   ::= { sm8tat2saMldVlanStatusEntry 6 }

sm8tat2saMldVlanStatusQuerierReceived OBJECT-TYPE
   SYNTAX Integer32 (0..2147483647)
   MAX-ACCESS read-only
   STATUS current
   DESCRIPTION
       "Mld vlan status's querier received packets. "
   ::= { sm8tat2saMldVlanStatusEntry 7 }

sm8tat2saMldVlanStatusV1ReportsReceived OBJECT-TYPE
   SYNTAX Integer32 (0..2147483647)
   MAX-ACCESS read-only
   STATUS current
   DESCRIPTION
       "Mld vlan status's v1 report received packets. "
   ::= { sm8tat2saMldVlanStatusEntry 8 }

sm8tat2saMldVlanStatusV2ReportsReceived OBJECT-TYPE
   SYNTAX Integer32 (0..2147483647)
   MAX-ACCESS read-only
   STATUS current
   DESCRIPTION
       "Mld vlan status's v2 report received packets. "
   ::= { sm8tat2saMldVlanStatusEntry 9 }

sm8tat2saMldVlanStatusV1LeavesReceived OBJECT-TYPE
   SYNTAX Integer32 (0..2147483647)
   MAX-ACCESS read-only
   STATUS current
   DESCRIPTION
       "Mld vlan status's v2 leave received packets. "
   ::= { sm8tat2saMldVlanStatusEntry 10 }

sm8tat2saMldRouterPortStatusTable OBJECT-TYPE
   SYNTAX SEQUENCE OF SM8TAT2SAMldRouterPortStatusEntry
   MAX-ACCESS not-accessible
   STATUS current
   DESCRIPTION
       " "
   ::= { sm8tat2saMldVlanStatus 2 }

sm8tat2saMldRouterPortStatusEntry OBJECT-TYPE
   SYNTAX SM8TAT2SAMldRouterPortStatusEntry
   MAX-ACCESS not-accessible
   STATUS current
   DESCRIPTION
       " "
   INDEX { sm8tat2saMldRouterPort }
   ::= { sm8tat2saMldRouterPortStatusTable 1 }

SM8TAT2SAMldRouterPortStatusEntry ::= SEQUENCE {
   sm8tat2saMldRouterPort Integer32,
   sm8tat2saMldRouterPortStatus DisplayString
}

sm8tat2saMldRouterPort OBJECT-TYPE
   SYNTAX Integer32(1..255)
   MAX-ACCESS not-accessible
   STATUS current
   DESCRIPTION
       " port, range : 1 - port number. "
   ::= { sm8tat2saMldRouterPortStatusEntry 1 }

sm8tat2saMldRouterPortStatus OBJECT-TYPE
   SYNTAX DisplayString
   MAX-ACCESS read-only
   STATUS current
   DESCRIPTION
       " Router Port Status. "
   ::= { sm8tat2saMldRouterPortStatusEntry 2 }

sm8tat2saMldGroupsInformation OBJECT IDENTIFIER ::= { sm8tat2saIpmc 9 }

sm8tat2saMldGroupsTable OBJECT-TYPE
   SYNTAX SEQUENCE OF SM8TAT2SAMldGroupsEntry
   MAX-ACCESS not-accessible
   STATUS current
   DESCRIPTION
       " "
   ::= { sm8tat2saMldGroupsInformation 1 }

sm8tat2saMldGroupsEntry OBJECT-TYPE
   SYNTAX SM8TAT2SAMldGroupsEntry
   MAX-ACCESS not-accessible
   STATUS current
   DESCRIPTION
       " "
   INDEX { sm8tat2saMldGroupsIndex }
   ::= { sm8tat2saMldGroupsTable 1 }

SM8TAT2SAMldGroupsEntry ::= SEQUENCE {
   sm8tat2saMldGroupsIndex Integer32,
   sm8tat2saMldGroupsVid Integer32,
   sm8tat2saMldGroupsAddress DisplayString,
   sm8tat2saMldGroupsPort DisplayString
}

sm8tat2saMldGroupsIndex OBJECT-TYPE
   SYNTAX Integer32 (1..4094)
   MAX-ACCESS not-accessible
   STATUS current
   DESCRIPTION
       "The Mld Group Index."
   ::= { sm8tat2saMldGroupsEntry 1 }

sm8tat2saMldGroupsVid OBJECT-TYPE
   SYNTAX Integer32 (1..4094)
   MAX-ACCESS read-only
   STATUS current
   DESCRIPTION
       "Mld group's vid.
        range: 1-4094. "
   ::= { sm8tat2saMldGroupsEntry 2 }

sm8tat2saMldGroupsAddress OBJECT-TYPE
   SYNTAX DisplayString
   MAX-ACCESS read-only
   STATUS current
   DESCRIPTION
       "Mld group's address. "
   ::= { sm8tat2saMldGroupsEntry 3 }

sm8tat2saMldGroupsPort OBJECT-TYPE
   SYNTAX DisplayString
   MAX-ACCESS read-only
   STATUS current
   DESCRIPTION
       "Mld group's port member. "
   ::= { sm8tat2saMldGroupsEntry 4 }

sm8tat2saMldSFMInformation OBJECT IDENTIFIER ::= { sm8tat2saIpmc 10 }

sm8tat2saMldSFMTable OBJECT-TYPE
   SYNTAX SEQUENCE OF SM8TAT2SAMldSFMEntry
   MAX-ACCESS not-accessible
   STATUS current
   DESCRIPTION
       " "
   ::= { sm8tat2saMldSFMInformation 1 }

sm8tat2saMldSFMEntry OBJECT-TYPE
   SYNTAX SM8TAT2SAMldSFMEntry
   MAX-ACCESS not-accessible
   STATUS current
   DESCRIPTION
       " "
   INDEX { sm8tat2saMldSFMIndex }
   ::= { sm8tat2saMldSFMTable 1 }

SM8TAT2SAMldSFMEntry ::= SEQUENCE {
   sm8tat2saMldSFMIndex Integer32,
   sm8tat2saMldSFMVid Integer32,
   sm8tat2saMldSFMAddress DisplayString,
   sm8tat2saMldSFMPort Integer32,
   sm8tat2saMldSFMMode DisplayString,
   sm8tat2saMldSFMSourceAddress DisplayString,
   sm8tat2saMldSFMType DisplayString
}

sm8tat2saMldSFMIndex OBJECT-TYPE
   SYNTAX Integer32 (1..4094)
   MAX-ACCESS not-accessible
   STATUS current
   DESCRIPTION
       "The Mld SFM Index."
   ::= { sm8tat2saMldSFMEntry 1 }

sm8tat2saMldSFMVid OBJECT-TYPE
   SYNTAX Integer32 (1..4094)
   MAX-ACCESS read-only
   STATUS current
   DESCRIPTION
       "Mld SFM's vid.
        range: 1-4094. "
   ::= { sm8tat2saMldSFMEntry 2 }

sm8tat2saMldSFMAddress OBJECT-TYPE
   SYNTAX DisplayString
   MAX-ACCESS read-only
   STATUS current
   DESCRIPTION
       "Mld SFM's group address. "
   ::= { sm8tat2saMldSFMEntry 3 }

sm8tat2saMldSFMPort OBJECT-TYPE
   SYNTAX Integer32 (1..100)
   MAX-ACCESS read-only
   STATUS current
   DESCRIPTION
       "Mld group's port member. "
   ::= { sm8tat2saMldSFMEntry 4 }

sm8tat2saMldSFMMode OBJECT-TYPE
   SYNTAX DisplayString
   MAX-ACCESS read-only
   STATUS current
   DESCRIPTION
       "Mld SFM's mode. "
   ::= { sm8tat2saMldSFMEntry 5 }

sm8tat2saMldSFMSourceAddress OBJECT-TYPE
   SYNTAX DisplayString
   MAX-ACCESS read-only
   STATUS current
   DESCRIPTION
       "Mld SFM's source address. "
   ::= { sm8tat2saMldSFMEntry 6 }

sm8tat2saMldSFMType OBJECT-TYPE
   SYNTAX DisplayString
   MAX-ACCESS read-only
   STATUS current
   DESCRIPTION
       "Mld SFM's type. "
   ::= { sm8tat2saMldSFMEntry 7 }

sm8tat2saMulticastFilteringProfile OBJECT IDENTIFIER ::= { sm8tat2saIpmc 11 }

sm8tat2saMulticastProfileEnable OBJECT-TYPE
   SYNTAX INTEGER { disable(0), enable(1) }
   MAX-ACCESS read-write
   STATUS current
   DESCRIPTION
       "Configure profile mode.
        0: disable,
        1: enable. "
   ::= { sm8tat2saMulticastFilteringProfile 1 }

sm8tat2saMulticastProfileTable OBJECT-TYPE
   SYNTAX SEQUENCE OF SM8TAT2SAMulticastProfileEntry
   MAX-ACCESS not-accessible
   STATUS current
   DESCRIPTION
       "Multicast Profile Table. "
   ::= { sm8tat2saMulticastFilteringProfile 2 }

sm8tat2saMulticastProfileEntry OBJECT-TYPE
   SYNTAX SM8TAT2SAMulticastProfileEntry
   MAX-ACCESS not-accessible
   STATUS current
   DESCRIPTION
       " "
   INDEX { sm8tat2saMulticastProfileIndex }
   ::= { sm8tat2saMulticastProfileTable 1 }

SM8TAT2SAMulticastProfileEntry ::= SEQUENCE {
   sm8tat2saMulticastProfileIndex Integer32,
   sm8tat2saMulticastProfileName DisplayString,
   sm8tat2saMulticastProfileDescription DisplayString,
   sm8tat2saMulticastProfileRowStatus RowStatus
}

sm8tat2saMulticastProfileIndex OBJECT-TYPE
   SYNTAX Integer32(1..64)
   MAX-ACCESS not-accessible
   STATUS current
   DESCRIPTION
       " Multicast Profile Index. "
   ::= { sm8tat2saMulticastProfileEntry 1 }

sm8tat2saMulticastProfileName OBJECT-TYPE
   SYNTAX DisplayString
   MAX-ACCESS read-create
   STATUS current
   DESCRIPTION
       " Multicast Profile Name. "
   ::= { sm8tat2saMulticastProfileEntry 2 }

sm8tat2saMulticastProfileDescription OBJECT-TYPE
   SYNTAX DisplayString
   MAX-ACCESS read-create
   STATUS current
   DESCRIPTION
       " Multicast Profile Description. "
   ::= { sm8tat2saMulticastProfileEntry 3 }

sm8tat2saMulticastProfileRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm8tat2saMulticastProfileEntry 4 }

sm8tat2saFilteringAddressTable OBJECT-TYPE
   SYNTAX SEQUENCE OF SM8TAT2SAFilteringAddressEntry
   MAX-ACCESS not-accessible
   STATUS current
   DESCRIPTION
       " "
   ::= { sm8tat2saMulticastFilteringProfile 3 }

sm8tat2saFilteringAddressEntry OBJECT-TYPE
   SYNTAX SM8TAT2SAFilteringAddressEntry
   MAX-ACCESS not-accessible
   STATUS current
   DESCRIPTION
       " "
   INDEX { sm8tat2saFilteringAddressIndex }
   ::= { sm8tat2saFilteringAddressTable 1 }

SM8TAT2SAFilteringAddressEntry ::= SEQUENCE {
   sm8tat2saFilteringAddressIndex Integer32,
   sm8tat2saFilteringAddressEntryName DisplayString,
   sm8tat2saFilteringAddressStartAddress DisplayString,
   sm8tat2saFilteringAddressEndAddress DisplayString,
   sm8tat2saFilteringAddressRowStatus RowStatus
}

sm8tat2saFilteringAddressIndex OBJECT-TYPE
   SYNTAX Integer32 (1..32)
   MAX-ACCESS not-accessible
   STATUS current
   DESCRIPTION
       "Multicast Filtering Address Table Index. "
   ::= { sm8tat2saFilteringAddressEntry 1 }

sm8tat2saFilteringAddressEntryName OBJECT-TYPE
   SYNTAX DisplayString
   MAX-ACCESS read-create
   STATUS current
   DESCRIPTION
       "Multicast Filtering Address Table Name. "
   ::= { sm8tat2saFilteringAddressEntry 2 }

sm8tat2saFilteringAddressStartAddress OBJECT-TYPE
   SYNTAX DisplayString
   MAX-ACCESS read-create
   STATUS current
   DESCRIPTION
       "Multicast Filtering Address Table Start Address. "
   ::= { sm8tat2saFilteringAddressEntry 3 }

sm8tat2saFilteringAddressEndAddress OBJECT-TYPE
   SYNTAX DisplayString
   MAX-ACCESS read-create
   STATUS current
   DESCRIPTION
       "Multicast Filtering Address Table End Address. "
   ::= { sm8tat2saFilteringAddressEntry 4 }

sm8tat2saFilteringAddressRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm8tat2saFilteringAddressEntry 5 }

sm8tat2saMulticastProfileRuleTable OBJECT-TYPE
   SYNTAX SEQUENCE OF SM8TAT2SAMulticastProfileRuleEntry
   MAX-ACCESS not-accessible
   STATUS current
   DESCRIPTION
       " "
   ::= { sm8tat2saMulticastFilteringProfile 4 }

sm8tat2saMulticastProfileRuleEntry OBJECT-TYPE
   SYNTAX SM8TAT2SAMulticastProfileRuleEntry
   MAX-ACCESS not-accessible
   STATUS current
   DESCRIPTION
       " "
   INDEX { sm8tat2saMulticastProfileRuleIndex }
   ::= { sm8tat2saMulticastProfileRuleTable 1 }

SM8TAT2SAMulticastProfileRuleEntry ::= SEQUENCE {
   sm8tat2saMulticastProfileRuleIndex Integer32,
   sm8tat2saMulticastProfileRuleProfileName DisplayString,
   sm8tat2saMulticastProfileRuleEntryName DisplayString,
   sm8tat2saMulticastProfileRuleAction INTEGER,
   sm8tat2saMulticastProfileRuleLog INTEGER,
   sm8tat2saMulticastProfileRuleRowStatus RowStatus
}

sm8tat2saMulticastProfileRuleIndex OBJECT-TYPE
   SYNTAX Integer32 (1..32)
   MAX-ACCESS not-accessible
   STATUS current
   DESCRIPTION
       "Multicast Profile Rule Table Index. "
   ::= { sm8tat2saMulticastProfileRuleEntry 1 }

sm8tat2saMulticastProfileRuleProfileName OBJECT-TYPE
   SYNTAX DisplayString
   MAX-ACCESS read-create
   STATUS current
   DESCRIPTION
       "Multicast Profile Rule Table Profile Name. "
   ::= { sm8tat2saMulticastProfileRuleEntry 2 }

sm8tat2saMulticastProfileRuleEntryName OBJECT-TYPE
   SYNTAX DisplayString
   MAX-ACCESS read-create
   STATUS current
   DESCRIPTION
       "Multicast Profile Rule Table Entry Name. "
   ::= { sm8tat2saMulticastProfileRuleEntry 3 }

sm8tat2saMulticastProfileRuleAction OBJECT-TYPE
   SYNTAX INTEGER { deny(0), permit(1) }
   MAX-ACCESS read-create
   STATUS current
   DESCRIPTION
       "Multicast Profile Rule Table Action. "
   ::= { sm8tat2saMulticastProfileRuleEntry 4 }

sm8tat2saMulticastProfileRuleLog OBJECT-TYPE
   SYNTAX INTEGER { disable(0), enable(1) }
   MAX-ACCESS read-create
   STATUS current
   DESCRIPTION
       "Multicast Profile Rule Table Log. "
   ::= { sm8tat2saMulticastProfileRuleEntry 5 }

sm8tat2saMulticastProfileRuleRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm8tat2saMulticastProfileRuleEntry 6 }

-- *************************************************************
-- Start sm8tat2saSystemAccount group
-- *************************************************************
sm8tat2saConfigurationConformance OBJECT IDENTIFIER ::= { sm8tat2saConfiguration 200 }
sm8tat2saConfigurationCompliances OBJECT IDENTIFIER ::= { sm8tat2saConfigurationConformance 1 }
sm8tat2saConfigurationGroups OBJECT IDENTIFIER ::= { sm8tat2saConfigurationConformance 2 }

sm8tat2saPortGroup OBJECT-GROUP
    OBJECTS {
    --sm8tat2saPort
      --sm8tat2saPortConfigurationTable
        sm8tat2saPortConfPortMedia,
        sm8tat2saPortConfLink,
        sm8tat2saPortConfCurrentSpeed,
        sm8tat2saPortConfSpeed,
        sm8tat2saPortConfCurrentFlowControlRx,
        sm8tat2saPortConfCurrentFlowControlTx,
        sm8tat2saPortConfFlowControl,
        sm8tat2saPortConfDescription,

      --sm8tat2saSFPInfoTable
        sm8tat2saSFPInfoPort,
        sm8tat2saSFPConnectorType,
        sm8tat2saSFPFiberType,
        sm8tat2saSFPTxCentralWavelength,
        sm8tat2saSFPBitRate,
        sm8tat2saSFPVendorOUI,
        sm8tat2saSFPVendorName,
        sm8tat2saSFPVendorPN,
        sm8tat2saSFPVendorRev,
        sm8tat2saSFPVendorSN,
        sm8tat2saSFPDateCode,
        sm8tat2saSFPTemperature,
        sm8tat2saSFPVcc,
        sm8tat2saSFPMon1Bias,
        sm8tat2saSFPMon2TxPWR,
        sm8tat2saSFPMon3RxPWR,

      --sm8tat2saPortEnergyEfficientTable
        sm8tat2saPortEnergyEfficientMode

        ,sm8tat2saPortMaximumFrameSize

    }
    STATUS current
    DESCRIPTION
        "The collection of objects which are used to
        indicate port information."
    ::= { sm8tat2saConfigurationGroups 1 }

sm8tat2saEventConfigGroup OBJECT-GROUP
    OBJECTS {
    --sm8tat2saEventConfig
      --sm8tat2saEventConfigTable
        sm8tat2saEventConfigGroupName,
        sm8tat2saEventConfigSeverityLevel,
        sm8tat2saEventConfigSyslog,
        sm8tat2saEventConfigTrap,
        sm8tat2saEventConfigSMTP
    }
    STATUS current
    DESCRIPTION
        "The collection of objects which are used to
        indicate event config information."
    ::= { sm8tat2saConfigurationGroups 7 }

sm8tat2saSMTPGroup OBJECT-GROUP
    OBJECTS {
    --sm8tat2saSMTP
        sm8tat2saSMTPMailServer,
        sm8tat2saSMTPUserName,
        sm8tat2saSMTPPassword,
        sm8tat2saSMTPSender,
        sm8tat2saSMTPReturnPath,
        sm8tat2saSMTPEmailAddress1,
        sm8tat2saSMTPEmailAddress2,
        sm8tat2saSMTPEmailAddress3,
        sm8tat2saSMTPEmailAddress4,
        sm8tat2saSMTPEmailAddress5,
        sm8tat2saSMTPEmailAddress6
    }
    STATUS current
    DESCRIPTION
        "The collection of objects which are used to
        indicate event config information."
    ::= { sm8tat2saConfigurationGroups 8 }

sm8tat2saQosConfGroup OBJECT-GROUP
    OBJECTS {
    --sm8tat2saQosConf
      --sm8tat2saQosGobalSettings
        sm8tat2saQosGobalSettingsTrustMode,

      --sm8tat2saQosPortSettings
        --sm8tat2saQosPortSettingsTable
        sm8tat2saQosPortSettingsMode,
        sm8tat2saQosPortSettingsDefaultCoS,
        sm8tat2saQosPortSettingsSourceCoS,
        sm8tat2saQosPortSettingsRemarkCoS,
        sm8tat2saQosPortSettingsRemarkDSCP,
        sm8tat2saQosPortSettingsRemarkIPPrecedence,

      --sm8tat2saQosPortPolicing
        --sm8tat2saQosPortPolicingTable
        sm8tat2saQosPortPolicingEnabled,
        sm8tat2saQosPortPolicingRate,

      --sm8tat2saQosPortShaper
        --sm8tat2saQosQueueShaperTable
        sm8tat2saQosQueueShaperEnabled,
        sm8tat2saQosQueueShaperRate,
        --sm8tat2saQosPortShaperTable
        sm8tat2saQosPortShaperEnabled,
        sm8tat2saQosPortShaperRate,

      --sm8tat2saQosStormControl
        --sm8tat2saQosStormControlTable
        sm8tat2saQosStormControlBroadcastEnabled,
        sm8tat2saQosStormControlBraoadcastRate,
        sm8tat2saQosStormControlUnknownMulticastEnabled,
        sm8tat2saQosStormControlUnknownMulticastRate,
        sm8tat2saQosStormControlUnknownUnicastEnabled,
        sm8tat2saQosStormControlUnknownUnicastRate,

      --sm8tat2saQosPortScheduler
        --sm8tat2saQosPortSchedulerTable
        sm8tat2saQosSchedulerMode,
        sm8tat2saQosSchedulerWeight,

      --sm8tat2saQosCoS8021pMapping
        --sm8tat2saQosCoS8021pMappingTable
        sm8tat2saQosCoS8021pMappingQueueID,

      --sm8tat2saQosCoS8021pRemarking
        --sm8tat2saQosCoS8021pRemarkingTable
        sm8tat2saQosCoS8021pRemarkingCoS8021p,

      --sm8tat2saQosIPPrecedenceMapping
        --sm8tat2saQosIPPrecedenceMappingTable
        sm8tat2saQosIPPrecedenceMappingQueueID,

      --sm8tat2saQosIPPrecedenceRemarking
        --sm8tat2saQosIPPrecedenceRemarkingTable
        sm8tat2saQosIPPrecedenceRemarkingIPPrecedence,

      --sm8tat2saQosDSCPMapping
        --sm8tat2saQosDSCPMappingTable
        sm8tat2saQosDSCPMappingQueueID,

      --sm8tat2saQosDSCPRemarking
        --sm8tat2saQosDSCPRemarkingTable
        sm8tat2saQosDSCPRemarkingDSCP
    }
    STATUS current
    DESCRIPTION
        "The collection of objects which are used to
        indicate qos config information."
    ::= { sm8tat2saConfigurationGroups 10 }

sm8tat2saLoopProtectionGroup OBJECT-GROUP
    OBJECTS {
    --sm8tat2saLoopProtection
      --sm8tat2saLoopProtectionConfig
        sm8tat2saLoopProtectionGlobalEnable,
        sm8tat2saLoopProtectionTranmisstionTime,
        sm8tat2saLoopProtectionShutdownTime,

        --sm8tat2saLoopProtectionConfigurationTable
        sm8tat2saLoopProtectionConfEnable,
        sm8tat2saLoopProtectionConfAction,
        sm8tat2saLoopProtectionConfTxmode,

        --sm8tat2saLoopProtectionStatusTable
        sm8tat2saLoopProtectionStatusLoops,
        sm8tat2saLoopProtectionStatusStatus,
        sm8tat2saLoopProtectionStatusLoop,
        sm8tat2saLoopProtectionStatusTimeLastLoop
    }
    STATUS current
    DESCRIPTION
        "The collection of objects which are used to
        indicate loop protection information."
    ::= { sm8tat2saConfigurationGroups 12 }

sm8tat2saPoeGroup OBJECT-GROUP
    OBJECTS {
    --sm8tat2saPoe
      --sm8tat2saPoeConfiguration
        sm8tat2saPrimaryPowerSupply,
        sm8tat2saCapacitorDetection,

        --sm8tat2saPoePortConfigTable
        sm8tat2saPoePortConfigPoeMode,
        sm8tat2saPoePortConfigPoeSchedule,
        sm8tat2saPoePortConfigPriority,
        sm8tat2saPoePortConfigMaximumPower,

        sm8tat2saPoEManagementMode,

        sm8tat2saPoEAlwaysOnPoE,

        --sm8tat2saPoeStatus
        --sm8tat2saPoeStatusTable
        sm8tat2saPoeStatusPDClass,
        sm8tat2saPoeStatusPowerAllocated,
        sm8tat2saPoeStatusPowerUsed,
        sm8tat2saPoeStatusCurrentUsed,
        sm8tat2saPoeStatusPriority,
        sm8tat2saPoeStatusPortStatus,

      --sm8tat2saPoePowerDelay
        --sm8tat2saPoePowerDelayTable
        sm8tat2saPoePowerDelayMode,
        sm8tat2saPoePowerDelayTime,

      --sm8tat2saPoeAutoCheck
        sm8tat2saPoeAutoCheckPingCheck,

        --sm8tat2saPoeAutoCheckTable
        sm8tat2saPoeAutoCheckPingIPAddress,
        sm8tat2saPoeAutoCheckStartupTime,
        sm8tat2saPoeAutoCheckIntervalTime,
        sm8tat2saPoeAutoCheckRetryTime,
        sm8tat2saPoeAutoCheckFailureLog,
        sm8tat2saPoeAutoCheckFailureAction,
        sm8tat2saPoeAutoCheckRebootTime,
        sm8tat2saPoeAutoCheckMaxRebootTimes,

      --sm8tat2saPoeSchedulingProfile
        --sm8tat2saPoeSchedulingNameTable
        sm8tat2saPoeSchedulingName,

        --sm8tat2saPoeSchedulingTimeTable
        sm8tat2saPoeSchedulingTimeStartTimeHour,
        sm8tat2saPoeSchedulingTimeStartTimeMinute,
        sm8tat2saPoeSchedulingTimeEndTimeHour,
        sm8tat2saPoeSchedulingTimeEndTimeMinute
    }
    STATUS current
    DESCRIPTION
        "The collection of objects which are used to
        indicate PoE information."
    ::= { sm8tat2saConfigurationGroups 13 }

sm8tat2saMstpGroupGroup OBJECT-GROUP
    OBJECTS {
    --sm8tat2saMstpGroup
      --sm8tat2saMstpMiscellaneousConfig
        sm8tat2saMstpMibGlobalEnable,
        sm8tat2saMstpMstiAddVlans
    }
    STATUS current
    DESCRIPTION
        "The collection of objects which are used to
        indicate mstp information."
    ::= { sm8tat2saConfigurationGroups 18 }

sm8tat2saLinkAggregationGroupGroup OBJECT-GROUP
    OBJECTS {
    --sm8tat2saLinkAggregationGroup
      --sm8tat2saLagMiscellaneousConfig,
        sm8tat2saLagTrafficDistributionMode,
        sm8tat2saLagLacpSystemPriority,

      --sm8tat2saLagPortTable
        sm8tat2saLagPortLacpAggAdminKey,
        sm8tat2saLagPortStaticAggAdminKey,
        sm8tat2saLagPortLacpActivity,
        sm8tat2saLagPortLacpTimeout,
        sm8tat2saLagPortAggregatorPort,
        sm8tat2saLagPortReadyState,

      --sm8tat2saLagAggregatorTable
        sm8tat2saLagPortAggregationMethod,
        sm8tat2saLagAggregatorMemberPorts,
        sm8tat2saLagAggregatorReadyPorts,

      --sm8tat2saLagLacpPortTable
        sm8tat2saLagLacpActorOperKey,
        sm8tat2saLagLacpPartnerPort,
        sm8tat2saLagLacpPartnerOperKey,
        sm8tat2saLagLacpActorSystemPriority,
        sm8tat2saLagLacpActorSystemID,
        sm8tat2saLagLacpPartnerSystemPriority,
        sm8tat2saLagLacpPartnerSystemID,
        sm8tat2saLagLacpPortReadyState
    }
    STATUS current
    DESCRIPTION
        "The collection of objects which are used to
        indicate link aggregation information."
    ::= { sm8tat2saConfigurationGroups 23 }

sm8tat2saIpmcGroup OBJECT-GROUP
    OBJECTS {
    --sm8tat2saIpmc
      --sm8tat2saIgmpConfig
        sm8tat2saIgmpSnoopingEnable,
        sm8tat2saIgmpUnkownFlooding,
        sm8tat2saIgmpSsmRangeAddress,
        sm8tat2saIgmpSsmRangeLen,
        sm8tat2saIgmpProxyEnable,

        --sm8tat2saIgmpConfigurationTable
        sm8tat2saIgmpConfRouterPort,
        sm8tat2saIgmpConfFastLeave,
        sm8tat2saIgmpConfThrottling,
        sm8tat2saIgmpConfProfile,

      --sm8tat2saIgmpVlanConfiguration
        --sm8tat2saIgmpVlanConfigTable
        sm8tat2saIgmpVlanVid,
        sm8tat2saIgmpVlanSnoopingMode,
        sm8tat2saIgmpVlanQuerier,
        sm8tat2saIgmpVlanCompatibility,
        sm8tat2saIgmpVlanRV,
        sm8tat2saIgmpVlanQI,
        sm8tat2saIgmpVlanQRI,
        sm8tat2saIgmpVlanLLQI,
        sm8tat2saIgmpVlanURI,
        sm8tat2saIgmpVlanRowStatus,

      --sm8tat2saIgmpVlanStatus
        --sm8tat2saIgmpVlanStatusTable
        sm8tat2saIgmpVlanStatusVid,
        sm8tat2saIgmpVlanStatusQuerierVersion,
        sm8tat2saIgmpVlanStatusHostVersion,
        sm8tat2saIgmpVlanStatusQuerierStatus,
        sm8tat2saIgmpVlanStatusQuerierTransmitted,
        sm8tat2saIgmpVlanStatusQuerierReceived,
        sm8tat2saIgmpVlanStatusV1ReportsReceived,
        sm8tat2saIgmpVlanStatusV2ReportsReceived,
        sm8tat2saIgmpVlanStatusV3ReportsReceived,
        sm8tat2saIgmpVlanStatusV2LeavesReceived,

        --sm8tat2saIgmpRouterPortStatusTable
        sm8tat2saIgmpRouterPortStatus,

      --sm8tat2saIgmpGroupsInformation
        --sm8tat2saIgmpGroupsTable
        sm8tat2saIgmpGroupsVid,
        sm8tat2saIgmpGroupsAddress,
        sm8tat2saIgmpGroupsPort,

      --sm8tat2saIgmpSFMInformation
        --sm8tat2saIgmpSFMTable
        sm8tat2saIgmpSFMVid,
        sm8tat2saIgmpSFMAddress,
        sm8tat2saIgmpSFMPort,
        sm8tat2saIgmpSFMMode,
        sm8tat2saIgmpSFMSourceAddress,
        sm8tat2saIgmpSFMType,

      --sm8tat2saMldConfig
        sm8tat2saMldSnoopingEnable,
        sm8tat2saMldUnkownFlooding,
        sm8tat2saMldSsmRangeAddress,
        sm8tat2saMldSsmRangeLen,
        sm8tat2saMldProxyEnable,

        --sm8tat2saMldConfigurationTable
        sm8tat2saMldConfRouterPort,
        sm8tat2saMldConfFastLeave,
        sm8tat2saMldConfThrottling,
        sm8tat2saMldConfProfile,

      --sm8tat2saMldVlanConfiguration
        --sm8tat2saMldVlanConfigTable
        sm8tat2saMldVlanVid,
        sm8tat2saMldVlanSnoopingMode,
        sm8tat2saMldVlanQuerier,
        sm8tat2saMldVlanCompatibility,
        sm8tat2saMldVlanRV,
        sm8tat2saMldVlanQI,
        sm8tat2saMldVlanQRI,
        sm8tat2saMldVlanLLQI,
        sm8tat2saMldVlanURI,
        sm8tat2saMldVlanRowStatus,

      --sm8tat2saMldVlanStatus
        --sm8tat2saMldVlanStatusTable
        sm8tat2saMldVlanStatusVid,
        sm8tat2saMldVlanStatusQuerierVersion,
        sm8tat2saMldVlanStatusHostVersion,
        sm8tat2saMldVlanStatusQuerierStatus,
        sm8tat2saMldVlanStatusQuerierTransmitted,
        sm8tat2saMldVlanStatusQuerierReceived,
        sm8tat2saMldVlanStatusV1ReportsReceived,
        sm8tat2saMldVlanStatusV2ReportsReceived,
        sm8tat2saMldVlanStatusV1LeavesReceived,

        --sm8tat2saMldRouterPortStatusTable
        sm8tat2saMldRouterPortStatus,

      --sm8tat2saMldGroupsInformation
        --sm8tat2saMldGroupsTable
        sm8tat2saMldGroupsVid,
        sm8tat2saMldGroupsAddress,
        sm8tat2saMldGroupsPort,

      --sm8tat2saMldSFMInformation
        --sm8tat2saMldSFMTable
        sm8tat2saMldSFMVid,
        sm8tat2saMldSFMAddress,
        sm8tat2saMldSFMPort,
        sm8tat2saMldSFMMode,
        sm8tat2saMldSFMSourceAddress,
        sm8tat2saMldSFMType,

      --sm8tat2saMulticastFilteringProfile
        sm8tat2saMulticastProfileEnable,

        --sm8tat2saMulticastProfileTable
        sm8tat2saMulticastProfileName,
        sm8tat2saMulticastProfileDescription,
        sm8tat2saMulticastProfileRowStatus,

        --sm8tat2saFilteringAddressTable
        sm8tat2saFilteringAddressEntryName,
        sm8tat2saFilteringAddressStartAddress,
        sm8tat2saFilteringAddressEndAddress,
        sm8tat2saFilteringAddressRowStatus,

        --sm8tat2saMulticastProfileRuleTable
        sm8tat2saMulticastProfileRuleProfileName,
        sm8tat2saMulticastProfileRuleEntryName,
        sm8tat2saMulticastProfileRuleAction,
        sm8tat2saMulticastProfileRuleLog,
        sm8tat2saMulticastProfileRuleRowStatus
    }
    STATUS current
    DESCRIPTION
        "The collection of objects which are used to
        indicate ipmc information."
    ::= { sm8tat2saConfigurationGroups 24 }

sm8tat2saConfigurationCompliance MODULE-COMPLIANCE
    STATUS current
    DESCRIPTION
        "The compliance statement for devices supporting configuration."
    MODULE
        MANDATORY-GROUPS {
            sm8tat2saPortGroup,
            sm8tat2saEventConfigGroup,
            sm8tat2saSMTPGroup,
            sm8tat2saQosConfGroup,
            sm8tat2saLoopProtectionGroup,
            sm8tat2saPoeGroup,
            sm8tat2saMstpGroupGroup,
            sm8tat2saLinkAggregationGroupGroup,
            sm8tat2saIpmcGroup
        }
    ::= { sm8tat2saConfigurationCompliances 1 }

-- ================================================================================================================

sm8tat2saSecurity OBJECT IDENTIFIER ::= { sm8tat2saProductId 3 }

-- *************************************************************
-- Start sm8tat2saIPSourceGuard group
-- *************************************************************
sm8tat2saIPSourceGuard OBJECT IDENTIFIER ::= { sm8tat2saSecurity 1 }

sm8tat2saIPSourceGuardMode OBJECT-TYPE
   SYNTAX INTEGER {off(0), on(1)}
   MAX-ACCESS read-write
   STATUS current
   DESCRIPTION
      "Enable the Global IP Source Guard or disable the Global IP Source Guard.
        default: 0,
        0: off(diable,
        1: on(enable)"
   ::= { sm8tat2saIPSourceGuard 1 }

sm8tat2saIPSourceGuardPortConfigTable OBJECT-TYPE
   SYNTAX SEQUENCE OF SM8TAT2SAIPSourceGuardPortConfigEntry
   MAX-ACCESS not-accessible
   STATUS current
   DESCRIPTION
      "The IP Source Guard Port Configuration Table.
       INDEX for this table is ifIndex which is equivalent to the panel port number."
   ::= { sm8tat2saIPSourceGuard 2 }

sm8tat2saIPSourceGuardPortConfigEntry OBJECT-TYPE
   SYNTAX SM8TAT2SAIPSourceGuardPortConfigEntry
   MAX-ACCESS not-accessible
   STATUS current
   DESCRIPTION
      "The IP Source Guard Port Configuration Entry."
   INDEX { ifIndex }
   ::= { sm8tat2saIPSourceGuardPortConfigTable 1 }

SM8TAT2SAIPSourceGuardPortConfigEntry ::= SEQUENCE {
   sm8tat2saIPSourceGuardPortConfigMode AdminMode,
   sm8tat2saIPSourceGuardPortMaxDynamicClients Integer32
}

sm8tat2saIPSourceGuardPortConfigMode OBJECT-TYPE
   SYNTAX AdminMode
   MAX-ACCESS read-write
   STATUS current
   DESCRIPTION
      "Specify IP Source Guard is enabled on which ports."
   ::= { sm8tat2saIPSourceGuardPortConfigEntry 1 }

sm8tat2saIPSourceGuardPortMaxDynamicClients OBJECT-TYPE
   SYNTAX Integer32(0..2|65535)
   MAX-ACCESS read-write
   STATUS current
   DESCRIPTION
      "Specify the maximum number of dynamic clients that can
       be learned on given port.
       default: 65535
       0~2: Max Dynamic clients
       65535:Unlimited "
   ::= { sm8tat2saIPSourceGuardPortConfigEntry 2 }

sm8tat2saIPSourceGuardStaticTable OBJECT-TYPE
   SYNTAX SEQUENCE OF SM8TAT2SAIPSourceGuardStaticEntry
   MAX-ACCESS not-accessible
   STATUS current
   DESCRIPTION
      "The IP Source Guard Static Table."
   ::= { sm8tat2saIPSourceGuard 3 }

sm8tat2saIPSourceGuardStaticEntry OBJECT-TYPE
   SYNTAX SM8TAT2SAIPSourceGuardStaticEntry
   MAX-ACCESS not-accessible
   STATUS current
   DESCRIPTION
      "The IP Source Guard Static Entry."
   INDEX { sm8tat2saIPSourceGuardStaticIndex }
   ::= { sm8tat2saIPSourceGuardStaticTable 1 }

SM8TAT2SAIPSourceGuardStaticEntry ::= SEQUENCE {
   sm8tat2saIPSourceGuardStaticIndex Integer32,
   sm8tat2saIPSourceGuardStaticPort Integer32,
   sm8tat2saIPSourceGuardStaticIPAddress DisplayString,
   sm8tat2saIPSourceGuardStaticMACAddress DisplayString,
   sm8tat2saIPSourceGuardStaticRowStatus RowStatus
}

sm8tat2saIPSourceGuardStaticIndex OBJECT-TYPE
   SYNTAX Integer32 (1..4095)
   MAX-ACCESS not-accessible
   STATUS current
   DESCRIPTION
      "The entry of table."
   ::= { sm8tat2saIPSourceGuardStaticEntry 1 }

sm8tat2saIPSourceGuardStaticPort OBJECT-TYPE
   SYNTAX Integer32 (1..26)
   MAX-ACCESS read-create
   STATUS current
   DESCRIPTION
      "The port number of table. range: 1 - port number."
   ::= { sm8tat2saIPSourceGuardStaticEntry 2 }

sm8tat2saIPSourceGuardStaticIPAddress OBJECT-TYPE
   SYNTAX DisplayString
   MAX-ACCESS read-create
   STATUS current
   DESCRIPTION
      "IP address allowed for doing IP source guard."
   ::= { sm8tat2saIPSourceGuardStaticEntry 3 }

sm8tat2saIPSourceGuardStaticMACAddress OBJECT-TYPE
   SYNTAX DisplayString
   MAX-ACCESS read-create
   STATUS current
   DESCRIPTION
      "Allowed Source MAC address, format: 0a 1b 2c 3d 4e 5f."
   ::= { sm8tat2saIPSourceGuardStaticEntry 4 }

sm8tat2saIPSourceGuardStaticRowStatus OBJECT-TYPE
   SYNTAX RowStatus
   MAX-ACCESS read-create
   STATUS current
   DESCRIPTION
      "This object indicates the status of this entry, and is
       used to create/delete entries. Any object in an entry of
       this table may be modified while the value of the
       corresponding instance of this object is active(1).
       createAndGo, notReady not supported."
   ::= { sm8tat2saIPSourceGuardStaticEntry 5 }

sm8tat2saIPSourceGuardDynamicTable OBJECT-TYPE
   SYNTAX SEQUENCE OF SM8TAT2SAIPSourceGuardDynamicEntry
   MAX-ACCESS not-accessible
   STATUS current
   DESCRIPTION
      "The IP Source Guard Dynamic Table."
   ::= { sm8tat2saIPSourceGuard 4 }

sm8tat2saIPSourceGuardDynamicEntry OBJECT-TYPE
   SYNTAX SM8TAT2SAIPSourceGuardDynamicEntry
   MAX-ACCESS not-accessible
   STATUS current
   DESCRIPTION
      "The IP Source Guard Dynamic Entry."
   INDEX { sm8tat2saIPSourceGuardDynamicIndex }
   ::= { sm8tat2saIPSourceGuardDynamicTable 1 }

SM8TAT2SAIPSourceGuardDynamicEntry ::= SEQUENCE {
   sm8tat2saIPSourceGuardDynamicIndex Integer32,
   sm8tat2saIPSourceGuardDynamicPort Integer32,
   sm8tat2saIPSourceGuardDynamicIPAddress DisplayString,
   sm8tat2saIPSourceGuardDynamicMACAddress DisplayString
}

sm8tat2saIPSourceGuardDynamicIndex OBJECT-TYPE
   SYNTAX Integer32 (1..4095)
   MAX-ACCESS not-accessible
   STATUS current
   DESCRIPTION
      "The entry of table."
   ::= { sm8tat2saIPSourceGuardDynamicEntry 1 }

sm8tat2saIPSourceGuardDynamicPort OBJECT-TYPE
   SYNTAX Integer32 (1..26)
   MAX-ACCESS read-only
   STATUS current
   DESCRIPTION
      "The logical port for the settings."
   ::= { sm8tat2saIPSourceGuardDynamicEntry 2 }

sm8tat2saIPSourceGuardDynamicIPAddress OBJECT-TYPE
   SYNTAX DisplayString
   MAX-ACCESS read-only
   STATUS current
   DESCRIPTION
      "Allowed Source IP address."
   ::= { sm8tat2saIPSourceGuardDynamicEntry 3 }

sm8tat2saIPSourceGuardDynamicMACAddress OBJECT-TYPE
   SYNTAX DisplayString
   MAX-ACCESS read-only
   STATUS current
   DESCRIPTION
      "Allowed Source MAC address."
   ::= { sm8tat2saIPSourceGuardDynamicEntry 4 }

-- *************************************************************
-- Start sm8tat2saARPInspection group
-- *************************************************************
sm8tat2saARPInspection OBJECT IDENTIFIER ::= { sm8tat2saSecurity 2 }

sm8tat2saARPInspectionMode OBJECT-TYPE
   SYNTAX INTEGER {off(0), on(1)}
   MAX-ACCESS read-write
   STATUS current
   DESCRIPTION
      "Enable the Global ARP Inspection or disable the Global ARP Inspection."
   ::= { sm8tat2saARPInspection 1 }

sm8tat2saARPPortConfigTable OBJECT-TYPE
   SYNTAX SEQUENCE OF SM8TAT2SAARPPortConfigEntry
   MAX-ACCESS not-accessible
   STATUS current
   DESCRIPTION
      "The ARP Port Configuration Table."
   ::= { sm8tat2saARPInspection 2 }

sm8tat2saARPPortConfigEntry OBJECT-TYPE
   SYNTAX SM8TAT2SAARPPortConfigEntry
   MAX-ACCESS not-accessible
   STATUS current
   DESCRIPTION
      "The ARP Port Configuration Entry."
   INDEX { ifIndex }
   ::= { sm8tat2saARPPortConfigTable 1 }

SM8TAT2SAARPPortConfigEntry ::= SEQUENCE {
   sm8tat2saARPPortConfigMode AdminMode,
   sm8tat2saARPPortConfigCheckVLAN AdminMode,
   sm8tat2saARPPortConfigLogType INTEGER
}

sm8tat2saARPPortConfigMode OBJECT-TYPE
   SYNTAX AdminMode
   MAX-ACCESS read-write
   STATUS current
   DESCRIPTION
      "Specify ARP Inspection is enabled on which ports."
   ::= { sm8tat2saARPPortConfigEntry 1 }

sm8tat2saARPPortConfigCheckVLAN OBJECT-TYPE
   SYNTAX AdminMode
   MAX-ACCESS read-write
   STATUS current
   DESCRIPTION
      "When the setting of 'Check VLAN' is disabled, the log type of ARP Inspection will refer to the port setting.
       And the setting of 'Check VLAN' is enabled, the log type of ARP Inspection will refer to the VLAN setting."
   ::= { sm8tat2saARPPortConfigEntry 2 }

sm8tat2saARPPortConfigLogType OBJECT-TYPE
   SYNTAX INTEGER { none(0), deny(1), permit(2), all(3) }
   MAX-ACCESS read-write
   STATUS current
   DESCRIPTION
      "The log type of ARP Inspection will refer to the port setting.
       0: none,
       1: deny,
       2: permit,
       3: all,
       range: 0-3."
   ::= { sm8tat2saARPPortConfigEntry 3 }

sm8tat2saARPVlanConfigTable OBJECT-TYPE
   SYNTAX SEQUENCE OF SM8TAT2SAARPVlanConfigEntry
   MAX-ACCESS not-accessible
   STATUS current
   DESCRIPTION
      "The ARP Vlan Configuration Table."
   ::= { sm8tat2saARPInspection 3 }

sm8tat2saARPVlanConfigEntry OBJECT-TYPE
   SYNTAX SM8TAT2SAARPVlanConfigEntry
   MAX-ACCESS not-accessible
   STATUS current
   DESCRIPTION
      "The ARP Vlan Configuration Entry."
   INDEX { sm8tat2saARPVlanConfigIndex }
   ::= { sm8tat2saARPVlanConfigTable 1 }

SM8TAT2SAARPVlanConfigEntry ::= SEQUENCE {
   sm8tat2saARPVlanConfigIndex Integer32,
   sm8tat2saARPVlanConfigVlanID Integer32,
   sm8tat2saARPVlanConfigLogType INTEGER,
   sm8tat2saARPVlanConfigRowStatus RowStatus
}

sm8tat2saARPVlanConfigIndex OBJECT-TYPE
   SYNTAX Integer32 (1..4095)
   MAX-ACCESS not-accessible
   STATUS current
   DESCRIPTION
      "The entry of table."
   ::= { sm8tat2saARPVlanConfigEntry 1 }

sm8tat2saARPVlanConfigVlanID OBJECT-TYPE
   SYNTAX Integer32(1..4095)
   MAX-ACCESS read-create
   STATUS current
   DESCRIPTION
      "Specify ARP Inspection is enabled on which VLANs.
       range: 1 - 4095."
   ::= { sm8tat2saARPVlanConfigEntry 2 }

sm8tat2saARPVlanConfigLogType OBJECT-TYPE
   SYNTAX INTEGER {none(0), deny(1), permit(2), all(3)}
   MAX-ACCESS read-create
   STATUS current
   DESCRIPTION
      "The log type also can be configured on per VLAN setting.
       0: none,
       1: deny,
       2: permit,
       3: all,
       range: 0-3."
   ::= { sm8tat2saARPVlanConfigEntry 3 }

sm8tat2saARPVlanConfigRowStatus OBJECT-TYPE
   SYNTAX RowStatus
   MAX-ACCESS read-create
   STATUS current
   DESCRIPTION
      "This object indicates the status of this entry, and is used to create/delete entries.
       Any object in an entry of this table may be modified while the value of the corresponding instance of this object is active(1).
       createAndGo, notReady not supported."
   ::= { sm8tat2saARPVlanConfigEntry 4 }

sm8tat2saARPStaticTable OBJECT-TYPE
   SYNTAX SEQUENCE OF SM8TAT2SAARPStaticEntry
   MAX-ACCESS not-accessible
   STATUS current
   DESCRIPTION
      "The ARP Static Table."
   ::= { sm8tat2saARPInspection 4 }

sm8tat2saARPStaticEntry OBJECT-TYPE
   SYNTAX SM8TAT2SAARPStaticEntry
   MAX-ACCESS not-accessible
   STATUS current
   DESCRIPTION
      "The ARP Static Entry."
   INDEX { sm8tat2saARPStaticIndex }
   ::= { sm8tat2saARPStaticTable 1 }

SM8TAT2SAARPStaticEntry ::= SEQUENCE {
   sm8tat2saARPStaticIndex Integer32,
   sm8tat2saARPStaticPort Integer32,
   sm8tat2saARPStaticVlanID Integer32,
   sm8tat2saARPStaticMACAddress DisplayString,
   sm8tat2saARPStaticIPAddress DisplayString,
   sm8tat2saARPStaticRowStatus RowStatus
}

sm8tat2saARPStaticIndex OBJECT-TYPE
   SYNTAX Integer32 (1..4095)
   MAX-ACCESS not-accessible
   STATUS current
   DESCRIPTION
      "The entry of table."
   ::= { sm8tat2saARPStaticEntry 1 }

sm8tat2saARPStaticPort OBJECT-TYPE
   SYNTAX Integer32 (1..26)
   MAX-ACCESS read-create
   STATUS current
   DESCRIPTION
      "The logical port for the settings."
   ::= { sm8tat2saARPStaticEntry 2 }

sm8tat2saARPStaticVlanID OBJECT-TYPE
   SYNTAX Integer32 (1..4095)
   MAX-ACCESS read-create
   STATUS current
   DESCRIPTION
      "The vlan id for the settings."
   ::= { sm8tat2saARPStaticEntry 3 }

sm8tat2saARPStaticMACAddress OBJECT-TYPE
   SYNTAX DisplayString
   MAX-ACCESS read-create
   STATUS current
   DESCRIPTION
      "Allowed Source MAC address in ARP request packets."
   ::= { sm8tat2saARPStaticEntry 4 }

sm8tat2saARPStaticIPAddress OBJECT-TYPE
   SYNTAX DisplayString
   MAX-ACCESS read-create
   STATUS current
   DESCRIPTION
      "Allowed Source IP address in ARP request packets."
   ::= { sm8tat2saARPStaticEntry 5 }

sm8tat2saARPStaticRowStatus OBJECT-TYPE
   SYNTAX RowStatus
   MAX-ACCESS read-create
   STATUS current
   DESCRIPTION
      "This object indicates the status of this entry, and is used to create/delete entries.
       Any object in an entry of this table may be modified while the value of the corresponding instance of this object is active(1).
       createAndGo, notReady not supported."
   ::= { sm8tat2saARPStaticEntry 6 }

sm8tat2saARPDynamicTable OBJECT-TYPE
   SYNTAX SEQUENCE OF SM8TAT2SAARPDynamicEntry
   MAX-ACCESS not-accessible
   STATUS current
   DESCRIPTION
      "The ARP Dynamic Table."
   ::= { sm8tat2saARPInspection 5 }

sm8tat2saARPDynamicEntry OBJECT-TYPE
   SYNTAX SM8TAT2SAARPDynamicEntry
   MAX-ACCESS not-accessible
   STATUS current
   DESCRIPTION
      "The ARP Dynamic Entry."
   INDEX { sm8tat2saARPDynamicIndex }
   ::= { sm8tat2saARPDynamicTable 1 }

SM8TAT2SAARPDynamicEntry ::= SEQUENCE {
   sm8tat2saARPDynamicIndex Integer32,
   sm8tat2saARPDynamicPort Integer32,
   sm8tat2saARPDynamicVLANId Integer32,
   sm8tat2saARPDynamicMACAddress DisplayString,
   sm8tat2saARPDynamicIPAddress DisplayString
}

sm8tat2saARPDynamicIndex OBJECT-TYPE
   SYNTAX Integer32(1..4095)
   MAX-ACCESS not-accessible
   STATUS current
   DESCRIPTION
      "The entry of table."
   ::= { sm8tat2saARPDynamicEntry 1 }

sm8tat2saARPDynamicPort OBJECT-TYPE
   SYNTAX Integer32(1..255)
   MAX-ACCESS read-only
   STATUS current
   DESCRIPTION
      "Switch Port Number for which the entries are displayed."
   ::= { sm8tat2saARPDynamicEntry 2 }

sm8tat2saARPDynamicVLANId OBJECT-TYPE
   SYNTAX Integer32(1..4095)
   MAX-ACCESS read-only
   STATUS current
   DESCRIPTION
      "VLAN-ID in which the ARP traffic is permitted."
   ::= { sm8tat2saARPDynamicEntry 3 }

sm8tat2saARPDynamicMACAddress OBJECT-TYPE
   SYNTAX DisplayString
   MAX-ACCESS read-only
   STATUS current
   DESCRIPTION
      "User MAC address of the entry."
   ::= { sm8tat2saARPDynamicEntry 4 }

sm8tat2saARPDynamicIPAddress OBJECT-TYPE
   SYNTAX DisplayString
   MAX-ACCESS read-only
   STATUS current
   DESCRIPTION
      "User IP address of the entry."
   ::= { sm8tat2saARPDynamicEntry 5 }

-- *************************************************************
-- Start sm8tat2saDHCPSnooping group
-- *************************************************************
sm8tat2saDHCPSnooping OBJECT IDENTIFIER ::= { sm8tat2saSecurity 3}

sm8tat2saDHCPSnoopingConfiguration OBJECT IDENTIFIER ::= { sm8tat2saDHCPSnooping 1 }

sm8tat2saDHCPSnoopingMode OBJECT-TYPE
   SYNTAX INTEGER {off(0), on(1)}
   MAX-ACCESS read-write
   STATUS current
   DESCRIPTION
      "default: 0
       0: off(diable)
       1: on(enable)"
   ::= { sm8tat2saDHCPSnoopingConfiguration 1 }

sm8tat2saDHCPSnoopingPortModeConfigurationTable OBJECT-TYPE
   SYNTAX SEQUENCE OF SM8TAT2SADHCPSnoopingPortModeConfigurationEntry
   MAX-ACCESS not-accessible
   STATUS current
   DESCRIPTION
       " "
   ::= { sm8tat2saDHCPSnoopingConfiguration 2 }

sm8tat2saDHCPSnoopingPortModeConfigurationEntry OBJECT-TYPE
   SYNTAX SM8TAT2SADHCPSnoopingPortModeConfigurationEntry
   MAX-ACCESS not-accessible
   STATUS current
   DESCRIPTION
       " "
   INDEX { sm8tat2saDHCPSnoopingPortModeConfigurationPort }
   ::= { sm8tat2saDHCPSnoopingPortModeConfigurationTable 1 }

SM8TAT2SADHCPSnoopingPortModeConfigurationEntry ::= SEQUENCE {
   sm8tat2saDHCPSnoopingPortModeConfigurationPort Integer32,
   sm8tat2saDHCPSnoopingPortModeConfigurationMode Integer32
}

sm8tat2saDHCPSnoopingPortModeConfigurationPort OBJECT-TYPE
   SYNTAX Integer32(1..26)
   MAX-ACCESS not-accessible
   STATUS current
   DESCRIPTION
       " "
   ::= { sm8tat2saDHCPSnoopingPortModeConfigurationEntry 1 }

sm8tat2saDHCPSnoopingPortModeConfigurationMode OBJECT-TYPE
   SYNTAX Integer32 (0|1)
   MAX-ACCESS read-write
   STATUS current
   DESCRIPTION
       "default: 1
       0: trust port mode
       1: untrust port mode"
   ::= { sm8tat2saDHCPSnoopingPortModeConfigurationEntry 2 }

sm8tat2saDynamicDHCPSnoopingTable OBJECT-TYPE
   SYNTAX SEQUENCE OF SM8TAT2SADynamicDHCPSnoopingEntry
   MAX-ACCESS not-accessible
   STATUS current
   DESCRIPTION
       " "
   ::= { sm8tat2saDHCPSnooping 2 }

sm8tat2saDynamicDHCPSnoopingEntry OBJECT-TYPE
   SYNTAX SM8TAT2SADynamicDHCPSnoopingEntry
   MAX-ACCESS not-accessible
   STATUS current
   DESCRIPTION
       " "
   INDEX { sm8tat2saDynamicDHCPSnoopingIndex }
   ::= { sm8tat2saDynamicDHCPSnoopingTable 1 }

SM8TAT2SADynamicDHCPSnoopingEntry ::= SEQUENCE {
   sm8tat2saDynamicDHCPSnoopingIndex Integer32,
   sm8tat2saDynamicDHCPSnoopingMACAddress DisplayString,
   sm8tat2saDynamicDHCPSnoopingVLANID Integer32,
   sm8tat2saDynamicDHCPSnoopingPort Integer32,
   sm8tat2saDynamicDHCPSnoopingIPAddress DisplayString,
   sm8tat2saDynamicDHCPSnoopingIPSubnetMask DisplayString,
   sm8tat2saDynamicDHCPSnoopingDHCPServer DisplayString
}

sm8tat2saDynamicDHCPSnoopingIndex OBJECT-TYPE
   SYNTAX Integer32(1..4095)
   MAX-ACCESS not-accessible
   STATUS current
   DESCRIPTION
       " "
   ::= { sm8tat2saDynamicDHCPSnoopingEntry 1 }

sm8tat2saDynamicDHCPSnoopingMACAddress OBJECT-TYPE
   SYNTAX DisplayString
   MAX-ACCESS read-only
   STATUS current
   DESCRIPTION
       " "
   ::= { sm8tat2saDynamicDHCPSnoopingEntry 2 }

sm8tat2saDynamicDHCPSnoopingVLANID OBJECT-TYPE
   SYNTAX Integer32(1..4095)
   MAX-ACCESS read-only
   STATUS current
   DESCRIPTION
       " "
   ::= { sm8tat2saDynamicDHCPSnoopingEntry 3 }

sm8tat2saDynamicDHCPSnoopingPort OBJECT-TYPE
   SYNTAX Integer32(1..26)
   MAX-ACCESS read-only
   STATUS current
   DESCRIPTION
       " "
   ::= { sm8tat2saDynamicDHCPSnoopingEntry 4 }

sm8tat2saDynamicDHCPSnoopingIPAddress OBJECT-TYPE
   SYNTAX DisplayString
   MAX-ACCESS read-only
   STATUS current
   DESCRIPTION
       " "
   ::= { sm8tat2saDynamicDHCPSnoopingEntry 5 }

sm8tat2saDynamicDHCPSnoopingIPSubnetMask OBJECT-TYPE
   SYNTAX DisplayString
   MAX-ACCESS read-only
   STATUS current
   DESCRIPTION
       " "
   ::= { sm8tat2saDynamicDHCPSnoopingEntry 6 }

sm8tat2saDynamicDHCPSnoopingDHCPServer OBJECT-TYPE
   SYNTAX DisplayString
   MAX-ACCESS read-only
   STATUS current
   DESCRIPTION
       " "
   ::= { sm8tat2saDynamicDHCPSnoopingEntry 7 }

sm8tat2saPortSecLimitCtrl OBJECT IDENTIFIER ::= { sm8tat2saSecurity 5}

sm8tat2saPortSecLimitCtrlSystemConf OBJECT IDENTIFIER ::= { sm8tat2saPortSecLimitCtrl 1 }

sm8tat2saPortSecurityMode OBJECT-TYPE
   SYNTAX INTEGER { disable(0), enable(1) }
   MAX-ACCESS read-write
   STATUS current
   DESCRIPTION
       "default: 0
       0: disable
       1: enable "
   ::= { sm8tat2saPortSecLimitCtrlSystemConf 1 }

sm8tat2saPortSecLimitCtrlTable OBJECT-TYPE
   SYNTAX SEQUENCE OF SM8TAT2SAPortSecLimitCtrlEntry
   MAX-ACCESS not-accessible
   STATUS current
   DESCRIPTION
       " "
   ::= { sm8tat2saPortSecLimitCtrlSystemConf 2 }

sm8tat2saPortSecLimitCtrlEntry OBJECT-TYPE
   SYNTAX SM8TAT2SAPortSecLimitCtrlEntry
   MAX-ACCESS not-accessible
   STATUS current
   DESCRIPTION
       " "
   INDEX { sm8tat2saPortSecLimitCtrlPort }
   ::= { sm8tat2saPortSecLimitCtrlTable 1 }

SM8TAT2SAPortSecLimitCtrlEntry ::= SEQUENCE {
   sm8tat2saPortSecLimitCtrlPort Integer32,
   sm8tat2saPortSecLimitCtrlPortMode INTEGER,
   sm8tat2saPortSecLimitCtrlPortLimit Integer32,
   sm8tat2saPortSecLimitCtrlPortAction INTEGER,
   sm8tat2saPortSecLimitCtrlPortState DisplayString,
   sm8tat2saPortSecLimitCtrlPortReOpen INTEGER
}

sm8tat2saPortSecLimitCtrlPort OBJECT-TYPE
   SYNTAX Integer32 (1..4095)
   MAX-ACCESS not-accessible
   STATUS current
   DESCRIPTION
       " "
   ::= { sm8tat2saPortSecLimitCtrlEntry 1 }

sm8tat2saPortSecLimitCtrlPortMode OBJECT-TYPE
   SYNTAX INTEGER { disable(0), enable(1) }
   MAX-ACCESS read-write
   STATUS current
   DESCRIPTION
       "default: 0
       0: disable
       1: enable"
   ::= { sm8tat2saPortSecLimitCtrlEntry 2 }

sm8tat2saPortSecLimitCtrlPortLimit OBJECT-TYPE
   SYNTAX Integer32(1..1024)
   MAX-ACCESS read-write
   STATUS current
   DESCRIPTION
       "default: 4, range: 1-1024"
   ::= { sm8tat2saPortSecLimitCtrlEntry 3 }

sm8tat2saPortSecLimitCtrlPortAction OBJECT-TYPE
   SYNTAX INTEGER { none(0), trap(1), shutdown(2), trapShutdown(3) }
   MAX-ACCESS read-write
   STATUS current
   DESCRIPTION
       "default: 0
       0: none
       1: trap
       2: shutdown
       3: trap&shutdown"
   ::= { sm8tat2saPortSecLimitCtrlEntry 4 }

sm8tat2saPortSecLimitCtrlPortState OBJECT-TYPE
   SYNTAX DisplayString
   MAX-ACCESS read-only
   STATUS current
   DESCRIPTION
       " "
   ::= { sm8tat2saPortSecLimitCtrlEntry 5 }

sm8tat2saPortSecLimitCtrlPortReOpen OBJECT-TYPE
   SYNTAX INTEGER { none(0), reopen(1) }
   MAX-ACCESS read-write
   STATUS current
   DESCRIPTION
       "default: 0
       0: none
       1: reopen"
   ::= { sm8tat2saPortSecLimitCtrlEntry 6 }

sm8tat2saPortSecSwitchStatusTable OBJECT-TYPE
   SYNTAX SEQUENCE OF SM8TAT2SAPortSecSwitchStatusEntry
   MAX-ACCESS not-accessible
   STATUS current
   DESCRIPTION
       " "
   ::= { sm8tat2saPortSecLimitCtrl 2 }

sm8tat2saPortSecSwitchStatusEntry OBJECT-TYPE
   SYNTAX SM8TAT2SAPortSecSwitchStatusEntry
   MAX-ACCESS not-accessible
   STATUS current
   DESCRIPTION
       " "
   INDEX { sm8tat2saPortSecSwitchStatusPort }
   ::= { sm8tat2saPortSecSwitchStatusTable 1 }

SM8TAT2SAPortSecSwitchStatusEntry ::= SEQUENCE {
   sm8tat2saPortSecSwitchStatusPort Integer32,
   sm8tat2saPortSecSwitchStatusState DisplayString,
   sm8tat2saPortSecSwitchStatusMACCountCurrent Integer32
}

sm8tat2saPortSecSwitchStatusPort OBJECT-TYPE
   SYNTAX Integer32 (1..4095)
   MAX-ACCESS not-accessible
   STATUS current
   DESCRIPTION
       " "
   ::= { sm8tat2saPortSecSwitchStatusEntry 1 }

sm8tat2saPortSecSwitchStatusState OBJECT-TYPE
   SYNTAX DisplayString
   MAX-ACCESS read-only
   STATUS current
   DESCRIPTION
       " Shows the current state of the port : Disabled, Ready, Limit Reached, Shutdown. "
   ::= { sm8tat2saPortSecSwitchStatusEntry 2 }

sm8tat2saPortSecSwitchStatusMACCountCurrent OBJECT-TYPE
   SYNTAX Integer32(1..4095)
   MAX-ACCESS read-only
   STATUS current
   DESCRIPTION
       " "
   ::= { sm8tat2saPortSecSwitchStatusEntry 3 }

-- *************************************************************
-- Start sm8tat2saTACACS group
-- *************************************************************
sm8tat2saTACACS OBJECT IDENTIFIER ::= { sm8tat2saSecurity 7 }

sm8tat2saTACACSGlobalConfigTimeout OBJECT-TYPE
   SYNTAX Integer32(1..1000)
   MAX-ACCESS read-write
   STATUS current
   DESCRIPTION
      "Timeout is the number of seconds,to wait for a reply from a TACACS+ server before it is considered to be dead.
        range: 1-1000 seconds, default: 5 seconds."
   ::= { sm8tat2saTACACS 1 }

sm8tat2saTACACSGlobalConfigDeadtime OBJECT-TYPE
   SYNTAX Integer32(0..1440)
   MAX-ACCESS read-write
   STATUS current
   DESCRIPTION
      "The period during which the switch will not send new requests to a server that has failed to respond to a previous request.
       This will stop the switch from continually trying to contact a server that it has already determined as dead.
        range: 0-1440 minutes, default: 0 minutes."
   ::= { sm8tat2saTACACS 2 }

sm8tat2saTACACSGlobalConfigKey OBJECT-TYPE
   SYNTAX DisplayString
   MAX-ACCESS read-write
   STATUS current
   DESCRIPTION
      "The secret key shared between the TACACS+ server and the switch."
   ::= { sm8tat2saTACACS 3 }

sm8tat2saTACACSServerConfigTable OBJECT-TYPE
   SYNTAX SEQUENCE OF SM8TAT2SATACACSServerConfigEntry
   MAX-ACCESS not-accessible
   STATUS current
   DESCRIPTION
      "The TACACS Server configuration Table."
   ::= { sm8tat2saTACACS 4 }

sm8tat2saTACACSServerConfigEntry OBJECT-TYPE
   SYNTAX SM8TAT2SATACACSServerConfigEntry
   MAX-ACCESS not-accessible
   STATUS current
   DESCRIPTION
      "The TACACS Server configuration Entry."
   INDEX { sm8tat2saTACACSServerConfigServerNo }
   ::= { sm8tat2saTACACSServerConfigTable 1 }

SM8TAT2SATACACSServerConfigEntry ::=
SEQUENCE {
   sm8tat2saTACACSServerConfigServerNo Integer32,
   sm8tat2saTACACSServerConfigHostname DisplayString,
   sm8tat2saTACACSServerConfigPort Integer32,
   sm8tat2saTACACSServerConfigTimeout Integer32,
   sm8tat2saTACACSServerConfigKey DisplayString,
   sm8tat2saTACACSServerConfigRowStatus RowStatus
}

sm8tat2saTACACSServerConfigServerNo OBJECT-TYPE
   SYNTAX Integer32(1..5)
   MAX-ACCESS not-accessible
   STATUS current
   DESCRIPTION
      "The TACACS server number.
        max: 5"
   ::= { sm8tat2saTACACSServerConfigEntry 1 }

sm8tat2saTACACSServerConfigHostname OBJECT-TYPE
   SYNTAX DisplayString
   MAX-ACCESS read-create
   STATUS current
   DESCRIPTION
      "The IP address or hostname of the TACACS+ server."
   ::= { sm8tat2saTACACSServerConfigEntry 2 }

sm8tat2saTACACSServerConfigPort OBJECT-TYPE
   SYNTAX Integer32(0..65535)
   MAX-ACCESS read-create
   STATUS current
   DESCRIPTION
      "The TCP port to use on the TACACS+ server for authentication."
   ::= { sm8tat2saTACACSServerConfigEntry 3 }

sm8tat2saTACACSServerConfigTimeout OBJECT-TYPE
   SYNTAX Integer32(1..1000)
   MAX-ACCESS read-create
   STATUS current
   DESCRIPTION
      "This optional setting overrides the global timeout value.
       Leaving it blank will use the global timeout value.
        range: 1-1000."
   ::= { sm8tat2saTACACSServerConfigEntry 4 }

sm8tat2saTACACSServerConfigKey OBJECT-TYPE
   SYNTAX DisplayString
   MAX-ACCESS read-create
   STATUS current
   DESCRIPTION
      "This optional setting overrides the global key.
       Leaving it blank will use the global key. "
   ::= { sm8tat2saTACACSServerConfigEntry 5 }

sm8tat2saTACACSServerConfigRowStatus OBJECT-TYPE
   SYNTAX RowStatus
   MAX-ACCESS read-create
   STATUS current
   DESCRIPTION
      "This object indicates the status of this entry, and is used to create/delete entries.
       Any object in an entry of this table may be modified while the value of the corresponding instance of this object is active(1).
       notReady(3) and createAndGo(4) are not supported."
   ::= { sm8tat2saTACACSServerConfigEntry 6 }

-- *************************************************************
-- Start sm8tat2saAuthMethod group
-- *************************************************************
sm8tat2saAuthMethod OBJECT IDENTIFIER ::= { sm8tat2saSecurity 9 }

sm8tat2saAuthMethodConfigTable OBJECT-TYPE
   SYNTAX SEQUENCE OF SM8TAT2SAAuthMethodConfigEntry
   MAX-ACCESS not-accessible
   STATUS current
   DESCRIPTION
      "The Auth Method Config Table."
   ::= { sm8tat2saAuthMethod 1 }

sm8tat2saAuthMethodConfigEntry OBJECT-TYPE
   SYNTAX SM8TAT2SAAuthMethodConfigEntry
   MAX-ACCESS not-accessible
   STATUS current
   DESCRIPTION
      "The Auth Method Config Entry."
   INDEX { sm8tat2saAuthMethodConfigClient }
   ::= { sm8tat2saAuthMethodConfigTable 1 }

SM8TAT2SAAuthMethodConfigEntry ::=
SEQUENCE {
   sm8tat2saAuthMethodConfigClient INTEGER,
   sm8tat2saAuthMethodConfigMethod1 INTEGER,
   sm8tat2saAuthMethodConfigMethod2 INTEGER,
   sm8tat2saAuthMethodConfigMethod3 INTEGER,
   sm8tat2saAuthMethodConfigServicePort Integer32
}

sm8tat2saAuthMethodConfigClient OBJECT-TYPE

   SYNTAX INTEGER {telnet(2), ssh(3), http(4), https(5)}

   MAX-ACCESS not-accessible
   STATUS current
   DESCRIPTION

      "The Client of the Auth Method Config.  2: telnet, 3: ssh, 4: http, 5: https"

   ::= { sm8tat2saAuthMethodConfigEntry 1 }

sm8tat2saAuthMethodConfigMethod1 OBJECT-TYPE
   SYNTAX INTEGER {no(0) ,local(1) ,radius(2) ,tacacs(3) ,redirect(4)}
   MAX-ACCESS read-write
   STATUS current
   DESCRIPTION
      "Methods that involves remote servers are timed out if the remote servers are offline.Each method is tried from left to
       right and continues until a method either approves or rejects a user.
         0: no, Authentication is disabled and login is not possible.
         1: local(default), Use the local user database on the switch for authentication.
         2: radius, Use remote RADIUS server(s) for authentication.
         3: tacacs+, Use remote TACACS+ server(s) for authentication.
         4: redirect, HTTP redirect HTTPS. "
   ::= { sm8tat2saAuthMethodConfigEntry 2 }

sm8tat2saAuthMethodConfigMethod2 OBJECT-TYPE
   SYNTAX INTEGER {no(0) ,local(1) ,radius(2) ,tacacs(3)}
   MAX-ACCESS read-write
   STATUS current
   DESCRIPTION
      "Methods that involves remote servers are timed out if the remote servers are offline.Each method is tried from left to
       right and continues until a method either approves or rejects a user.
         0: no(default), Authentication is disabled and login is not possible.
         1: local, Use the local user database on the switch for authentication.
         2: radius, Use remote RADIUS server(s) for authentication.
         3: tacacs+, Use remote TACACS+ server(s) for authentication. "
   ::= { sm8tat2saAuthMethodConfigEntry 3 }

sm8tat2saAuthMethodConfigMethod3 OBJECT-TYPE
   SYNTAX INTEGER {no(0), local(1), radius(2), tacacs(3)}
   MAX-ACCESS read-write
   STATUS current
   DESCRIPTION
      "Methods that involves remote servers are timed out if the remote servers are offline.Each method is tried from left to
       right and continues until a method either approves or rejects a user.
         0: no(default), Authentication is disabled and login is not possible.
         1: local, Use the local user database on the switch for authentication.
         2: radius, Use remote RADIUS server(s) for authentication.
         3: tacacs+, Use remote TACACS+ server(s) for authentication. "
   ::= { sm8tat2saAuthMethodConfigEntry 4 }

sm8tat2saAuthMethodConfigServicePort OBJECT-TYPE
   SYNTAX Integer32 (1..65535)
   MAX-ACCESS read-write
   STATUS current
   DESCRIPTION
      "The Service Port of the Auth Method Config Table.  range: 0~65535.  deault: 23(telnet), 22(ssh), 80(http), 443(https)."
   ::= { sm8tat2saAuthMethodConfigEntry 5 }

sm8tat2saCmdAuthMethodConfigTable OBJECT-TYPE
   SYNTAX SEQUENCE OF SM8TAT2SACmdAuthMethodConfigEntry
   MAX-ACCESS not-accessible
   STATUS current
   DESCRIPTION
      "The Command Auth Method Config Table."
   ::= { sm8tat2saAuthMethod 3 }

sm8tat2saCmdAuthMethodConfigEntry OBJECT-TYPE
   SYNTAX SM8TAT2SACmdAuthMethodConfigEntry
   MAX-ACCESS not-accessible
   STATUS current
   DESCRIPTION
      "The Command Auth Method Config Entry."
   INDEX { sm8tat2saCmdAuthMethodConfigClient }
   ::= { sm8tat2saCmdAuthMethodConfigTable 1 }

SM8TAT2SACmdAuthMethodConfigEntry ::=
SEQUENCE {
   sm8tat2saCmdAuthMethodConfigClient INTEGER,
   sm8tat2saCmdAuthMethodConfigMethods INTEGER,
   sm8tat2saCmdAuthMethodConfigCmdLvl Integer32,
   sm8tat2saCmdAuthMethodConfigCfgCmd INTEGER,
   sm8tat2saCmdAuthMethodConfigFallback INTEGER
}

sm8tat2saCmdAuthMethodConfigClient OBJECT-TYPE

   SYNTAX INTEGER {telnet(2), ssh(3)}

   MAX-ACCESS not-accessible
   STATUS current
   DESCRIPTION

      "The Client of the Command Auth Method Config.  2: telnet, 3: ssh"

   ::= { sm8tat2saCmdAuthMethodConfigEntry 1 }

sm8tat2saCmdAuthMethodConfigMethods OBJECT-TYPE
   SYNTAX INTEGER {no(0), tacacs(3)}
   MAX-ACCESS read-write
   STATUS current
   DESCRIPTION
      "Methods that involves remote servers are timed out if the remote servers are offline.Each method is tried from left to
       right and continues until a method either approves or rejects a user.
         0: no(default), Authentication is disabled and login is not possible.
         3: tacacs+, Use remote TACACS+ server(s) for authentication. "
   ::= { sm8tat2saCmdAuthMethodConfigEntry 2 }

sm8tat2saCmdAuthMethodConfigCmdLvl OBJECT-TYPE
   SYNTAX Integer32 (0..15)
   MAX-ACCESS read-write
   STATUS current
   DESCRIPTION
      "The Command Level of the Command Auth Method Config.  range: 0~15, deault: 0. "
   ::= { sm8tat2saCmdAuthMethodConfigEntry 3 }

sm8tat2saCmdAuthMethodConfigCfgCmd OBJECT-TYPE
   SYNTAX AdminMode
   MAX-ACCESS read-write
   STATUS current
   DESCRIPTION
      "Control whether The Config Command of the Command Auth Method Config is enabled or not.  0: disable(default), 1: enable. "
   ::= { sm8tat2saCmdAuthMethodConfigEntry 4 }

sm8tat2saCmdAuthMethodConfigFallback OBJECT-TYPE
   SYNTAX AdminMode
   MAX-ACCESS read-write
   STATUS current
   DESCRIPTION
      "Control whether The Fallback of the Command Auth Method Config is enabled or not.  0: disable(default), 1: enable. "
   ::= { sm8tat2saCmdAuthMethodConfigEntry 5 }

sm8tat2saAcctAuthMethodConfigTable OBJECT-TYPE
   SYNTAX SEQUENCE OF SM8TAT2SAAcctAuthMethodConfigEntry
   MAX-ACCESS not-accessible
   STATUS current
   DESCRIPTION
      "The Accounting Auth Method Config Table."
   ::= { sm8tat2saAuthMethod 4 }

sm8tat2saAcctAuthMethodConfigEntry OBJECT-TYPE
   SYNTAX SM8TAT2SAAcctAuthMethodConfigEntry
   MAX-ACCESS not-accessible
   STATUS current
   DESCRIPTION
      "The Accounting Auth Method Config Entry."
   INDEX { sm8tat2saAcctAuthMethodConfigClient }
   ::= { sm8tat2saAcctAuthMethodConfigTable 1 }

SM8TAT2SAAcctAuthMethodConfigEntry ::=
SEQUENCE {
   sm8tat2saAcctAuthMethodConfigClient INTEGER,
   sm8tat2saAcctAuthMethodConfigMethods INTEGER,
   sm8tat2saAcctAuthMethodConfigCmdLvl Integer32,
   sm8tat2saAcctAuthMethodConfigExec INTEGER
}

sm8tat2saAcctAuthMethodConfigClient OBJECT-TYPE

   SYNTAX INTEGER {telnet(2), ssh(3)}

   MAX-ACCESS not-accessible
   STATUS current
   DESCRIPTION

      "The Client of the Accounting Auth Method Config.  2: telnet, 3: ssh"

   ::= { sm8tat2saAcctAuthMethodConfigEntry 1 }

sm8tat2saAcctAuthMethodConfigMethods OBJECT-TYPE
   SYNTAX INTEGER {no(0), tacacs(3)}
   MAX-ACCESS read-write
   STATUS current
   DESCRIPTION
      "Methods that involves remote servers are timed out if the remote servers are offline.Each method is tried from left to
       right and continues until a method either approves or rejects a user.
         0: no(deault), Authentication is disabled and login is not possible.
         3: tacacs+, Use remote TACACS+ server(s) for authentication. "
   ::= { sm8tat2saAcctAuthMethodConfigEntry 2 }

sm8tat2saAcctAuthMethodConfigCmdLvl OBJECT-TYPE
   SYNTAX Integer32 (0..15)
   MAX-ACCESS read-write
   STATUS current
   DESCRIPTION
      "The Command Level of the Accounting Auth Method Config.  range: 0~15, deault: 0. "
   ::= { sm8tat2saAcctAuthMethodConfigEntry 3 }

sm8tat2saAcctAuthMethodConfigExec OBJECT-TYPE
   SYNTAX AdminMode
   MAX-ACCESS read-write
   STATUS current
   DESCRIPTION
      "Control whether The Exec of the Accounting Auth Method Config is enabled or not.  0: disable(default), 1: enable. "
   ::= { sm8tat2saAcctAuthMethodConfigEntry 4 }

-- *************************************************************
-- Start sm8tat2saAccessManagementConfig group
-- *************************************************************
sm8tat2saAccessManagementConfig OBJECT IDENTIFIER ::= { sm8tat2saSecurity 10 }

sm8tat2saAccessManagementConfigGlobals OBJECT IDENTIFIER ::= { sm8tat2saAccessManagementConfig 1 }

sm8tat2saAccessManagementConfigGlobalsAdminState OBJECT-TYPE
    SYNTAX INTEGER { disable(0), enable(1) }
    MAX-ACCESS read-write
    STATUS current
    DESCRIPTION
        "Enable/Disable the Access Management global functionality."
    ::= { sm8tat2saAccessManagementConfigGlobals 1 }

sm8tat2saAccessManagementConfigIpv4Table OBJECT-TYPE
    SYNTAX SEQUENCE OF SM8TAT2SAAccessManagementConfigIpv4Entry
    MAX-ACCESS not-accessible
    STATUS current
    DESCRIPTION
        "This is a table for managing Access Management per IPv4 basis"
    ::= { sm8tat2saAccessManagementConfig 2 }

sm8tat2saAccessManagementConfigIpv4Entry OBJECT-TYPE
    SYNTAX SM8TAT2SAAccessManagementConfigIpv4Entry
    MAX-ACCESS not-accessible
    STATUS current
    DESCRIPTION
        "Each entry has a set of parameters"
    INDEX { sm8tat2saAccessManagementConfigIpv4AccessIndex }
    ::= { sm8tat2saAccessManagementConfigIpv4Table 1 }

SM8TAT2SAAccessManagementConfigIpv4Entry ::= SEQUENCE {
    sm8tat2saAccessManagementConfigIpv4AccessIndex Integer32,
    sm8tat2saAccessManagementConfigIpv4VlanId Integer32,
    sm8tat2saAccessManagementConfigIpv4Address DisplayString,
    sm8tat2saAccessManagementConfigIpv4MaskLength Integer32,
    sm8tat2saAccessManagementConfigIpv4WebServices INTEGER,
    sm8tat2saAccessManagementConfigIpv4SnmpServices INTEGER,
    sm8tat2saAccessManagementConfigIpv4TelnetServices INTEGER,
    sm8tat2saAccessManagementConfigIpv4RowStatus RowStatus
}

sm8tat2saAccessManagementConfigIpv4AccessIndex OBJECT-TYPE
    SYNTAX Integer32 (0..2147483647)
    MAX-ACCESS not-accessible
    STATUS current
    DESCRIPTION
        "Index for Access Management IPv4/IPv6 table."
    ::= { sm8tat2saAccessManagementConfigIpv4Entry 1 }

sm8tat2saAccessManagementConfigIpv4VlanId OBJECT-TYPE
    SYNTAX Integer32 (1..4095)
    MAX-ACCESS read-create
    STATUS current
    DESCRIPTION
        "The ID of specific VLAN interface that Access Management should take
         effect for IPv4."
    ::= { sm8tat2saAccessManagementConfigIpv4Entry 2 }

sm8tat2saAccessManagementConfigIpv4Address OBJECT-TYPE
    SYNTAX DisplayString
    MAX-ACCESS read-create
    STATUS current
    DESCRIPTION
        "The starting IPv4 address of the range that Access Management performs
         checking."
    ::= { sm8tat2saAccessManagementConfigIpv4Entry 3 }

sm8tat2saAccessManagementConfigIpv4MaskLength OBJECT-TYPE
    SYNTAX Integer32
    MAX-ACCESS read-create
    STATUS current
    DESCRIPTION
        "The ending IPv4 address of the range that Access Management performs
         checking."
    ::= { sm8tat2saAccessManagementConfigIpv4Entry 4 }

sm8tat2saAccessManagementConfigIpv4WebServices OBJECT-TYPE
    SYNTAX INTEGER { disable(0), enable(1) }
    MAX-ACCESS read-create
    STATUS current
    DESCRIPTION
        "Enable/Disable HTTP and HTTPS functionality via Access Management. At
         least one of WebServices/SnmpServices/TelnetServices has to be enabled
         for a specific AccessIndex in Access Management IPv4 table."
    ::= { sm8tat2saAccessManagementConfigIpv4Entry 5 }

sm8tat2saAccessManagementConfigIpv4SnmpServices OBJECT-TYPE
    SYNTAX INTEGER { disable(0), enable(1) }
    MAX-ACCESS read-create
    STATUS current
    DESCRIPTION
        "Enable/Disable SNMP functionality via Access Management. At least one
         of WebServices/SnmpServices/TelnetServices has to be enabled for a
         specific AccessIndex in Access Management IPv4 table."
    ::= { sm8tat2saAccessManagementConfigIpv4Entry 6 }

sm8tat2saAccessManagementConfigIpv4TelnetServices OBJECT-TYPE
    SYNTAX INTEGER { disable(0), enable(1) }
    MAX-ACCESS read-create
    STATUS current
    DESCRIPTION
        "Enable/Disable TELNET/SSH functionality via Access Management. At least
         one of WebServices/SnmpServices/TelnetServices has to be enabled for a
         specific AccessIndex in Access Management IPv4 table."
    ::= { sm8tat2saAccessManagementConfigIpv4Entry 7 }

sm8tat2saAccessManagementConfigIpv4RowStatus OBJECT-TYPE
    SYNTAX RowStatus
    MAX-ACCESS read-create
    STATUS current
    DESCRIPTION
       "This object indicates the status of this entry, and is
        used to create/delete entries. Any object in an entry of
        this table may be modified while the value of the
        corresponding instance of this object is active(1).
        notReady(3) and createAndGo(4) not supported."
    ::= { sm8tat2saAccessManagementConfigIpv4Entry 8 }

-- *************************************************************
-- Start sm8tat2saSecurity group
-- *************************************************************
sm8tat2saSecurityConformance OBJECT IDENTIFIER ::= { sm8tat2saSecurity 200 }
sm8tat2saSecurityCompliances OBJECT IDENTIFIER ::= { sm8tat2saSecurityConformance 1 }
sm8tat2saSecurityGroups OBJECT IDENTIFIER ::= { sm8tat2saSecurityConformance 2 }

sm8tat2saIPSourceGuardGroup OBJECT-GROUP
    OBJECTS {
    --sm8tat2saIPSourceGuard
        sm8tat2saIPSourceGuardMode,

      --sm8tat2saIPSourceGuardPortConfigTable
        sm8tat2saIPSourceGuardPortConfigMode,
        sm8tat2saIPSourceGuardPortMaxDynamicClients,

      --sm8tat2saIPSourceGuardStaticTable
        sm8tat2saIPSourceGuardStaticPort,
        sm8tat2saIPSourceGuardStaticIPAddress,
        sm8tat2saIPSourceGuardStaticMACAddress,
        sm8tat2saIPSourceGuardStaticRowStatus,

      --sm8tat2saIPSourceGuardDynamicTable
        sm8tat2saIPSourceGuardDynamicPort,
        sm8tat2saIPSourceGuardDynamicIPAddress,
        sm8tat2saIPSourceGuardDynamicMACAddress
    }
    STATUS current
    DESCRIPTION
        "The collection of objects which are used to
        indicate ip source guard information."
    ::= { sm8tat2saSecurityGroups 1 }

sm8tat2saARPInspectionGroup OBJECT-GROUP
    OBJECTS {
    --sm8tat2saARPInspection
        sm8tat2saARPInspectionMode,

      --sm8tat2saARPPortConfigTable
        sm8tat2saARPPortConfigMode,
        sm8tat2saARPPortConfigCheckVLAN,
        sm8tat2saARPPortConfigLogType,

      --sm8tat2saARPVlanConfigTable
        sm8tat2saARPVlanConfigVlanID,
        sm8tat2saARPVlanConfigLogType,
        sm8tat2saARPVlanConfigRowStatus,

      --sm8tat2saARPStaticTable
        sm8tat2saARPStaticPort,
        sm8tat2saARPStaticVlanID,
        sm8tat2saARPStaticMACAddress,
        sm8tat2saARPStaticIPAddress,
        sm8tat2saARPStaticRowStatus,

      --sm8tat2saARPDynamicTable
        sm8tat2saARPDynamicPort,
        sm8tat2saARPDynamicVLANId,
        sm8tat2saARPDynamicMACAddress,
        sm8tat2saARPDynamicIPAddress
    }
    STATUS current
    DESCRIPTION
        "The collection of objects which are used to
        indicate ARP inspection information."
    ::= { sm8tat2saSecurityGroups 2 }

sm8tat2saDHCPSnoopingGroup OBJECT-GROUP
    OBJECTS {
    --sm8tat2saDHCPSnooping
      --sm8tat2saDHCPSnoopingConfiguration
        sm8tat2saDHCPSnoopingMode,

        --sm8tat2saDHCPSnoopingPortModeConfigurationTable
        sm8tat2saDHCPSnoopingPortModeConfigurationMode,

      --sm8tat2saDynamicDHCPSnoopingTable
        sm8tat2saDynamicDHCPSnoopingMACAddress,
        sm8tat2saDynamicDHCPSnoopingVLANID,
        sm8tat2saDynamicDHCPSnoopingPort,
        sm8tat2saDynamicDHCPSnoopingIPAddress,
        sm8tat2saDynamicDHCPSnoopingIPSubnetMask,
        sm8tat2saDynamicDHCPSnoopingDHCPServer,

      --sm8tat2saPortSecLimitCtrl
        --sm8tat2saPortSecLimitCtrlSystemConf
        sm8tat2saPortSecurityMode,

          --sm8tat2saPortSecLimitCtrlTable
        sm8tat2saPortSecLimitCtrlPortMode,
        sm8tat2saPortSecLimitCtrlPortLimit,
        sm8tat2saPortSecLimitCtrlPortAction,
        sm8tat2saPortSecLimitCtrlPortState,
        sm8tat2saPortSecLimitCtrlPortReOpen,

        --sm8tat2saPortSecSwitchStatusTable
        sm8tat2saPortSecSwitchStatusState,
        sm8tat2saPortSecSwitchStatusMACCountCurrent
    }
    STATUS current
    DESCRIPTION
        "The collection of objects which are used to
        indicate DHCP snooping information."
    ::= { sm8tat2saSecurityGroups 3 }

sm8tat2saTACACSGroup OBJECT-GROUP
    OBJECTS {
    --sm8tat2saTACACS
        sm8tat2saTACACSGlobalConfigTimeout,
        sm8tat2saTACACSGlobalConfigDeadtime,
        sm8tat2saTACACSGlobalConfigKey,

      --sm8tat2saTACACSServerConfigTable
        sm8tat2saTACACSServerConfigHostname,
        sm8tat2saTACACSServerConfigPort,
        sm8tat2saTACACSServerConfigTimeout,
        sm8tat2saTACACSServerConfigKey,
        sm8tat2saTACACSServerConfigRowStatus
    }
    STATUS current
    DESCRIPTION
        "The collection of objects which are used to
        indicate TACACS information."
    ::= { sm8tat2saSecurityGroups 7 }

sm8tat2saAuthMethodGroup OBJECT-GROUP
    OBJECTS {
    --sm8tat2saAuthMethod
      --sm8tat2saAuthMethodConfigTable
        sm8tat2saAuthMethodConfigMethod1,
        sm8tat2saAuthMethodConfigMethod2,
        sm8tat2saAuthMethodConfigMethod3,
        sm8tat2saAuthMethodConfigServicePort,

      --sm8tat2saCmdAuthMethodConfigTable
        sm8tat2saCmdAuthMethodConfigMethods,
        sm8tat2saCmdAuthMethodConfigCmdLvl,
        sm8tat2saCmdAuthMethodConfigCfgCmd,
        sm8tat2saCmdAuthMethodConfigFallback,

      --sm8tat2saAcctAuthMethodConfigTable
        sm8tat2saAcctAuthMethodConfigMethods,
        sm8tat2saAcctAuthMethodConfigCmdLvl,
        sm8tat2saAcctAuthMethodConfigExec
    }
    STATUS current
    DESCRIPTION
        "The collection of objects which are used to
        indicate auth method information."
    ::= { sm8tat2saSecurityGroups 9 }

sm8tat2saAccessManagementConfigGroup OBJECT-GROUP
    OBJECTS {
    --sm8tat2saAccessManagementConfig
      --sm8tat2saAccessManagementConfigGlobals
        sm8tat2saAccessManagementConfigGlobalsAdminState,

      --sm8tat2saAccessManagementConfigIpv4Table
        sm8tat2saAccessManagementConfigIpv4VlanId,
        sm8tat2saAccessManagementConfigIpv4Address,
        sm8tat2saAccessManagementConfigIpv4MaskLength,
        sm8tat2saAccessManagementConfigIpv4WebServices,
        sm8tat2saAccessManagementConfigIpv4SnmpServices,
        sm8tat2saAccessManagementConfigIpv4TelnetServices,
        sm8tat2saAccessManagementConfigIpv4RowStatus
    }
    STATUS current
    DESCRIPTION
        "The collection of objects which are used to
        indicate access management information."
    ::= { sm8tat2saSecurityGroups 10 }

sm8tat2saSecurityCompliance MODULE-COMPLIANCE
    STATUS current
    DESCRIPTION
        "The compliance statement for devices supporting security."
    MODULE
        MANDATORY-GROUPS {
            sm8tat2saIPSourceGuardGroup,
            sm8tat2saARPInspectionGroup,
            sm8tat2saDHCPSnoopingGroup,
            sm8tat2saTACACSGroup,
            sm8tat2saAuthMethodGroup,
            sm8tat2saAccessManagementConfigGroup
        }
    ::= { sm8tat2saSecurityCompliances 1 }

-- ======================================================================================================================
sm8tat2saMaintenance OBJECT IDENTIFIER ::= { sm8tat2saProductId 4 }

sm8tat2saSoftware OBJECT IDENTIFIER ::= { sm8tat2saMaintenance 3 }
sm8tat2saConfig OBJECT IDENTIFIER ::= { sm8tat2saMaintenance 4 }

-- *************************************************************
-- Objects in the sm8tat2saMaintenance Group
-- *************************************************************

sm8tat2saRestartDevice OBJECT-TYPE
   SYNTAX ActivateCmd
   MAX-ACCESS read-write
   STATUS current
   DESCRIPTION
       "Command to restart the device."
   ::= { sm8tat2saMaintenance 1 }

sm8tat2saFactoryDefaults OBJECT-TYPE
   SYNTAX ActivateCmd
   MAX-ACCESS read-write
   STATUS current
   DESCRIPTION
       "Reset the configuration to Factory Defaults keep-ip."
   ::= { sm8tat2saMaintenance 2 }

--sm8tat2saSoftware
sm8tat2saSoftwareIpAddress OBJECT-TYPE
   SYNTAX IpAddress
   MAX-ACCESS read-write
   STATUS current
   DESCRIPTION
        "Get/Set the firmware tftp server."
   ::= { sm8tat2saSoftware 1 }

sm8tat2saSoftwareFileName OBJECT-TYPE
   SYNTAX DisplayString
   MAX-ACCESS read-write
   STATUS current
   DESCRIPTION
        "Get/Set the path and filename for firmware upgrading."
   ::= { sm8tat2saSoftware 2 }

sm8tat2saSoftwareUpgradeCmd OBJECT-TYPE
   SYNTAX INTEGER { noAction ( 0 ), tftpUpgrade ( 1 )}
   MAX-ACCESS read-write
   STATUS current
   DESCRIPTION
        "Firmware upgrade command.
         noAction(0 )- do nothing (read only).
         tftpUpgrade (1) - activate 'tftp' firmware upgrade"
   ::= { sm8tat2saSoftware 3 }

sm8tat2saSoftwareImageSelectionCmd OBJECT-TYPE
   SYNTAX ActivateCmd
   MAX-ACCESS read-write
   STATUS current
   DESCRIPTION
        "Activate firmware image selection.
         noAction(0) - do nothing - returned upon get.
         activate(1) - activate firmware image selection."
   ::= { sm8tat2saSoftware 4 }

sm8tat2saSaveStart OBJECT-TYPE
   SYNTAX INTEGER { none(0), yes(1) }
   MAX-ACCESS read-write
   STATUS current
   DESCRIPTION
       "default: 0
        0:none
        1:yes"
   ::= { sm8tat2saConfig 1 }

sm8tat2saBackupIpAddress OBJECT-TYPE
   SYNTAX IpAddress
   MAX-ACCESS read-write
   STATUS current
   DESCRIPTION
        "Get/Set the backup tftp server."
   ::= { sm8tat2saConfig 2 }

sm8tat2saBackupFilename OBJECT-TYPE
   SYNTAX DisplayString
   MAX-ACCESS read-write
   STATUS current
   DESCRIPTION
        "Get/Set the backup file."
   ::= { sm8tat2saConfig 3 }

sm8tat2saDoBackupConfig OBJECT-TYPE
   SYNTAX INTEGER{ doNothing(0), do(1) }
   MAX-ACCESS read-write
   STATUS current
   DESCRIPTION
        "Do export-config.
         Get this OID always return zero.
         1 - export.
         If BackupFilename is running-config, you must wait for some seconds to get the file."
   ::= { sm8tat2saConfig 4 }

sm8tat2saRestoreIpAddress OBJECT-TYPE
   SYNTAX IpAddress
   MAX-ACCESS read-write
   STATUS current
   DESCRIPTION
        "Get/Set the import tftp server."
   ::= { sm8tat2saConfig 5 }

sm8tat2saRestoreConfigName OBJECT-TYPE
   SYNTAX DisplayString
   MAX-ACCESS read-write
   STATUS current
   DESCRIPTION
       "Get/Set the import file path and name."
   ::= { sm8tat2saConfig 6 }

sm8tat2saRestoreDestinationName OBJECT-TYPE
   SYNTAX DisplayString
   MAX-ACCESS read-write
   STATUS current
   DESCRIPTION
       "Get/Set the import destination file name.
        Note: The file name default-config is reserved."
   ::= { sm8tat2saConfig 7 }

sm8tat2saRestoreMode OBJECT-TYPE
   SYNTAX INTEGER{ replace(0), merge(1) }
   MAX-ACCESS read-write
   STATUS current
   DESCRIPTION
        "When destination file is running-config, it can be replaced or merged.
         Other destination file must be replaced. If merge, don't care."
   ::= { sm8tat2saConfig 8 }

sm8tat2saDoRestoreConfig OBJECT-TYPE
   SYNTAX INTEGER{ doNothing(0), do(1) }
   MAX-ACCESS read-write
   STATUS current
   DESCRIPTION
        "Do export-config.
         Get this OID always return zero.
         1 - import."
   ::= { sm8tat2saConfig 9 }

sm8tat2saConfigListActivateTable OBJECT-TYPE
   SYNTAX SEQUENCE OF SM8TAT2SAConfigListActivateEntry
   MAX-ACCESS not-accessible
   STATUS current
   DESCRIPTION
       " "
   ::= { sm8tat2saConfig 10 }

sm8tat2saConfigListActivateEntry OBJECT-TYPE
   SYNTAX SM8TAT2SAConfigListActivateEntry
   MAX-ACCESS not-accessible
   STATUS current
   DESCRIPTION
       " "
   INDEX { sm8tat2saConfigListActivateIndex }
   ::= { sm8tat2saConfigListActivateTable 1 }

SM8TAT2SAConfigListActivateEntry ::= SEQUENCE {
   sm8tat2saConfigListActivateIndex Integer32,
   sm8tat2saConfigListActivateFilename DisplayString,
   sm8tat2saConfigListActivate INTEGER
}

sm8tat2saConfigListActivateIndex OBJECT-TYPE
   SYNTAX Integer32(1..4095)
   MAX-ACCESS not-accessible
   STATUS current
   DESCRIPTION
       " "
   ::= { sm8tat2saConfigListActivateEntry 1 }

sm8tat2saConfigListActivateFilename OBJECT-TYPE
   SYNTAX DisplayString
   MAX-ACCESS read-only
   STATUS current
   DESCRIPTION
       " "
   ::= { sm8tat2saConfigListActivateEntry 2 }

sm8tat2saConfigListActivate OBJECT-TYPE
   SYNTAX INTEGER { doNothing(0), do(1) }
   MAX-ACCESS read-write
   STATUS current
   DESCRIPTION
        "Do activate-config.
         Get this OID always return zero.
         1 - import."
   ::= { sm8tat2saConfigListActivateEntry 3 }

sm8tat2saConfigListDeleteTable OBJECT-TYPE
   SYNTAX SEQUENCE OF SM8TAT2SAConfigListDeleteEntry
   MAX-ACCESS not-accessible
   STATUS current
   DESCRIPTION
       " "
   ::= { sm8tat2saConfig 11 }

sm8tat2saConfigListDeleteEntry OBJECT-TYPE
   SYNTAX SM8TAT2SAConfigListDeleteEntry
   MAX-ACCESS not-accessible
   STATUS current
   DESCRIPTION
       " "
   INDEX { sm8tat2saConfigListDeleteIndex }
   ::= { sm8tat2saConfigListDeleteTable 1 }

SM8TAT2SAConfigListDeleteEntry ::= SEQUENCE {
   sm8tat2saConfigListDeleteIndex Integer32,
   sm8tat2saConfigListDeleteFilename DisplayString,
   sm8tat2saConfigListDelete INTEGER
}

sm8tat2saConfigListDeleteIndex OBJECT-TYPE
   SYNTAX Integer32(1..4095)
   MAX-ACCESS not-accessible
   STATUS current
   DESCRIPTION
       " "
   ::= { sm8tat2saConfigListDeleteEntry 1 }

sm8tat2saConfigListDeleteFilename OBJECT-TYPE
   SYNTAX DisplayString
   MAX-ACCESS read-only
   STATUS current
   DESCRIPTION
       " "
   ::= { sm8tat2saConfigListDeleteEntry 2 }

sm8tat2saConfigListDelete OBJECT-TYPE
   SYNTAX INTEGER { doNothing(0), do(1) }
   MAX-ACCESS read-write
   STATUS current
   DESCRIPTION
        "Do delete-config.
         Get this OID always return zero.
         1 - import."
   ::= { sm8tat2saConfigListDeleteEntry 3 }

-- *************************************************************
-- Start sm8tat2saSystemAccount group
-- *************************************************************
sm8tat2saMaintenanceConformance OBJECT IDENTIFIER ::= { sm8tat2saMaintenance 200 }
sm8tat2saMaintenanceCompliances OBJECT IDENTIFIER ::= { sm8tat2saMaintenanceConformance 1 }
sm8tat2saMaintenanceGroups OBJECT IDENTIFIER ::= { sm8tat2saMaintenanceConformance 2 }

sm8tat2saMaintenanceGroup OBJECT-GROUP
    OBJECTS {
        sm8tat2saRestartDevice,
        sm8tat2saFactoryDefaults,
      --sm8tat2saSoftware
        sm8tat2saSoftwareIpAddress,
        sm8tat2saSoftwareFileName,
        sm8tat2saSoftwareUpgradeCmd,
        sm8tat2saSoftwareImageSelectionCmd,

      --sm8tat2saConfig
        sm8tat2saSaveStart,
        sm8tat2saBackupIpAddress,
        sm8tat2saBackupFilename,
        sm8tat2saDoBackupConfig,
        sm8tat2saRestoreIpAddress,
        sm8tat2saRestoreConfigName,
        sm8tat2saRestoreDestinationName,
        sm8tat2saRestoreMode,
        sm8tat2saDoRestoreConfig,

        --sm8tat2saConfigListActivateTable
        sm8tat2saConfigListActivateFilename,
        sm8tat2saConfigListActivate,

        --sm8tat2saConfigListDeleteTable
        sm8tat2saConfigListDeleteFilename,
        sm8tat2saConfigListDelete
    }
    STATUS current
    DESCRIPTION
        "The collection of objects which are used to
        indicate maintenance information."
    ::= { sm8tat2saMaintenanceGroups 1 }

sm8tat2saMaintenanceCompliance MODULE-COMPLIANCE
    STATUS current
    DESCRIPTION
        "The compliance statement for devices supporting maintenance."
    MODULE
        MANDATORY-GROUPS {
            sm8tat2saMaintenanceGroup
        }
    ::= { sm8tat2saMaintenanceCompliances 1 }

-- ================================================================================================================
sm8tat2saTrap OBJECT IDENTIFIER ::= { sm8tat2saProductId 5 }

-- *************************************************************
-- Start sm8tat2saTrapEvent group
-- *************************************************************
sm8tat2saTrapEvent OBJECT IDENTIFIER ::= { sm8tat2saTrap 0 }

sm8tat2saEmergency NOTIFICATION-TYPE
  OBJECTS { sm8tat2saInformation }
  STATUS current
    DESCRIPTION
        "The severity level is Emergency. Emergency conditions."
    ::= { sm8tat2saTrapEvent 1 }

sm8tat2saAlert NOTIFICATION-TYPE
  OBJECTS { sm8tat2saInformation }
  STATUS current
    DESCRIPTION
        "The severity level is Alert. Alert conditions."
    ::= { sm8tat2saTrapEvent 2 }

sm8tat2saCritical NOTIFICATION-TYPE
  OBJECTS { sm8tat2saInformation }
  STATUS current
    DESCRIPTION
        "The severity level is Critical. Critical conditions."
    ::= { sm8tat2saTrapEvent 3 }

sm8tat2saError NOTIFICATION-TYPE
  OBJECTS { sm8tat2saInformation }
  STATUS current
    DESCRIPTION
        "The severity level is Error. Error conditions."
    ::= { sm8tat2saTrapEvent 4 }

sm8tat2saWarning NOTIFICATION-TYPE
  OBJECTS { sm8tat2saInformation }
  STATUS current
    DESCRIPTION
        "The severity level is Warning. Warning conditions."
    ::= { sm8tat2saTrapEvent 5 }

sm8tat2saNotice NOTIFICATION-TYPE
  OBJECTS { sm8tat2saInformation }
  STATUS current
    DESCRIPTION
        "The severity level is Notice. Notice conditions."
    ::= { sm8tat2saTrapEvent 6 }

sm8tat2saInformational NOTIFICATION-TYPE
  OBJECTS { sm8tat2saInformation }
  STATUS current
    DESCRIPTION
        "The severity level is Informational. Informational conditions."
    ::= { sm8tat2saTrapEvent 7 }

sm8tat2saDebug NOTIFICATION-TYPE
  OBJECTS { sm8tat2saInformation }
  STATUS current
    DESCRIPTION
        "The severity level is Debug. Debug conditions."
    ::= { sm8tat2saTrapEvent 8 }

sm8tat2saTrapVariable OBJECT IDENTIFIER ::= { sm8tat2saTrap 2 }

sm8tat2saInformation OBJECT-TYPE
    SYNTAX DisplayString
    MAX-ACCESS read-only
    STATUS current
    DESCRIPTION
        "Trap information."
    ::= { sm8tat2saTrapVariable 1 }

sm8tat2saZTPTrap OBJECT IDENTIFIER ::= { sm8tat2saTrap 3 }
sm8tat2saZTPTrapEvent OBJECT IDENTIFIER ::= { sm8tat2saZTPTrap 0 }
sm8tat2saZTPOnboardTrap NOTIFICATION-TYPE
  OBJECTS { sm8tat2saInformation }
  STATUS current
    DESCRIPTION
        "The severity level is Emergency. Emergency conditions."
    ::= { sm8tat2saZTPTrapEvent 1 }

-- *************************************************************
-- Start sm8tat2saTrap group
-- *************************************************************
sm8tat2saTrapConformance OBJECT IDENTIFIER ::= { sm8tat2saTrap 200 }
sm8tat2saTrapCompliances OBJECT IDENTIFIER ::= { sm8tat2saTrapConformance 1 }
sm8tat2saTrapGroups OBJECT IDENTIFIER ::= { sm8tat2saTrapConformance 2 }

sm8tat2saTrapEventGroup NOTIFICATION-GROUP
    NOTIFICATIONS {
    --sm8tat2saTrapEvent
        sm8tat2saEmergency,
        sm8tat2saAlert,
        sm8tat2saCritical,
        sm8tat2saError,
        sm8tat2saWarning,
        sm8tat2saNotice,
        sm8tat2saInformational,
        sm8tat2saDebug
    }
    STATUS current
    DESCRIPTION
        "The collection of objects which are used to
        indicate trap event information."
    ::= { sm8tat2saTrapGroups 1 }

sm8tat2saTrapVariableGroup OBJECT-GROUP
    OBJECTS {
    --sm8tat2saTrapVariable
        sm8tat2saInformation
    }
    STATUS current
    DESCRIPTION
        "The collection of objects which are used to
        indicate trap variable information."
    ::= { sm8tat2saTrapGroups 2 }

sm8tat2saZTPTrapGroup NOTIFICATION-GROUP
    NOTIFICATIONS {
    --sm8tat2saZTPTrap
        sm8tat2saZTPOnboardTrap
    }
    STATUS current
    DESCRIPTION
        "The collection of objects which are used to
        indicate trap event information."
    ::= { sm8tat2saTrapGroups 3 }

sm8tat2saTrapCompliance MODULE-COMPLIANCE
    STATUS current
    DESCRIPTION
        "The compliance statement for devices supporting trap."
    MODULE
        MANDATORY-GROUPS {
            sm8tat2saTrapEventGroup,
            sm8tat2saTrapVariableGroup

            ,sm8tat2saZTPTrapGroup

        }
    ::= { sm8tat2saTrapCompliances 1 }

END
