--SM16TAT2SA-MIB

SM16TAT2SA-MIB DEFINITIONS ::= BEGIN

IMPORTS
    DisplayString,MacAddress,TEXTUAL-CONVENTION,RowStatus FROM SNMPv2-TC
    MODULE-COMPLIANCE,OBJECT-GROUP,NOTIFICATION-GROUP FROM SNMPv2-CONF
    ifIndex FROM IF-MIB
    --Unsigned32,Counter64 FROM SNMPv2-SMI
    enterprises,MODULE-IDENTITY,OBJECT-TYPE,NOTIFICATION-TYPE,Integer32,Counter32,IpAddress FROM SNMPv2-SMI;

transition MODULE-IDENTITY
        LAST-UPDATED "202203170850Z"
        ORGANIZATION "Corp."
        CONTACT-INFO " "
        DESCRIPTION "Smart Managed Switch, 16-port Gigabit PoE+, 2-port 100/1000 SFP"
        REVISION "202203170850Z"
        DESCRIPTION "To pass the SimpleWeb validation"
        ::= { enterprises 868 }

switch OBJECT IDENTIFIER ::= { transition 2 }
sm16tat2saProductId OBJECT IDENTIFIER ::= { switch 72 }

-- ================================================================================================================
     OperState ::= TEXTUAL-CONVENTION
       STATUS current
       DESCRIPTION
                      "Oper state."
       SYNTAX INTEGER { up ( 1 ) , down ( 2 ) }

     AdminMode ::= TEXTUAL-CONVENTION
       STATUS current
       DESCRIPTION
            "The Admin state - default: disable(0)."
       SYNTAX INTEGER { disable(0), enable(1) }

     AdminMode2 ::= TEXTUAL-CONVENTION
       STATUS current
       DESCRIPTION
            "The Admin state - default: disable(0)."
       SYNTAX INTEGER { disable(0), enable(1), notSupported(2) }

     ActivateCmd ::= TEXTUAL-CONVENTION
       STATUS current
       DESCRIPTION
            "Used to activate commands. default: noAction(0). "
       SYNTAX INTEGER { noAction ( 0 ),
                                  activate ( 1 )
                               }

     KeyType ::= TEXTUAL-CONVENTION
       STATUS current
       DESCRIPTION
           "The key type specifying the key generated for frames received
            on the port.
            0 : Normal,
            1 : Double Tag,
            2 : IP Address,
            3 : MAC and IP Address."
        SYNTAX INTEGER { normal ( 0 ),
                               doubleTag ( 1 ),
                               ipAddr ( 2 ),
                               macAndIpAddr ( 3 )
                             }

     FrameRate ::= TEXTUAL-CONVENTION
       STATUS current
       DESCRIPTION
           "The values for frame rate"
       SYNTAX INTEGER {
                            threeHundredFramesPerSec (0),
                            oneHundredFramesPerSec (1),
                            tenFramesPerSec (2),
                            oneFramePerSec (3),
                            sixFramesPerMin (4),
                            oneFramePerMin (5),
                            sixFramesPerHour (6)
                            }

     DayOfWeek ::= TEXTUAL-CONVENTION
       STATUS current
       DESCRIPTION
            "Used to set the days of the week."
       SYNTAX INTEGER {mon(1),tue(2),wed(3),thur(4),
                             fri(5),sat(6),sun(7) }

     Month ::= TEXTUAL-CONVENTION
       STATUS current
       DESCRIPTION
            "Used to set the month."
       SYNTAX INTEGER {jan(1),feb(2),march(3),april(4),
                             may(5),june(6),july(7),aug(8),
                             sept(9),oct(10),nov(11),dec(12)}

     PortSelect ::= TEXTUAL-CONVENTION
         DISPLAY-HINT "255a"
         STATUS current
         DESCRIPTION
             "Each octet within this value specifies a set of eight
             ports, with the first octet specifying ports 1 through
             8, the second octet specifying ports 9 through 16, etc.
             Within each octet, the least significant bit represents
             the lowest numbered port, and the most significant bit
             represents the highest numbered port. Thus, each port
             of the bridge is represented by a single bit within the
             value of this object. If that bit has a value of '1'
             then that port is included in the set of ports; the port
             is not included if its bit has a value of '0'."
         SYNTAX OCTET STRING (SIZE(0..255))

     VoiceVlanPortDiscoveryProtocol ::= TEXTUAL-CONVENTION
         STATUS current
         DESCRIPTION
             "This enumeration indicates per port Voice VLAN discovery protocol."
         SYNTAX INTEGER { oui(0), lldp(1), both(2) }

     VoiceVlanPortManagementType ::= TEXTUAL-CONVENTION
         STATUS current
         DESCRIPTION
             "This enumeration indicates per port Voice VLAN function administrative
              type."
         SYNTAX INTEGER { automatic(1), forced(2) }

     SeverityLevel ::= TEXTUAL-CONVENTION
       STATUS current
       DESCRIPTION
            "The Severity Level.
             0 : Emerg, 1 : Alert, 2 : Critical, 3 : Error, 4 : Warning, 5 : Notice, 6 : Info, 7 : Debug."
       SYNTAX INTEGER {
                    emergency(0),
                    alert(1),
                    critical(2),
                    error(3),
                    warning(4),
                    notice(5),
                    info(6),
                    debug(7)
               }

     LldpmedAltitudeType ::= TEXTUAL-CONVENTION
         STATUS current
         DESCRIPTION
             "This enumerations the altitude type."
         SYNTAX INTEGER { meters(1), floors(2) }

     LldpmedDatumType ::= TEXTUAL-CONVENTION
         STATUS current
         DESCRIPTION
             "This enumerations the datum (geodetic system)."
         SYNTAX INTEGER { wgs84(1), nad83navd88(2), nad83mllw(3) }

-- ================================================================================================================
sm16tat2saSystem OBJECT IDENTIFIER ::= { sm16tat2saProductId 1 }

-- *************************************************************
-- Objects in the sm16tat2saSystemInformation Group
-- *************************************************************
sm16tat2saSystemInformation OBJECT IDENTIFIER ::= { sm16tat2saSystem 1 }

sm16tat2saSystemInfoModelName OBJECT-TYPE
   SYNTAX DisplayString
   MAX-ACCESS read-only
   STATUS current
   DESCRIPTION
       "Model Name."
   ::= { sm16tat2saSystemInformation 1 }

sm16tat2saSystemInfoSystemDescript OBJECT-TYPE
   SYNTAX DisplayString
   MAX-ACCESS read-only
   STATUS current
   DESCRIPTION
       "System Description."
   ::= { sm16tat2saSystemInformation 2 }

sm16tat2saSystemInfoHardwareVersion OBJECT-TYPE
   SYNTAX DisplayString
   MAX-ACCESS read-only
   STATUS current
   DESCRIPTION
       "Hardware Version."
   ::= { sm16tat2saSystemInformation 3 }

sm16tat2saSystemInfoMechanicalVersion OBJECT-TYPE
   SYNTAX DisplayString
   MAX-ACCESS read-only
   STATUS current
   DESCRIPTION
       "Mechanical Version."
   ::= { sm16tat2saSystemInformation 4 }

sm16tat2saSystemInfoFirmwareVersion OBJECT-TYPE
   SYNTAX DisplayString
   MAX-ACCESS read-only
   STATUS current
   DESCRIPTION
       "Firmware Version."
   ::= { sm16tat2saSystemInformation 5 }

sm16tat2saSystemInfoHostMACAddress OBJECT-TYPE
   SYNTAX DisplayString
   MAX-ACCESS read-only
   STATUS current
   DESCRIPTION
       "MAC Address."
   ::= { sm16tat2saSystemInformation 6 }

sm16tat2saSystemInfoSeriesNumber OBJECT-TYPE
   SYNTAX DisplayString
   MAX-ACCESS read-only
   STATUS current
   DESCRIPTION
       "Series Number."
   ::= { sm16tat2saSystemInformation 7 }

sm16tat2saSystemInfoSystemName OBJECT-TYPE
   SYNTAX DisplayString
   MAX-ACCESS read-write
   STATUS current
   DESCRIPTION
       "System Name."
   ::= { sm16tat2saSystemInformation 8 }

sm16tat2saSystemInfoLocation OBJECT-TYPE
   SYNTAX DisplayString
   MAX-ACCESS read-write
   STATUS current
   DESCRIPTION
       "Location."
   ::= { sm16tat2saSystemInformation 9 }

sm16tat2saSystemInfoContact OBJECT-TYPE
   SYNTAX DisplayString
   MAX-ACCESS read-write
   STATUS current
   DESCRIPTION
       "Contact."
   ::= { sm16tat2saSystemInformation 10 }

sm16tat2saSystemInfoSystemDate OBJECT-TYPE
   SYNTAX DisplayString
   MAX-ACCESS read-only
   STATUS current
   DESCRIPTION
       "System Date."
   ::= { sm16tat2saSystemInformation 11 }

sm16tat2saSystemInfoSystemUptime OBJECT-TYPE
   SYNTAX DisplayString
   MAX-ACCESS read-only
   STATUS current
   DESCRIPTION
       "System Uptime."
   ::= { sm16tat2saSystemInformation 12 }

sm16tat2saSystemInfoPoEFirmwareVersion OBJECT-TYPE
   SYNTAX DisplayString
   MAX-ACCESS read-only
   STATUS current
   DESCRIPTION
       "PoE Firmware Version."
   ::= { sm16tat2saSystemInformation 15 }

-- *************************************************************
-- Objects in the sm16tat2saSystemTime Group
-- *************************************************************
sm16tat2saSystemTimeConf OBJECT IDENTIFIER ::= { sm16tat2saSystem 2 }

sm16tat2saSystemTimeManual OBJECT IDENTIFIER ::= { sm16tat2saSystemTimeConf 1 }

sm16tat2saSystemTimeManualClockSource OBJECT-TYPE
   SYNTAX INTEGER { useLocal(0), useNTP(1) }
   MAX-ACCESS read-write
   STATUS current
   DESCRIPTION
       "0 : Use Local Settings,
        1 : Use NTP Server."
   ::= { sm16tat2saSystemTimeManual 1 }

sm16tat2saSystemTimeManualLocaltime OBJECT-TYPE
   SYNTAX DisplayString
   MAX-ACCESS read-write
   STATUS current
   DESCRIPTION
       "Get/Set the system time of the device.
        The input format is 'Year-Month-Day Hour:Minute:Second'.
        ex: 2011-01-01 05:43:05 means 2011/1/1 - 05:43:05 .
        The value range:
        Year : 2010 - 2090,
        Mouth : 1 - 12,
        Day : 1 - 31,
        Hour : 0 - 23,
        Minute : 0 - 59,
        Sec : 0 - 59."
   ::= { sm16tat2saSystemTimeManual 2 }

sm16tat2saSystemTimeManualTimeZoneOffset OBJECT-TYPE
   SYNTAX Integer32 (-12..12)
   MAX-ACCESS read-write
   STATUS current
   DESCRIPTION
       "Get/Set the NTP Time Zone.
        The value range is between -12 and 12."
   ::= { sm16tat2saSystemTimeManual 3 }

sm16tat2saSystemTimeManualTimeZoneAcronym OBJECT-TYPE
   SYNTAX DisplayString
   MAX-ACCESS read-write
   STATUS current
   DESCRIPTION
       "User can set the acronym of the time zone. This is
        a User configurable acronym to identify the time zone.
        Max: 16 characters."
   ::= { sm16tat2saSystemTimeManual 4 }

sm16tat2saSystemTimeManualDaylightSavings OBJECT-TYPE
   SYNTAX INTEGER { disable(0), enable(1) }
   MAX-ACCESS read-write
   STATUS current
   DESCRIPTION
       "0 : Disable,
        1 : Enable."
   ::= { sm16tat2saSystemTimeManual 5 }

sm16tat2saSystemTimeManualTimeSetOffset OBJECT-TYPE
   SYNTAX Integer32(1..1440)
   MAX-ACCESS read-write
   STATUS current
   DESCRIPTION
       "Get/Set the Daylight Saving Time.
        The value range is between 1 and 1440 (minutes)."
   ::= { sm16tat2saSystemTimeManual 6 }

sm16tat2saSystemTimeManualDaylightSavingsMonthFrom OBJECT-TYPE
   SYNTAX Month
   MAX-ACCESS read-write
   STATUS current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { sm16tat2saSystemTimeManual 7 }

sm16tat2saSystemTimeManualDaylightSavingsWeekFrom OBJECT-TYPE
   SYNTAX INTEGER{
                        firstWeek(1),
                        secondWeek(2),
                        thirdWeek(3),
                        fourthWeek(4),
                        listWeek(5)
                        }
   MAX-ACCESS read-write
   STATUS current
   DESCRIPTION
       "Get/Set the Daylight Saving Time Week From.
        1 : first week, 2, 3, 4, 5 : last week"
   ::= { sm16tat2saSystemTimeManual 8 }

sm16tat2saSystemTimeManualDaylightSavingsDayFrom OBJECT-TYPE
   SYNTAX INTEGER {
                        monday(1),
                        tuseday(2),
                        wednesday(3),
                        thursday(4),
                        friday(5),
                        saturday(6),
                        sunday(7)
                        }
   MAX-ACCESS read-write
   STATUS current
   DESCRIPTION
       "Get/Set the Daylight Saving Time Day From.
        1 : Mon, 2 : Tue, 3 : Wed, 4 : Thu, 5 : Fri, 6 : Sat, 7 : Sun."
   ::= { sm16tat2saSystemTimeManual 9 }

sm16tat2saSystemTimeManualDaylightSavingsHourFrom OBJECT-TYPE
   SYNTAX Integer32(0..23)
   MAX-ACCESS read-write
   STATUS current
   DESCRIPTION
       "Get/Set the Daylight Saving Time Hour From.
        range: 0 - 23."
   ::= { sm16tat2saSystemTimeManual 10 }

sm16tat2saSystemTimeManualDaylightSavingsMonthTo OBJECT-TYPE
   SYNTAX Month
   MAX-ACCESS read-write
   STATUS current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { sm16tat2saSystemTimeManual 11 }

sm16tat2saSystemTimeManualDaylightSavingsWeekTo OBJECT-TYPE
   SYNTAX INTEGER{
                        firstWeek(1),
                        secondWeek(2),
                        thirdWeek(3),
                        fourthWeek(4),
                        listWeek(5)
                        }
   MAX-ACCESS read-write
   STATUS current
   DESCRIPTION
       "Get/Set the Daylight Saving Time Week To.
        1 : first week, 2, 3, 4, 5 : last week"
   ::= { sm16tat2saSystemTimeManual 12 }

sm16tat2saSystemTimeManualDaylightSavingsDayTo OBJECT-TYPE
   SYNTAX INTEGER {
                        monday(1),
                        tuseday(2),
                        wednesday(3),
                        thursday(4),
                        friday(5),
                        saturday(6),
                        sunday(7)
                        }
   MAX-ACCESS read-write
   STATUS current
   DESCRIPTION
       "Get/Set the Daylight Saving Time Day To.
        1 : Mon, 2 : Tue, 3 : Wed, 4 : Thu, 5 : Fri, 6 : Sat, 7 : Sun."
   ::= { sm16tat2saSystemTimeManual 13 }

sm16tat2saSystemTimeManualDaylightSavingsHourTo OBJECT-TYPE
   SYNTAX Integer32(0..23)
   MAX-ACCESS read-write
   STATUS current
   DESCRIPTION
       "Get/Set the Daylight Saving Time Hour To.
        range: 0 - 23."
   ::= { sm16tat2saSystemTimeManual 14 }

-- *************************************************************
-- Objects in the sm16tat2saSystemNTP Group
-- *************************************************************
sm16tat2saSystemTimeNTP OBJECT IDENTIFIER ::= { sm16tat2saSystemTimeConf 2 }

sm16tat2saSystemTimeNTPInterval OBJECT-TYPE
   SYNTAX Integer32(5..120)
   MAX-ACCESS read-write
   STATUS current
   DESCRIPTION
       "NTP poll interval.
        range : 5 min, 10 min, 15 min, 30 min, 60 min, 120 min"
   ::= { sm16tat2saSystemTimeNTP 1 }

sm16tat2saSystemTimeNTPTable OBJECT-TYPE
   SYNTAX SEQUENCE OF SM16TAT2SASystemTimeNTPEntry
   MAX-ACCESS not-accessible
   STATUS current
   DESCRIPTION
       " "
   ::= { sm16tat2saSystemTimeNTP 2 }

sm16tat2saSystemTimeNTPEntry OBJECT-TYPE
   SYNTAX SM16TAT2SASystemTimeNTPEntry
   MAX-ACCESS not-accessible
   STATUS current
   DESCRIPTION
       " "
   INDEX { sm16tat2saSystemTimeNTPIndex }
   ::= { sm16tat2saSystemTimeNTPTable 1 }

SM16TAT2SASystemTimeNTPEntry ::= SEQUENCE {
   sm16tat2saSystemTimeNTPIndex Integer32,
   sm16tat2saSystemTimeNTPServer DisplayString
}

sm16tat2saSystemTimeNTPIndex OBJECT-TYPE
   SYNTAX Integer32(1..6)
   MAX-ACCESS not-accessible
   STATUS current
   DESCRIPTION
       " The index of the ntp entry. "
   ::= { sm16tat2saSystemTimeNTPEntry 1 }

sm16tat2saSystemTimeNTPServer OBJECT-TYPE
   SYNTAX DisplayString
   MAX-ACCESS read-write
   STATUS current
   DESCRIPTION
       "Get/Set the NTP Time Server. You can use the IP address or domain name."
   ::= { sm16tat2saSystemTimeNTPEntry 2 }

-- *************************************************************
-- Start sm16tat2saSystemAccount group
-- *************************************************************
sm16tat2saSystemAccount OBJECT IDENTIFIER ::= { sm16tat2saSystem 3 }

sm16tat2saSystemUsersTable OBJECT-TYPE
   SYNTAX SEQUENCE OF SM16TAT2SASystemUsersEntry
   MAX-ACCESS not-accessible
   STATUS current
   DESCRIPTION
       " "
   ::= { sm16tat2saSystemAccount 1 }

sm16tat2saSystemUsersEntry OBJECT-TYPE
   SYNTAX SM16TAT2SASystemUsersEntry
   MAX-ACCESS not-accessible
   STATUS current
   DESCRIPTION
       " "
   INDEX { sm16tat2saUserIndex }
   ::= { sm16tat2saSystemUsersTable 1 }

SM16TAT2SASystemUsersEntry ::= SEQUENCE {
   sm16tat2saUserIndex Integer32,
   sm16tat2saUserName DisplayString,
   sm16tat2saPassword DisplayString,
   sm16tat2saUserPrivilegeLevel Integer32,
   sm16tat2saAccountUserRowStatus RowStatus
}

sm16tat2saUserIndex OBJECT-TYPE
   SYNTAX Integer32 (1..20)
   MAX-ACCESS not-accessible
   STATUS current
   DESCRIPTION
       "The user Config Index."
   ::= { sm16tat2saSystemUsersEntry 1 }

sm16tat2saUserName OBJECT-TYPE
   SYNTAX DisplayString (SIZE (1..31))
   MAX-ACCESS read-create
   STATUS current
   DESCRIPTION
       "A string identifying the user name for the entry.
        string length: 1-31."
   ::= { sm16tat2saSystemUsersEntry 2 }

sm16tat2saPassword OBJECT-TYPE
   SYNTAX DisplayString (SIZE (1..31))
   MAX-ACCESS read-create
   STATUS current
   DESCRIPTION
       "The password of the user.
        string length: 0-31."
   ::= { sm16tat2saSystemUsersEntry 3 }

sm16tat2saUserPrivilegeLevel OBJECT-TYPE
   SYNTAX Integer32 (0..15)
   MAX-ACCESS read-create
   STATUS current
   DESCRIPTION
       "The privilege level of the user.If the privilege level
        value is 15, it can access all groups.range: 0-15."
   ::= { sm16tat2saSystemUsersEntry 4 }

sm16tat2saAccountUserRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm16tat2saSystemUsersEntry 5 }

-- *************************************************************
-- Start sm16tat2saIP group
-- *************************************************************
sm16tat2saIP OBJECT IDENTIFIER ::= { sm16tat2saSystem 4 }

sm16tat2saIPConfiguration OBJECT IDENTIFIER ::= { sm16tat2saIP 1 }

sm16tat2saDNSServerMode OBJECT-TYPE
   SYNTAX INTEGER {noDNSServer(0), configured(1), fromThisDHCPInterface(2), fromAnyDHCPInterface(3)}
   MAX-ACCESS read-write
   STATUS current
   DESCRIPTION
       "DNS Server Mode.
        0: No DNS Server
        1: Configured
        2: From this DHCP interface
        3: From any DHCP interfaces
        If set: 1:Configured, please also set IPV4 or IPv6 address to DNSServerValueIPVLAN.
        If set: 2:From this DHCP interface, it will set DNSServerValueIPVLAN to VLAN 1 for default, please set it to your value."
   ::= { sm16tat2saIPConfiguration 1 }

sm16tat2saDNSServerIPAddress OBJECT-TYPE
   SYNTAX DisplayString
   MAX-ACCESS read-write
   STATUS current
   DESCRIPTION
       "DNS IPv4/IPv6 Address.
        For set IPv4/IPv6 Address, please set DNSServerMode to : 1:Configured first."
   ::= { sm16tat2saIPConfiguration 2 }

sm16tat2saDNSServerVLAN OBJECT-TYPE
   SYNTAX Integer32 (1..4095)
   MAX-ACCESS read-write
   STATUS current
   DESCRIPTION
       "VLAN value.
        For set VLAN value, please set DNSServerMode to : 2:From this DHCP interface first.
        For set VLAN value, please set an interface with IPv4 DHCP enable. And then set VLAN to it."
   ::= { sm16tat2saIPConfiguration 3 }

sm16tat2saIPInterfacesTable OBJECT-TYPE
   SYNTAX SEQUENCE OF SM16TAT2SAIPInterfacesEntry
   MAX-ACCESS not-accessible
   STATUS current
   DESCRIPTION
       "A table of IP interface for switch."
    ::= { sm16tat2saIPConfiguration 4 }

sm16tat2saIPInterfacesEntry OBJECT-TYPE
    SYNTAX SM16TAT2SAIPInterfacesEntry
    MAX-ACCESS not-accessible
    STATUS current
    DESCRIPTION
        "An entry in the sm16tat2saIPInterfacesTable."
    INDEX { sm16tat2saIPInterfacesIndex }
    ::= { sm16tat2saIPInterfacesTable 1 }

SM16TAT2SAIPInterfacesEntry ::=
    SEQUENCE {
        sm16tat2saIPInterfacesIndex Integer32,
        sm16tat2saIPInterfacesVLAN Integer32,
        sm16tat2saIPInterfacesIPv4DHCPEnable Integer32,
        sm16tat2saIPInterfacesIPv4DHCPFallback Integer32,
        sm16tat2saIPInterfacesIPv4DHCPCurrentLease DisplayString,
        sm16tat2saIPInterfacesIPv4Address DisplayString,
        sm16tat2saIPInterfacesIPv4Mask Integer32,
        sm16tat2saIPInterfacesIPv6Address DisplayString,
        sm16tat2saIPInterfacesIPv6Mask Integer32,
        sm16tat2saIPInterfacesRowStatus RowStatus
    }

sm16tat2saIPInterfacesIndex OBJECT-TYPE
   SYNTAX Integer32 (1..128)
   MAX-ACCESS not-accessible
   STATUS current
   DESCRIPTION
       "Interface Table Index"
   ::= { sm16tat2saIPInterfacesEntry 1 }

sm16tat2saIPInterfacesVLAN OBJECT-TYPE
   SYNTAX Integer32 (1..4095)
   MAX-ACCESS read-create
   STATUS current
   DESCRIPTION
       "VLAN ID for interface, range: 1-4095.
        If you add a new VLAN ID here, you also need to set IPInterfacesIPv4Address, IPInterfacesIPv4Mask, or IPInterfacesIPv6Address, IPInterfacesIPv6Mask."
   ::= { sm16tat2saIPInterfacesEntry 2 }

sm16tat2saIPInterfacesIPv4DHCPEnable OBJECT-TYPE
   SYNTAX Integer32 (0|1)
   MAX-ACCESS read-create
   STATUS current
   DESCRIPTION
       "IPv4 DHCP Setting for interface.
        Please add IPInterfacesVLAN first if you want to set IPInterfacesIPv4DHCP to an empty entry in table.
        default:0
        0: disable
        1: enable"
   ::= { sm16tat2saIPInterfacesEntry 3 }

sm16tat2saIPInterfacesIPv4DHCPFallback OBJECT-TYPE
   SYNTAX Integer32
   MAX-ACCESS read-create
   STATUS current
   DESCRIPTION
       "IPv4 DHCP fallbcak. range: 1-4294967295 seconds.
        Please add IPInterfacesVLAN first if you want to set IPInterfacesIPv4DHCPFallback to an empty entry in table.
        Please enable IPInterfacesIPv4DHCP first if you want to set IPInterfacesIPv4DHCPFallback."
   ::= { sm16tat2saIPInterfacesEntry 4 }

sm16tat2saIPInterfacesIPv4DHCPCurrentLease OBJECT-TYPE
   SYNTAX DisplayString
   MAX-ACCESS read-only
   STATUS current
   DESCRIPTION
       "IPv4 DHCP Current Lease Address for interface."
   ::= { sm16tat2saIPInterfacesEntry 5 }

sm16tat2saIPInterfacesIPv4Address OBJECT-TYPE
   SYNTAX DisplayString
   MAX-ACCESS read-create
   STATUS current
   DESCRIPTION
       "IPv4 address for interface.
        Please add IPInterfacesVLAN first if you want to set IPInterfacesIPv4Address to an empty entry in table.
        If you set IPInterfacesIPv4Address, please also set IPInterfacesIPv4Mask.
        If you set IPInterfacesIPv4Address and not set IPInterfacesIPv4Mask before, it will be set to value default 24."
   ::= { sm16tat2saIPInterfacesEntry 6 }

sm16tat2saIPInterfacesIPv4Mask OBJECT-TYPE
   SYNTAX Integer32 (1..32)
   MAX-ACCESS read-create
   STATUS current
   DESCRIPTION
       "IPv4 mask for interface.
        Please add IPInterfacesVLAN first if you want to set IPInterfacesIPv4Mask to an empty entry in table.
        Please set IPInterfacesIPv4Address first and then set IPInterfacesIPv4Mask."
   ::= { sm16tat2saIPInterfacesEntry 7 }

sm16tat2saIPInterfacesIPv6Address OBJECT-TYPE
   SYNTAX DisplayString (SIZE (0..30))
   MAX-ACCESS read-create
   STATUS current
   DESCRIPTION
       "IPv6 address for interface.
        Please add IPInterfacesVLAN first if you want to set IPInterfacesIPv6Address to an empty entry in table.
        If you set IPInterfacesIPv6Address, please also set IPInterfacesIPv6Mask.
        If you set IPInterfacesIPv6Address and not set IPInterfacesIPv6Mask before, it will be set to value default 64."
   ::= { sm16tat2saIPInterfacesEntry 8 }

sm16tat2saIPInterfacesIPv6Mask OBJECT-TYPE
   SYNTAX Integer32 (1..128)
   MAX-ACCESS read-create
   STATUS current
   DESCRIPTION
       "IPv6 mask for interface.
        Please add IPInterfacesVLAN first if you want to set IPInterfacesIPv6Mask to an empty entry in table.
        Please set IPInterfacesIPv6Address first and then set IPInterfacesIPv6Mask."
   ::= { sm16tat2saIPInterfacesEntry 9 }

sm16tat2saIPInterfacesRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm16tat2saIPInterfacesEntry 10 }

sm16tat2saIPRoutesTable OBJECT-TYPE
   SYNTAX SEQUENCE OF SM16TAT2SAIPRoutesEntry
   MAX-ACCESS not-accessible
   STATUS current
   DESCRIPTION
       "IP routes table for switch."
   ::= { sm16tat2saIPConfiguration 5 }

sm16tat2saIPRoutesEntry OBJECT-TYPE
   SYNTAX SM16TAT2SAIPRoutesEntry
   MAX-ACCESS not-accessible
   STATUS current
   DESCRIPTION
       "Entry in the sm16tat2saIPRoutesTable."
   INDEX { sm16tat2saIPRoutesIndex }
   ::= { sm16tat2saIPRoutesTable 1 }

SM16TAT2SAIPRoutesEntry ::=
    SEQUENCE {
        sm16tat2saIPRoutesIndex Integer32,
        sm16tat2saIPRoutesNetwork DisplayString,
        sm16tat2saIPRoutesMaskLength Integer32,
        sm16tat2saIPRoutesGateway DisplayString,
        sm16tat2saIPRoutesNextHopVLAN Integer32,
        sm16tat2saIPRoutesRowStatus RowStatus
    }

sm16tat2saIPRoutesIndex OBJECT-TYPE
   SYNTAX Integer32 (1..32)
   MAX-ACCESS not-accessible
   STATUS current
   DESCRIPTION
       "routes table index"
   ::= { sm16tat2saIPRoutesEntry 1 }

sm16tat2saIPRoutesNetwork OBJECT-TYPE
   SYNTAX DisplayString
   MAX-ACCESS read-create
   STATUS current
   DESCRIPTION
       "IPv4/IPv6 Network address.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry.
        If Set IPRoutesNetwork, please also set IPRoutesMaskLength, IPRoutesGateway, IPRoutesNextHopVLAN."
   ::= { sm16tat2saIPRoutesEntry 2 }

sm16tat2saIPRoutesMaskLength OBJECT-TYPE
   SYNTAX Integer32 (1..32)
   MAX-ACCESS read-create
   STATUS current
   DESCRIPTION
       "IPv4/IPv6 mask length.
        Please set IPRoutesNetwork first.
        Note: All entries in routes table will be sort by 1.network address 2.mask length 3. gateway 4. next hop VLAN, if you add/modify an entry, all entries will be reordered. Please check all entries in table to find your modified entry after set/add an entry."
   ::= { sm16tat2saIPRoutesEntry 3 }

sm16tat2saIPRoutesGateway OBJECT-TYPE
   SYNTAX DisplayString
   MAX-ACCESS read-create
   STATUS current
   DESCRIPTION
       "IPv4/IPv6 Gateway.
        Please set IPRoutesNetwork first.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry."
   ::= { sm16tat2saIPRoutesEntry 4 }

sm16tat2saIPRoutesNextHopVLAN OBJECT-TYPE
   SYNTAX Integer32 (1..4095)
   MAX-ACCESS read-create
   STATUS current
   DESCRIPTION
       "Next Hop VLAN ID, range: 1-4095.
        Please set IPRoutesNetwork first.
        This entry only work when 1.network address is IPv6, 2.Gateway is link-local, 3.Interface of specific VLAN ID is IPv6.
        Note: All entries in routes table will be sort by 1.network address 2.mask length 3. gateway 4. next hop VLAN, if you add/modify an entry, all entries will be reordered. Please check all entries in table to find your modified entry after set/add an entry."
   ::= { sm16tat2saIPRoutesEntry 5 }

sm16tat2saIPRoutesRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm16tat2saIPRoutesEntry 6 }

sm16tat2saIPStatusInterfaceTable OBJECT-TYPE
   SYNTAX SEQUENCE OF SM16TAT2SAIPStatusInterfaceEntry
   MAX-ACCESS not-accessible
   STATUS current
   DESCRIPTION
       "The system IP Status table to show all IP interfaces."
   ::= { sm16tat2saIPConfiguration 6 }

sm16tat2saIPStatusInterfaceEntry OBJECT-TYPE
   SYNTAX SM16TAT2SAIPStatusInterfaceEntry
   MAX-ACCESS not-accessible
   STATUS current
   DESCRIPTION
       "An entry in the IP Status Table."
       INDEX { sm16tat2saIPStatusInterfaceIndex }
   ::= { sm16tat2saIPStatusInterfaceTable 1 }

SM16TAT2SAIPStatusInterfaceEntry ::=
   SEQUENCE {
       sm16tat2saIPStatusInterfaceIndex Integer32,
       sm16tat2saIPStatusInterfaceName DisplayString,
       sm16tat2saIPStatusInterfaceType DisplayString,
       sm16tat2saIPStatusInterfaceAddress DisplayString,
       sm16tat2saIPStatusInterfaceStatus DisplayString
   }

sm16tat2saIPStatusInterfaceIndex OBJECT-TYPE
   SYNTAX Integer32(1..1024)
   MAX-ACCESS not-accessible
   STATUS current
   DESCRIPTION
       "The entry of table to show all IP interfaces."
   ::= { sm16tat2saIPStatusInterfaceEntry 1 }

sm16tat2saIPStatusInterfaceName OBJECT-TYPE
   SYNTAX DisplayString
   MAX-ACCESS read-only
   STATUS current
   DESCRIPTION
       "The name of the interface."
   ::= { sm16tat2saIPStatusInterfaceEntry 2 }

sm16tat2saIPStatusInterfaceType OBJECT-TYPE
   SYNTAX DisplayString
   MAX-ACCESS read-only
   STATUS current
   DESCRIPTION
       "The address type of the entry. This may be LINK or IPv4."
   ::= { sm16tat2saIPStatusInterfaceEntry 3 }

sm16tat2saIPStatusInterfaceAddress OBJECT-TYPE
   SYNTAX DisplayString
   MAX-ACCESS read-only
   STATUS current
   DESCRIPTION
       "The current address of the interface (of the given type)."
   ::= { sm16tat2saIPStatusInterfaceEntry 4 }

sm16tat2saIPStatusInterfaceStatus OBJECT-TYPE
   SYNTAX DisplayString
   MAX-ACCESS read-only
   STATUS current
   DESCRIPTION
       "The status flags of the interface (and/or address)."
   ::= { sm16tat2saIPStatusInterfaceEntry 5 }

sm16tat2saIPStatusRouteTable OBJECT-TYPE
   SYNTAX SEQUENCE OF SM16TAT2SAIPStatusRouteEntry
   MAX-ACCESS not-accessible
   STATUS current
   DESCRIPTION
      "The IP Status Route table show all routing entries."
   ::= { sm16tat2saIPConfiguration 7 }

sm16tat2saIPStatusRouteEntry OBJECT-TYPE
   SYNTAX SM16TAT2SAIPStatusRouteEntry
   MAX-ACCESS not-accessible
   STATUS current
   DESCRIPTION
       "an entry in the IP Status route table."
       INDEX { sm16tat2saIPStatusRouteIndex }
   ::= { sm16tat2saIPStatusRouteTable 1 }

SM16TAT2SAIPStatusRouteEntry ::=
   SEQUENCE {
       sm16tat2saIPStatusRouteIndex Integer32,
       sm16tat2saIPStatusRouteNetwork DisplayString,
       sm16tat2saIPStatusRouteGateway DisplayString,
       sm16tat2saIPStatusRouteStatus DisplayString,
       sm16tat2saIPStatusRouteInterface DisplayString
   }

sm16tat2saIPStatusRouteIndex OBJECT-TYPE
   SYNTAX Integer32(1..2048)
   MAX-ACCESS not-accessible
   STATUS current
   DESCRIPTION
       "The entry of table to show all routing entries."
   ::= { sm16tat2saIPStatusRouteEntry 1 }

sm16tat2saIPStatusRouteNetwork OBJECT-TYPE
   SYNTAX DisplayString
   MAX-ACCESS read-only
   STATUS current
   DESCRIPTION
       "The destination IP network or host address of this route."
   ::= { sm16tat2saIPStatusRouteEntry 2 }

sm16tat2saIPStatusRouteGateway OBJECT-TYPE
   SYNTAX DisplayString
   MAX-ACCESS read-only
   STATUS current
   DESCRIPTION
       "The gateway address of this route."
   ::= { sm16tat2saIPStatusRouteEntry 3 }

sm16tat2saIPStatusRouteStatus OBJECT-TYPE
   SYNTAX DisplayString
   MAX-ACCESS read-only
   STATUS current
   DESCRIPTION
       "The route address."
   ::= { sm16tat2saIPStatusRouteEntry 4 }

sm16tat2saIPStatusRouteInterface OBJECT-TYPE
   SYNTAX DisplayString
   MAX-ACCESS read-only
   STATUS current
   DESCRIPTION
       "The route interface."
   ::= { sm16tat2saIPStatusRouteEntry 5 }

sm16tat2saIPStatusNeighborCacheTable OBJECT-TYPE
   SYNTAX SEQUENCE OF SM16TAT2SAIPStatusNeighborCacheEntry
   MAX-ACCESS not-accessible
   STATUS current
   DESCRIPTION
       "The Ip Status Neighbor Cache Table."
   ::= { sm16tat2saIPConfiguration 8 }

sm16tat2saIPStatusNeighborCacheEntry OBJECT-TYPE
   SYNTAX SM16TAT2SAIPStatusNeighborCacheEntry
   MAX-ACCESS not-accessible
   STATUS current
   DESCRIPTION
       "An entry in the Ip Status Neighbor Cache Table."
       INDEX { sm16tat2saIPStatusNeighborCacheIndex }
   ::= { sm16tat2saIPStatusNeighborCacheTable 1 }

SM16TAT2SAIPStatusNeighborCacheEntry ::=
   SEQUENCE {
       sm16tat2saIPStatusNeighborCacheIndex Integer32,
       sm16tat2saIPStatusNeighborCacheIPAddress DisplayString,
       sm16tat2saIPStatusNeighborCacheLinkAddress DisplayString
   }

sm16tat2saIPStatusNeighborCacheIndex OBJECT-TYPE
   SYNTAX Integer32(1..1024)
   MAX-ACCESS not-accessible
   STATUS current
   DESCRIPTION
       "The index for the Ip Status Neighbor Cache Table."
   ::= { sm16tat2saIPStatusNeighborCacheEntry 1 }

sm16tat2saIPStatusNeighborCacheIPAddress OBJECT-TYPE
   SYNTAX DisplayString
   MAX-ACCESS read-only
   STATUS current
   DESCRIPTION
       "The IP address of the entry."
   ::= { sm16tat2saIPStatusNeighborCacheEntry 2 }

sm16tat2saIPStatusNeighborCacheLinkAddress OBJECT-TYPE
   SYNTAX DisplayString
   MAX-ACCESS read-only
   STATUS current
   DESCRIPTION
       "The Link (MAC) address for which a binding to the IP address given exist."
   ::= { sm16tat2saIPStatusNeighborCacheEntry 3 }

sm16tat2saIPInterfaces OBJECT IDENTIFIER ::= { sm16tat2saIP 2 }

sm16tat2saIPInterfacesDHCPPerPort OBJECT IDENTIFIER ::= { sm16tat2saIPInterfaces 1 }

sm16tat2saIPInterfacesDHCPPerPortMode OBJECT-TYPE
   SYNTAX INTEGER { disable(0), enable(1) }
   MAX-ACCESS read-write
   STATUS current
   DESCRIPTION
       "The dhcp per-port mode for the interface.
        0: Disable,
        1: Enable,
        default: Disable. "
   ::= { sm16tat2saIPInterfacesDHCPPerPort 2 }

sm16tat2saIPInterfacesDHCPPerPortVlan OBJECT-TYPE
   SYNTAX Integer32
   MAX-ACCESS read-write
   STATUS current
   DESCRIPTION
       "The dhcp per-port vlan for the interface."
   ::= { sm16tat2saIPInterfacesDHCPPerPort 3 }

sm16tat2saIPInterfacesDHCPPerPortIPRangeLow OBJECT-TYPE
   SYNTAX DisplayString
   MAX-ACCESS read-write
   STATUS current
   DESCRIPTION
       "The dhcp per-port ip range low for the interface."
   ::= { sm16tat2saIPInterfacesDHCPPerPort 4 }

sm16tat2saIPInterfacesDHCPPerPortIPRangeHigh OBJECT-TYPE
   SYNTAX DisplayString
   MAX-ACCESS read-write
   STATUS current
   DESCRIPTION
       "The dhcp per-port ip range high for the interface."
   ::= { sm16tat2saIPInterfacesDHCPPerPort 5 }

sm16tat2saIPInterfacesDHCPPerPortRowStatus OBJECT-TYPE
   SYNTAX INTEGER { active(1),
                          notInService(2),
                          notReady(3),
                          createAndGo(4),
                          createAndWait(5),
                          destroy(6) }
   MAX-ACCESS read-write
   STATUS current
   DESCRIPTION
       "The dhcp per-port RowStatus for the interface."
   ::= { sm16tat2saIPInterfacesDHCPPerPort 10 }

-- *************************************************************
-- Objects in the sm16tat2saSyslog Group
-- *************************************************************
sm16tat2saSyslog OBJECT IDENTIFIER ::= { sm16tat2saSystem 5 }

sm16tat2saSyslogConf OBJECT IDENTIFIER ::= { sm16tat2saSyslog 1 }

sm16tat2saSystemLogServerMode OBJECT-TYPE
   SYNTAX AdminMode
   MAX-ACCESS read-write
   STATUS current
   DESCRIPTION
       "The System log server mode admin state."
   ::= { sm16tat2saSyslogConf 1 }

sm16tat2saSystemLogServerTable OBJECT-TYPE
   SYNTAX SEQUENCE OF SM16TAT2SASystemLogServerEntry
   MAX-ACCESS not-accessible
   STATUS current
   DESCRIPTION
       " "
   ::= { sm16tat2saSyslogConf 2 }

sm16tat2saSystemLogServerEntry OBJECT-TYPE
   SYNTAX SM16TAT2SASystemLogServerEntry
   MAX-ACCESS not-accessible
   STATUS current
   DESCRIPTION
       " "
   INDEX { sm16tat2saSystemLogServerIndex }
   ::= { sm16tat2saSystemLogServerTable 1 }

SM16TAT2SASystemLogServerEntry ::= SEQUENCE {
   sm16tat2saSystemLogServerIndex Integer32,
   sm16tat2saSystemLogServerAddress IpAddress
}

sm16tat2saSystemLogServerIndex OBJECT-TYPE
   SYNTAX Integer32(1..6)
   MAX-ACCESS not-accessible
   STATUS current
   DESCRIPTION
       " The index of the server entry. "
   ::= { sm16tat2saSystemLogServerEntry 1 }

sm16tat2saSystemLogServerAddress OBJECT-TYPE
   SYNTAX IpAddress
   MAX-ACCESS read-write
   STATUS current
   DESCRIPTION
       "The Host ip address of syslog server."
   ::= { sm16tat2saSystemLogServerEntry 2 }

sm16tat2saSysLogInfo OBJECT IDENTIFIER ::= { sm16tat2saSyslog 2 }

sm16tat2saSystemLogInfoClear OBJECT-TYPE
   SYNTAX ActivateCmd
   MAX-ACCESS read-write
   STATUS current
   DESCRIPTION
      "System log will be cleared."
   ::= { sm16tat2saSysLogInfo 1 }

sm16tat2saSystemLogDetailedInfoTable OBJECT-TYPE
  SYNTAX SEQUENCE OF SM16TAT2SASystemLogDetailedInfoEntry
  MAX-ACCESS not-accessible
  STATUS current
  DESCRIPTION
           "The system detailed Log Info table."
       ::= { sm16tat2saSysLogInfo 2 }

sm16tat2saSystemLogDetailedInfoEntry OBJECT-TYPE
   SYNTAX SM16TAT2SASystemLogDetailedInfoEntry
   MAX-ACCESS not-accessible
   STATUS current
   DESCRIPTION
           "An entry in the system detailed Log Info table."
   INDEX { sm16tat2saSystemLogDetailedInfoID }
   ::= { sm16tat2saSystemLogDetailedInfoTable 1 }

SM16TAT2SASystemLogDetailedInfoEntry ::= SEQUENCE {
    sm16tat2saSystemLogDetailedInfoID Integer32,
    sm16tat2saSystemLogDetailedInfoLevel SeverityLevel,
    sm16tat2saSystemLogDetailedInfoTime DisplayString,
    sm16tat2saSystemLogDetailedInfoMessage DisplayString
}

sm16tat2saSystemLogDetailedInfoID OBJECT-TYPE
   SYNTAX Integer32(1..65535)
   MAX-ACCESS not-accessible
   STATUS current
   DESCRIPTION
       "The index for the system detailed Log Info table."
   ::= { sm16tat2saSystemLogDetailedInfoEntry 1 }

sm16tat2saSystemLogDetailedInfoLevel OBJECT-TYPE
   SYNTAX SeverityLevel
   MAX-ACCESS read-only
   STATUS current
   DESCRIPTION
       "The Info Level."
   ::= { sm16tat2saSystemLogDetailedInfoEntry 2 }

sm16tat2saSystemLogDetailedInfoTime OBJECT-TYPE
   SYNTAX DisplayString(SIZE (0..20))
   MAX-ACCESS read-only
   STATUS current
   DESCRIPTION
       "The time"
   ::= { sm16tat2saSystemLogDetailedInfoEntry 3 }

sm16tat2saSystemLogDetailedInfoMessage OBJECT-TYPE
   SYNTAX DisplayString
   MAX-ACCESS read-only
   STATUS current
   DESCRIPTION
       "The message of this entry."
   ::= { sm16tat2saSystemLogDetailedInfoEntry 4 }

-- *************************************************************
-- Start sm16tat2saSnmp group
-- *************************************************************
sm16tat2saSnmp OBJECT IDENTIFIER ::= { sm16tat2saSystem 6 }

sm16tat2saSnmpGetCommunity OBJECT-TYPE
   SYNTAX DisplayString
   MAX-ACCESS read-write
   STATUS current
   DESCRIPTION
       "Get/Set the get-community of the SNMP."
   ::= { sm16tat2saSnmp 1 }

sm16tat2saSnmpSetCommunityMode OBJECT-TYPE
   SYNTAX INTEGER { disable(0), enable(1) }
   MAX-ACCESS read-write
   STATUS current
   DESCRIPTION
       "Get/Set the set-community mode of the SNMP.
        default : 1, 0: disable, 1: enable. "
   ::= { sm16tat2saSnmp 2 }

sm16tat2saSnmpSetCommunity OBJECT-TYPE
   SYNTAX DisplayString
   MAX-ACCESS read-write
   STATUS current
   DESCRIPTION
       "Get/Set the set-community of the SNMP."
   ::= { sm16tat2saSnmp 3 }

sm16tat2saSnmpVersion OBJECT-TYPE
   SYNTAX Integer32
   MAX-ACCESS read-only
   STATUS current
   DESCRIPTION
       "Get the get/set-community version of the SNMP."
   ::= { sm16tat2saSnmp 6 }

sm16tat2saSnmpCommunityTable OBJECT-TYPE
   SYNTAX SEQUENCE OF SM16TAT2SASnmpCommunityEntry
   MAX-ACCESS not-accessible
   STATUS current
   DESCRIPTION
       "A list of snmp community entry."
   ::= { sm16tat2saSnmp 4 }

sm16tat2saSnmpCommunityEntry OBJECT-TYPE
   SYNTAX SM16TAT2SASnmpCommunityEntry
   MAX-ACCESS not-accessible
   STATUS current
   DESCRIPTION
       "This is the entry information for snmp community."
   INDEX { sm16tat2saSnmpCommunityIndex }
   ::= { sm16tat2saSnmpCommunityTable 1 }

SM16TAT2SASnmpCommunityEntry ::= SEQUENCE {
    sm16tat2saSnmpCommunityIndex Integer32,
    sm16tat2saSnmpCommunityName DisplayString,
    sm16tat2saSnmpCommunityIP IpAddress,
    sm16tat2saSnmpCommunityMask Integer32,
    sm16tat2saSnmpCommunityRowStatus RowStatus
}

sm16tat2saSnmpCommunityIndex OBJECT-TYPE
   SYNTAX Integer32(1..6)
   MAX-ACCESS not-accessible
   STATUS current
   DESCRIPTION
       " The index of the snmp community entry. "
   ::= { sm16tat2saSnmpCommunityEntry 1 }

sm16tat2saSnmpCommunityName OBJECT-TYPE
   SYNTAX DisplayString(SIZE(1..32))
   MAX-ACCESS read-create
   STATUS current
   DESCRIPTION
       "Indicates the community access string to permit access to
       SNMPv3 agent. The community string will be treated as
       security name and map a SNMPv1 or SNMPv2c community string. "
   ::= { sm16tat2saSnmpCommunityEntry 2 }

sm16tat2saSnmpCommunityIP OBJECT-TYPE
   SYNTAX IpAddress
   MAX-ACCESS read-create
   STATUS current
   DESCRIPTION
       "Indicates the SNMP access source address. A particular
       range of source addresses can be used to restrict source
       subnet when combined with source mask."
   ::= { sm16tat2saSnmpCommunityEntry 3 }

sm16tat2saSnmpCommunityMask OBJECT-TYPE
   SYNTAX Integer32
   MAX-ACCESS read-create
   STATUS current
   DESCRIPTION
       "Indicates the SNMP access source address mask."
   ::= { sm16tat2saSnmpCommunityEntry 4 }

sm16tat2saSnmpCommunityRowStatus OBJECT-TYPE
   SYNTAX RowStatus
   MAX-ACCESS read-create
   STATUS current
   DESCRIPTION
       "This object indicates the status of this entry, and is
       used to create/delete entries. Any object in an entry of
       this table may be modified while the value of the
       corresponding instance of this object is active(1).
       notReady(3) and createAndGo(4) not supported."
   ::= { sm16tat2saSnmpCommunityEntry 5 }

sm16tat2saTrapHostConfTable OBJECT-TYPE
   SYNTAX SEQUENCE OF SM16TAT2SATrapHostConfEntry
   MAX-ACCESS not-accessible
   STATUS current
   DESCRIPTION
       "A list of trap host entry."
   ::= { sm16tat2saSnmp 5 }

sm16tat2saTrapHostConfEntry OBJECT-TYPE
   SYNTAX SM16TAT2SATrapHostConfEntry
   MAX-ACCESS not-accessible
   STATUS current
   DESCRIPTION
       "This is the entry information for trap host."
   INDEX { sm16tat2saTrapHostConfIndex }
   ::= { sm16tat2saTrapHostConfTable 1 }

SM16TAT2SATrapHostConfEntry ::= SEQUENCE {
    sm16tat2saTrapHostConfIndex Integer32,
    sm16tat2saTrapHostConfVersion DisplayString,
    sm16tat2saTrapHostConfMode INTEGER,
    sm16tat2saTrapHostConfIP DisplayString,
    sm16tat2saTrapHostConfPort Integer32,
    sm16tat2saTrapHostConfCommunity DisplayString,
    sm16tat2saTrapHostConfSeverityLevel SeverityLevel,
    sm16tat2saTrapHostConfCurrentMode INTEGER
}

sm16tat2saTrapHostConfIndex OBJECT-TYPE
   SYNTAX Integer32(1..6)
   MAX-ACCESS not-accessible
   STATUS current
   DESCRIPTION
       " The index of the trap host entry. "
   ::= { sm16tat2saTrapHostConfEntry 1 }

sm16tat2saTrapHostConfVersion OBJECT-TYPE
   SYNTAX DisplayString
   MAX-ACCESS read-only
   STATUS current
   DESCRIPTION
       "The version of the Trap PDU."
   ::= { sm16tat2saTrapHostConfEntry 2 }

sm16tat2saTrapHostConfMode OBJECT-TYPE
   SYNTAX INTEGER { disabled(0), udp(1), tcp(2) }
   MAX-ACCESS read-write
   STATUS current
   DESCRIPTION
       "ndicates the trap destination mode operation.
        0:disabled, 1:udp, 2:tcp."
   ::= { sm16tat2saTrapHostConfEntry 3 }

sm16tat2saTrapHostConfIP OBJECT-TYPE
   SYNTAX DisplayString
   MAX-ACCESS read-write
   STATUS current
   DESCRIPTION
       "This is the IP of the trap host."
   ::= { sm16tat2saTrapHostConfEntry 4 }

sm16tat2saTrapHostConfPort OBJECT-TYPE
   SYNTAX Integer32(1..65535)
   MAX-ACCESS read-write
   STATUS current
   DESCRIPTION
       "Indicates the SNMP trap destination port.
        SNMP Agent will send SNMP message via this port,
        the port range is 1~65535. "
   ::= { sm16tat2saTrapHostConfEntry 5 }

sm16tat2saTrapHostConfCommunity OBJECT-TYPE
   SYNTAX DisplayString (SIZE (1..32))
   MAX-ACCESS read-write
   STATUS current
   DESCRIPTION
       "The community name for the trap PDU."
   ::= { sm16tat2saTrapHostConfEntry 6 }

sm16tat2saTrapHostConfSeverityLevel OBJECT-TYPE
   SYNTAX SeverityLevel
   MAX-ACCESS read-write
   STATUS current
   DESCRIPTION
       "The Severity Level."
    ::= { sm16tat2saTrapHostConfEntry 7 }

sm16tat2saTrapHostConfCurrentMode OBJECT-TYPE
   SYNTAX INTEGER { empty(0), active(1), edit(2), delete(3) }
   MAX-ACCESS read-write
   STATUS current
   DESCRIPTION
       "0:Empty, 1:Active mode, 2:Edit mode, 3:Delete."
   ::= { sm16tat2saTrapHostConfEntry 13 }

-- *************************************************************
-- Start sm16tat2saPrivilegeLevel group
-- *************************************************************
sm16tat2saPrivilegeLevel OBJECT IDENTIFIER ::= { sm16tat2saSystem 7 }

sm16tat2saPrivilegeLevelConfigTable OBJECT-TYPE
   SYNTAX SEQUENCE OF SM16TAT2SAPrivilegeLevelConfigEntry
   MAX-ACCESS not-accessible
   STATUS current
   DESCRIPTION
       "The Privilege Level Config Table. "
   ::= { sm16tat2saPrivilegeLevel 1 }

sm16tat2saPrivilegeLevelConfigEntry OBJECT-TYPE
   SYNTAX SM16TAT2SAPrivilegeLevelConfigEntry
   MAX-ACCESS not-accessible
   STATUS current
   DESCRIPTION
       "The Privilege Level Config Entry."
   INDEX { sm16tat2saPrivilegeLevelIndex }
   ::= { sm16tat2saPrivilegeLevelConfigTable 1 }

SM16TAT2SAPrivilegeLevelConfigEntry ::=
SEQUENCE {
   sm16tat2saPrivilegeLevelIndex Integer32,
   sm16tat2saPrivilegeLevelGroupName DisplayString,
   sm16tat2saPrivilegeLevelConfigReadOnly Integer32,
   sm16tat2saPrivilegeLevelConfigReadWrite Integer32
}

sm16tat2saPrivilegeLevelIndex OBJECT-TYPE
   SYNTAX Integer32 (1..34)
   MAX-ACCESS not-accessible
   STATUS current
   DESCRIPTION
       "The Privilege Level Index. "
   ::= { sm16tat2saPrivilegeLevelConfigEntry 1 }

sm16tat2saPrivilegeLevelGroupName OBJECT-TYPE
   SYNTAX DisplayString
   MAX-ACCESS read-write
   STATUS current
   DESCRIPTION
       "The name identifying the privilege group."
   ::= { sm16tat2saPrivilegeLevelConfigEntry 2 }

sm16tat2saPrivilegeLevelConfigReadOnly OBJECT-TYPE
   SYNTAX Integer32 (0..15)
   MAX-ACCESS read-write
   STATUS current
   DESCRIPTION
       "The privilege level of configuration read-only.If the privilege level value is 15,it can access all groups.
        range: 0-15. "
   ::= { sm16tat2saPrivilegeLevelConfigEntry 3 }

sm16tat2saPrivilegeLevelConfigReadWrite OBJECT-TYPE
   SYNTAX Integer32 (0..15)
   MAX-ACCESS read-write
   STATUS current
   DESCRIPTION
       "The privilege level of configuration/execute read/write. If the privilege level value is 15,it can access all groups.
        range: 0-15. "
   ::= { sm16tat2saPrivilegeLevelConfigEntry 4 }

-- *************************************************************
-- Start sm16tat2saLldpConfig group
-- *************************************************************
sm16tat2saLldpConfig OBJECT IDENTIFIER ::= { sm16tat2saSystem 8 }

sm16tat2saLldpConfigTable OBJECT-TYPE
    SYNTAX SEQUENCE OF SM16TAT2SALldpConfigEntry
    MAX-ACCESS not-accessible
    STATUS current
    DESCRIPTION
        "This is a table to configure LLDP configurations for a specific
         interface."
    ::= { sm16tat2saLldpConfig 1 }

sm16tat2saLldpConfigEntry OBJECT-TYPE
    SYNTAX SM16TAT2SALldpConfigEntry
    MAX-ACCESS not-accessible
    STATUS current
    DESCRIPTION
        "Each interface has a set of control parameters"
    INDEX { sm16tat2saLldpConfigIfIndex }
    ::= { sm16tat2saLldpConfigTable 1 }

SM16TAT2SALldpConfigEntry ::= SEQUENCE {
    sm16tat2saLldpConfigIfIndex Integer32,
    sm16tat2saLldpConfigCdpAware INTEGER
}

sm16tat2saLldpConfigIfIndex OBJECT-TYPE
    SYNTAX Integer32 (1..4095)
    MAX-ACCESS not-accessible
    STATUS current
    DESCRIPTION
        "Logical interface number index."
    ::= { sm16tat2saLldpConfigEntry 1 }

sm16tat2saLldpConfigCdpAware OBJECT-TYPE
    SYNTAX INTEGER { disable(0), enable(1) }
    MAX-ACCESS read-write
    STATUS current
    DESCRIPTION
        "Enables/disables CDP awareness for the interface.

         CDP is Cisco's equivalent to LLDP.

         The CDP operation is restricted to decoding incoming CDP frames (The
         switch doesn't transmit CDP frames). CDP frames are only decoded if
         LLDP on the port is enabled.

         Only CDP TLVs that can be mapped to a corresponding field in the LLDP
         neighbors' table are decoded. All other TLVs are discarded
         (Unrecognized CDP TLVs and discarded CDP frames are not shown in the
         LLDP statistics.).

         CDP TLVs are mapped onto LLDP neighbors' table as shown below.

         CDP TLV 'Device ID' is mapped to the LLDP 'Chassis ID' field.

         CDP TLV 'Address' is mapped to the LLDP 'Management Address' field. The
         CDP address TLV can contain multiple addresses, but only the first
         address is shown in the LLDP neighbors table.

         CDP TLV 'Port ID' is mapped to the LLDP 'Port ID' field.

         CDP TLV 'Version and Platform' is mapped to the LLDP 'System
         Description' field.

         Both the CDP and LLDP support 'system capabilities', but the CDP
         capabilities cover capabilities that are not part of the LLDP. These
         capabilities are shown as 'others' in the LLDP neighbors' table.

         If all ports have CDP awareness disabled the switch forwards CDP frames
         received from neighbor devices. If at least one port has CDP awareness
         enabled all CDP frames are terminated by the switch.

         Note: When CDP awareness on a port is disabled the CDP information
         isn't removed immediately, but gets removed when the hold time is
         exceeded."
    ::= { sm16tat2saLldpConfigEntry 2 }

sm16tat2saLldpMedLocInfo OBJECT IDENTIFIER ::= { sm16tat2saLldpConfig 2 }

sm16tat2saLldpMedLatitude OBJECT-TYPE
    SYNTAX Integer32
    MAX-ACCESS read-write
    STATUS current
    DESCRIPTION
        "Latitude degrees"
    ::= { sm16tat2saLldpMedLocInfo 1 }

sm16tat2saLldpMedLatitudeDirection OBJECT-TYPE
    SYNTAX INTEGER { north(0), south(1) }
    MAX-ACCESS read-write
    STATUS current
    DESCRIPTION
        "Latitude degrees direction"
    ::= { sm16tat2saLldpMedLocInfo 2 }

sm16tat2saLldpMedLongitude OBJECT-TYPE
    SYNTAX Integer32
    MAX-ACCESS read-write
    STATUS current
    DESCRIPTION
        "Longitude degrees"
    ::= { sm16tat2saLldpMedLocInfo 3 }

sm16tat2saLldpMedLongitudeDirection OBJECT-TYPE
    SYNTAX INTEGER { east(0), west(1) }
    MAX-ACCESS read-write
    STATUS current
    DESCRIPTION
        "Longitude degrees"
    ::= { sm16tat2saLldpMedLocInfo 4 }

sm16tat2saLldpMedAltitude OBJECT-TYPE
    SYNTAX Integer32
    MAX-ACCESS read-write
    STATUS current
    DESCRIPTION
        "Altitude value"
    ::= { sm16tat2saLldpMedLocInfo 5 }

sm16tat2saLldpMedAltitudeType OBJECT-TYPE
    SYNTAX LldpmedAltitudeType
    MAX-ACCESS read-write
    STATUS current
    DESCRIPTION
        "Setting altitude type

         Possible to select between two altitude types (floors or meters).
         Meters are representing meters of altitude defined by the vertical
         datum specified. Floors are representing altitude in a form more
         relevant in buildings which have different floor-to-floor dimensions.
         An altitude = 0.0 is meaningful even outside a building, and represents
         ground level at the given latitude and longitude. Inside a building,
         0.0 represents the floor level associated with ground level at the main
         entrance."
    ::= { sm16tat2saLldpMedLocInfo 6 }

sm16tat2saLldpMedDatum OBJECT-TYPE
    SYNTAX LldpmedDatumType
    MAX-ACCESS read-write
    STATUS current
    DESCRIPTION
        "Setting datum to configure the datum (geodetic system) to use.

         The Map Datum is used for the coordinates given in these options:

         WGS84: (Geographical 3D) - World Geodesic System 1984, CRS Code 4327,
         Prime Meridian Name: Greenwich.

         NAD83/NAVD88: North American Datum 1983, CRS Code 4269, Prime Meridian
         Name: Greenwich;The associated vertical datum is the North American
         Vertical Datum of 1988 (NAVD88).This datum pair is to be used when
         referencing locations on land, not near tidal water(which would use
         Datum = NAD83/MLLW).

         NAD83/MLLW: North American Datum 1983, CRS Code 4269, Prime Meridian
         Name: Greenwich; The associated vertical datum is Mean Lower Low Water
         (MLLW). This datum pair is to be used when referencing locations on
         water/sea/ocean."
    ::= { sm16tat2saLldpMedLocInfo 7 }

sm16tat2saLldpMedElinAddr OBJECT-TYPE
    SYNTAX DisplayString (SIZE(0..25))
    MAX-ACCESS read-write
    STATUS current
    DESCRIPTION
        "Emergency Call Service ELIN identifier data format is defined to carry
         the ELIN identifier as used during emergency call setup to a
         traditional CAMA or ISDN trunk-based PSAP. This format consists of a
         numerical digit string, corresponding to the ELIN to be used for
         emergency calling. Maximum number of octets are 25."
    ::= { sm16tat2saLldpMedLocInfo 8 }

sm16tat2saLldpMedCivicAddrLocInfoCountryCode OBJECT-TYPE
    SYNTAX DisplayString (SIZE(0..2))
    MAX-ACCESS read-write
    STATUS current
    DESCRIPTION
        "The two-letter ISO 3166 country code in capital ASCII letters -
         Example: DK, DE or US."
    ::= { sm16tat2saLldpMedLocInfo 9 }

sm16tat2saLldpMedCivicAddrLocInfoState OBJECT-TYPE
    SYNTAX DisplayString (SIZE(0..50))
    MAX-ACCESS read-write
    STATUS current
    DESCRIPTION
        "National subdivision"
    ::= { sm16tat2saLldpMedLocInfo 10 }

sm16tat2saLldpMedCivicAddrLocInfoCounty OBJECT-TYPE
    SYNTAX DisplayString (SIZE(0..50))
    MAX-ACCESS read-write
    STATUS current
    DESCRIPTION
        "County"
    ::= { sm16tat2saLldpMedLocInfo 11 }

sm16tat2saLldpMedCivicAddrLocInfoCity OBJECT-TYPE
    SYNTAX DisplayString (SIZE(0..50))
    MAX-ACCESS read-write
    STATUS current
    DESCRIPTION
        "City"
    ::= { sm16tat2saLldpMedLocInfo 12 }

sm16tat2saLldpMedCivicAddrLocInfoDistrict OBJECT-TYPE
    SYNTAX DisplayString (SIZE(0..50))
    MAX-ACCESS read-write
    STATUS current
    DESCRIPTION
        "City district"
    ::= { sm16tat2saLldpMedLocInfo 13 }

sm16tat2saLldpMedCivicAddrLocInfoBlock OBJECT-TYPE
    SYNTAX DisplayString (SIZE(0..50))
    MAX-ACCESS read-write
    STATUS current
    DESCRIPTION
        "Block (Neighborhood)"
    ::= { sm16tat2saLldpMedLocInfo 14 }

sm16tat2saLldpMedCivicAddrLocInfoStreet OBJECT-TYPE
    SYNTAX DisplayString (SIZE(0..50))
    MAX-ACCESS read-write
    STATUS current
    DESCRIPTION
        "Street"
    ::= { sm16tat2saLldpMedLocInfo 15 }

sm16tat2saLldpMedCivicAddrLocInfoLeadingStreetDirection OBJECT-TYPE
    SYNTAX DisplayString (SIZE(0..50))
    MAX-ACCESS read-write
    STATUS current
    DESCRIPTION
        "Street Direction"
    ::= { sm16tat2saLldpMedLocInfo 16 }

sm16tat2saLldpMedCivicAddrLocInfoTrailingStreetSuffix OBJECT-TYPE
    SYNTAX DisplayString (SIZE(0..50))
    MAX-ACCESS read-write
    STATUS current
    DESCRIPTION
        "Trailing Street Suffix"
    ::= { sm16tat2saLldpMedLocInfo 17 }

sm16tat2saLldpMedCivicAddrLocInfoStreetSuffix OBJECT-TYPE
    SYNTAX DisplayString (SIZE(0..50))
    MAX-ACCESS read-write
    STATUS current
    DESCRIPTION
        "Street Suffix"
    ::= { sm16tat2saLldpMedLocInfo 18 }

sm16tat2saLldpMedCivicAddrLocInfoHouseNo OBJECT-TYPE
    SYNTAX DisplayString (SIZE(0..50))
    MAX-ACCESS read-write
    STATUS current
    DESCRIPTION
        "House No."
    ::= { sm16tat2saLldpMedLocInfo 19 }

sm16tat2saLldpMedCivicAddrLocInfoHouseNoSuffix OBJECT-TYPE
    SYNTAX DisplayString (SIZE(0..50))
    MAX-ACCESS read-write
    STATUS current
    DESCRIPTION
        "House No. Suffix"
    ::= { sm16tat2saLldpMedLocInfo 20 }

sm16tat2saLldpMedCivicAddrLocInfoLandmark OBJECT-TYPE
    SYNTAX DisplayString (SIZE(0..50))
    MAX-ACCESS read-write
    STATUS current
    DESCRIPTION
        "Landmark"
    ::= { sm16tat2saLldpMedLocInfo 21 }

sm16tat2saLldpMedCivicAddrLocInfoAdditionalInfo OBJECT-TYPE
    SYNTAX DisplayString (SIZE(0..50))
    MAX-ACCESS read-write
    STATUS current
    DESCRIPTION
        "Additional Location Info"
    ::= { sm16tat2saLldpMedLocInfo 22 }

sm16tat2saLldpMedCivicAddrLocInfoName OBJECT-TYPE
    SYNTAX DisplayString (SIZE(0..50))
    MAX-ACCESS read-write
    STATUS current
    DESCRIPTION
        "Name"
    ::= { sm16tat2saLldpMedLocInfo 23 }

sm16tat2saLldpMedCivicAddrLocInfoZipCode OBJECT-TYPE
    SYNTAX DisplayString (SIZE(0..50))
    MAX-ACCESS read-write
    STATUS current
    DESCRIPTION
        "Zip code"
    ::= { sm16tat2saLldpMedLocInfo 24 }

sm16tat2saLldpMedCivicAddrLocInfoBuilding OBJECT-TYPE
    SYNTAX DisplayString (SIZE(0..50))
    MAX-ACCESS read-write
    STATUS current
    DESCRIPTION
        "Building"
    ::= { sm16tat2saLldpMedLocInfo 25 }

sm16tat2saLldpMedCivicAddrLocInfoApartment OBJECT-TYPE
    SYNTAX DisplayString (SIZE(0..50))
    MAX-ACCESS read-write
    STATUS current
    DESCRIPTION
        "Apartment/unit"
    ::= { sm16tat2saLldpMedLocInfo 26 }

sm16tat2saLldpMedCivicAddrLocInfoFloor OBJECT-TYPE
    SYNTAX DisplayString (SIZE(0..50))
    MAX-ACCESS read-write
    STATUS current
    DESCRIPTION
        "Floor"
    ::= { sm16tat2saLldpMedLocInfo 27 }

sm16tat2saLldpMedCivicAddrLocInfoRoomNumber OBJECT-TYPE
    SYNTAX DisplayString (SIZE(0..50))
    MAX-ACCESS read-write
    STATUS current
    DESCRIPTION
        "Room Number"
    ::= { sm16tat2saLldpMedLocInfo 28 }

sm16tat2saLldpMedCivicAddrLocInfoPlaceType OBJECT-TYPE
    SYNTAX DisplayString (SIZE(0..50))
    MAX-ACCESS read-write
    STATUS current
    DESCRIPTION
        "Place type"
    ::= { sm16tat2saLldpMedLocInfo 29 }

sm16tat2saLldpMedCivicAddrLocInfoPostalCommunityName OBJECT-TYPE
    SYNTAX DisplayString (SIZE(0..50))
    MAX-ACCESS read-write
    STATUS current
    DESCRIPTION
        "Postal Community Name"
    ::= { sm16tat2saLldpMedLocInfo 30 }

sm16tat2saLldpMedCivicAddrLocInfoPoBox OBJECT-TYPE
    SYNTAX DisplayString (SIZE(0..50))
    MAX-ACCESS read-write
    STATUS current
    DESCRIPTION
        "Post Office Box"
    ::= { sm16tat2saLldpMedLocInfo 31 }

sm16tat2saLldpMedCivicAddrLocInfoAdditionalCode OBJECT-TYPE
    SYNTAX DisplayString (SIZE(0..50))
    MAX-ACCESS read-write
    STATUS current
    DESCRIPTION
        "Addination Code"
    ::= { sm16tat2saLldpMedLocInfo 32 }

-- ************************************************************
-- Start sm16tat2saVLANConf group
-- *************************************************************
sm16tat2saVLANConf OBJECT IDENTIFIER ::= { sm16tat2saSystem 10 }

sm16tat2saVLAN OBJECT IDENTIFIER ::= { sm16tat2saVLANConf 2}

sm16tat2saVlanExistingVLANs OBJECT-TYPE
   SYNTAX DisplayString
   MAX-ACCESS read-write
   STATUS current
   DESCRIPTION
       "This field shows the VLANs that are created on the switch.
        More VLANs may be created by using a
        list syntax where the individual elements are separated by commas.
        Ranges are specified with a
        dash separating the lower and upper bound.
        The following example will create VLANs 1, 10, 11, 12
        , 13, 200, and 300: 1,10-13,200,300.
        default: 1."
   ::= { sm16tat2saVLAN 1 }

sm16tat2saVlanEthertypeforCustomSPorts OBJECT-TYPE
   SYNTAX DisplayString
   MAX-ACCESS read-write
   STATUS current
   DESCRIPTION
       "This field specifies the ethertype/TPID (specified in hexadecimal)
        used for Custom S-ports. The
        setting is in force for all ports whose Port Type
        is set to S-Custom-Port.
        range: 0600-ffff,
        default: 88a8."
   ::= { sm16tat2saVLAN 2 }

sm16tat2saVlanTable OBJECT-TYPE
   SYNTAX SEQUENCE OF SM16TAT2SAVlanEntry
   MAX-ACCESS not-accessible
   STATUS current
   DESCRIPTION
       "Configure Vlan ports Configuration mode.
        INDEX for this table is ifIndex which is
        equivalent to the panel port number."
   ::= { sm16tat2saVLAN 3 }

sm16tat2saVlanEntry OBJECT-TYPE
   SYNTAX SM16TAT2SAVlanEntry
   MAX-ACCESS not-accessible
   STATUS current
   DESCRIPTION
       "The Vlan entry."
   INDEX { ifIndex }
   ::= { sm16tat2saVlanTable 1 }

SM16TAT2SAVlanEntry ::= SEQUENCE {
    sm16tat2saVlanMode INTEGER,
    sm16tat2saVlanPortVLAN Integer32,
    sm16tat2saVlanPortType INTEGER,
    sm16tat2saVlanIngressFiltering AdminMode,
-- sm16tat2saVlanVLANTrunking AdminMode,
    sm16tat2saVlanIngressAcceptance INTEGER,
    sm16tat2saVlanEgressTagging INTEGER,
    sm16tat2saVlanAllowedVLANs DisplayString
-- sm16tat2saVlanForbiddenVLANs DisplayString
    }

sm16tat2saVlanMode OBJECT-TYPE
   SYNTAX INTEGER{access(0), trunk(1), hybrid(2)}
   MAX-ACCESS read-write
   STATUS current
   DESCRIPTION
       "The port mode determines the fundamental
        behavior of the port in question.
        A port can be in one of three modes as described below.
        0: access,
        1: trunk,
        2: hybrid."
   DEFVAL { access }
   ::= { sm16tat2saVlanEntry 2 }

sm16tat2saVlanPortVLAN OBJECT-TYPE
   SYNTAX Integer32(1..4094)
   MAX-ACCESS read-write
   STATUS current
   DESCRIPTION
       "Determines the port's VLAN ID (a.k.a. PVID).
        range: 1-4095,
        default: 1."
   ::= { sm16tat2saVlanEntry 3 }

sm16tat2saVlanPortType OBJECT-TYPE
   SYNTAX INTEGER { unaware(0), cPort(1), sPort(2), sCustomPort(3) }
   MAX-ACCESS read-write
   STATUS current
   DESCRIPTION
       "Ports in hybrid mode allow for changing the port type,
        that is, whether a frame's VLAN tag is
        used to classify the frame on ingress to a particular VLAN,
        and if so, which TPID it reacts on.
        Likewise, on egress, the Port Type determines the
        TPID of the tag, if a tag is required.
        0: unaware,
        1: c-Port,
        2: s-Port,
        3: s-Custom-Port."
    DEFVAL { cPort }
   ::= { sm16tat2saVlanEntry 4 }

sm16tat2saVlanIngressFiltering OBJECT-TYPE
   SYNTAX AdminMode
   MAX-ACCESS read-write
   STATUS current
   DESCRIPTION
       "Hybrid ports allow for changing ingress filtering.
        Access and Trunk ports always have ingress
        filtering enabled.If ingress filtering is enabled,
        frames classified to
        a VLAN that the port is not a member of get discarded."
   ::= { sm16tat2saVlanEntry 5 }

-- sm16tat2saVlanVLANTrunking OBJECT-TYPE
-- SYNTAX AdminMode
-- MAX-ACCESS read-write
-- STATUS current
-- DESCRIPTION
-- "Trunk and Hybrid ports allow for enabling VLAN trunking.
-- When VLAN trunking is enabled, frames
-- classified to unknown VLANs are accepted on the port
-- whether ingress filtering is enabled or not."
-- DEFVAL { disable }
-- ::= { sm16tat2saVlanEntry 6 }

sm16tat2saVlanIngressAcceptance OBJECT-TYPE
   SYNTAX INTEGER { taggedAndUntagged ( 0 ),
                          taggedOnly ( 1 ),
                          untaggedOnly ( 2 )
                        }
   MAX-ACCESS read-write
   STATUS current
   DESCRIPTION
       "Hybrid ports allow for changing the type of frames that are
        accepted on ingress.
        0: Tagged and Untagged,
        1: Tagged Only,
        2: Untagged Only."
   ::= { sm16tat2saVlanEntry 7 }

sm16tat2saVlanEgressTagging OBJECT-TYPE
   SYNTAX INTEGER { untagPortVlan ( 0 ),
                          tagAll ( 1 ),
                          untagAll ( 2 )
                        }
   MAX-ACCESS read-write
   STATUS current
   DESCRIPTION
       "Ports in Trunk and Hybrid mode may control the
        tagging of frames on egress.
        0: Untag Port VLAN,
        1: Tag All,
        2: Untag All."
   ::= { sm16tat2saVlanEntry 8 }

sm16tat2saVlanAllowedVLANs OBJECT-TYPE
   SYNTAX DisplayString
   MAX-ACCESS read-write
   STATUS current
   DESCRIPTION
       "Ports in Trunk and Hybrid mode may control which
        VLANs they are allowed to become members of.
        Access ports can only be member of one VLAN, the Access VLAN.
        range: 1~4095.
        '-': Allowed VLANs is empty."
   ::= { sm16tat2saVlanEntry 9 }

sm16tat2saVlanStatus OBJECT IDENTIFIER ::= { sm16tat2saVLAN 6 }

sm16tat2saVLANPortStatusTable OBJECT-TYPE
   SYNTAX SEQUENCE OF SM16TAT2SAVLANPortStatusEntry
   MAX-ACCESS not-accessible
   STATUS current
   DESCRIPTION
       "The vlan port status table.
        INDEX for this table is ifIndex which is
        equivalent to the panel port number."
   ::= { sm16tat2saVlanStatus 2 }

sm16tat2saVLANPortStatusEntry OBJECT-TYPE
   SYNTAX SM16TAT2SAVLANPortStatusEntry
   MAX-ACCESS not-accessible
   STATUS current
   DESCRIPTION
       "The vlan port status entry."
   INDEX { ifIndex }
   ::= { sm16tat2saVLANPortStatusTable 1 }

SM16TAT2SAVLANPortStatusEntry ::= SEQUENCE {
    sm16tat2saVLANPortStatusPortType DisplayString,
    sm16tat2saVLANPortStatusIngressFiltering AdminMode,
    sm16tat2saVLANPortStatusFrameType DisplayString,
    sm16tat2saVLANPortStatusPortVLANID Integer32,
    sm16tat2saVLANPortStatusTxTag DisplayString
-- sm16tat2saVLANPortStatusUntaggedVLANID Integer32,
-- sm16tat2saVLANPortStatusConflicts DisplayString
    }

sm16tat2saVLANPortStatusPortType OBJECT-TYPE
   SYNTAX DisplayString
   MAX-ACCESS read-only
   STATUS current
   DESCRIPTION
       "Shows the port type (Unaware, C-Port, S-Port,
        S-Custom-Port.) that a given user wants to configure on
        the port.The field is empty if not overridden by the selected user."
   ::= { sm16tat2saVLANPortStatusEntry 2 }

sm16tat2saVLANPortStatusIngressFiltering OBJECT-TYPE
   SYNTAX AdminMode
   MAX-ACCESS read-only
   STATUS current
   DESCRIPTION
       "Shows whether a given user wants ingress filtering enabled or not."
   ::= { sm16tat2saVLANPortStatusEntry 3 }

sm16tat2saVLANPortStatusFrameType OBJECT-TYPE
   SYNTAX DisplayString
   MAX-ACCESS read-only
   STATUS current
   DESCRIPTION
       "Shows the acceptable frame types (All, Taged,
        Untagged) that a given user wants to configure on the port.
        The field is empty if not overridden by the selected user."
   ::= { sm16tat2saVLANPortStatusEntry 4 }

sm16tat2saVLANPortStatusPortVLANID OBJECT-TYPE
   SYNTAX Integer32 (1..4095)
   MAX-ACCESS read-only
   STATUS current
   DESCRIPTION
       "Shows the Port VLAN ID (PVID) that a given user
        wants the port to have.
        The field is 0 if not overridden by the selected user."
   ::= { sm16tat2saVLANPortStatusEntry 5 }

sm16tat2saVLANPortStatusTxTag OBJECT-TYPE
   SYNTAX DisplayString
   MAX-ACCESS read-only
   STATUS current
   DESCRIPTION
       "Shows the Tx Tag requirements (Tag All, Tag PVID,
        Tag UVID, Untag All, Untag PVID, Untag UVID)
        that a given user has on a port.The field is empty
        if not overridden by the selected user."
   ::= { sm16tat2saVLANPortStatusEntry 6 }

sm16tat2saVclConfig OBJECT IDENTIFIER ::= { sm16tat2saVLANConf 3 }

sm16tat2saVclConfigMac OBJECT IDENTIFIER ::= { sm16tat2saVclConfig 1 }

sm16tat2saVclConfigMacBasedTable OBJECT-TYPE
    SYNTAX SEQUENCE OF SM16TAT2SAVclConfigMacBasedEntry
    MAX-ACCESS not-accessible
    STATUS current
    DESCRIPTION
        "This is the MAC address to VLAN ID configuration table."
    ::= { sm16tat2saVclConfigMac 1 }

sm16tat2saVclConfigMacBasedEntry OBJECT-TYPE
    SYNTAX SM16TAT2SAVclConfigMacBasedEntry
    MAX-ACCESS not-accessible
    STATUS current
    DESCRIPTION
        "Each entry in this table represents a configured MAC-based
         classification."
    INDEX { sm16tat2saVclConfigMacIndex }
    ::= { sm16tat2saVclConfigMacBasedTable 1 }

SM16TAT2SAVclConfigMacBasedEntry ::= SEQUENCE {
    sm16tat2saVclConfigMacIndex Integer32,
    sm16tat2saVclConfigMacMacAddress MacAddress,
    sm16tat2saVclConfigMacVlanId Integer32,
    sm16tat2saVclConfigMacRowStatus RowStatus
}

sm16tat2saVclConfigMacIndex OBJECT-TYPE
   SYNTAX Integer32 (1..128)
   MAX-ACCESS not-accessible
   STATUS current
   DESCRIPTION
       "The VclConfigMac Index."
   ::= { sm16tat2saVclConfigMacBasedEntry 1 }

sm16tat2saVclConfigMacMacAddress OBJECT-TYPE
    SYNTAX MacAddress
    MAX-ACCESS read-create
    STATUS current
    DESCRIPTION
        "The MAC address for which this entry is applicable."
    ::= { sm16tat2saVclConfigMacBasedEntry 2 }

sm16tat2saVclConfigMacVlanId OBJECT-TYPE
    SYNTAX Integer32 (1..4095)
    MAX-ACCESS read-create
    STATUS current
    DESCRIPTION
        "Vlan id of the mapping."
    ::= { sm16tat2saVclConfigMacBasedEntry 3 }

sm16tat2saVclConfigMacRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm16tat2saVclConfigMacBasedEntry 4 }

sm16tat2saVclConfigMacStatusTable OBJECT-TYPE
    SYNTAX SEQUENCE OF SM16TAT2SAVclConfigMacStatusEntry
    MAX-ACCESS not-accessible
    STATUS current
    DESCRIPTION
        "This is the MAC address to VLAN ID Status table."
    ::= { sm16tat2saVclConfigMac 2 }

sm16tat2saVclConfigMacStatusEntry OBJECT-TYPE
    SYNTAX SM16TAT2SAVclConfigMacStatusEntry
    MAX-ACCESS not-accessible
    STATUS current
    DESCRIPTION
        "Each entry in this table represents a MAC-based Status
         classification."
    INDEX { sm16tat2saVclMacStatusIndex }
    ::= { sm16tat2saVclConfigMacStatusTable 1 }

SM16TAT2SAVclConfigMacStatusEntry ::= SEQUENCE {
    sm16tat2saVclMacStatusIndex Integer32,
    sm16tat2saVclMacStatusMacAddress MacAddress,
    sm16tat2saVclMacStatusVlanId Integer32,
    sm16tat2saVclMacStatusUser INTEGER
}

sm16tat2saVclMacStatusIndex OBJECT-TYPE
   SYNTAX Integer32 (1..128)
   MAX-ACCESS not-accessible
   STATUS current
   DESCRIPTION
       "The VclConfigMac Index."
   ::= { sm16tat2saVclConfigMacStatusEntry 1 }

sm16tat2saVclMacStatusMacAddress OBJECT-TYPE
    SYNTAX MacAddress
    MAX-ACCESS read-only
    STATUS current
    DESCRIPTION
        "The MAC address for which this entry is applicable."
    ::= { sm16tat2saVclConfigMacStatusEntry 2 }

sm16tat2saVclMacStatusVlanId OBJECT-TYPE
    SYNTAX Integer32 (1..4095)
    MAX-ACCESS read-only
    STATUS current
    DESCRIPTION
        "Vlan id of the mapping."
    ::= { sm16tat2saVclConfigMacStatusEntry 3 }

sm16tat2saVclMacStatusUser OBJECT-TYPE
    SYNTAX INTEGER { static(0), dms(1) }
    MAX-ACCESS read-only
    STATUS current
    DESCRIPTION
        "User of the mapping."
    ::= { sm16tat2saVclConfigMacStatusEntry 4 }

sm16tat2saVclConfigProtocol OBJECT IDENTIFIER
    ::= { sm16tat2saVclConfig 2 }

sm16tat2saVclConfigProtocolProto OBJECT IDENTIFIER
    ::= { sm16tat2saVclConfigProtocol 1 }

sm16tat2saVclConfigProtocolProtoTable OBJECT-TYPE
    SYNTAX SEQUENCE OF SM16TAT2SAVclConfigProtocolProtoEntry
    MAX-ACCESS not-accessible
    STATUS current
    DESCRIPTION
        "This is the Protocol to Protocol Group mapping table."
    ::= { sm16tat2saVclConfigProtocolProto 1 }

sm16tat2saVclConfigProtocolProtoEntry OBJECT-TYPE
    SYNTAX SM16TAT2SAVclConfigProtocolProtoEntry
    MAX-ACCESS not-accessible
    STATUS current
    DESCRIPTION
        "Each entry in this table represents a Protocol to Group mapping."
    INDEX { sm16tat2saVclConfigProtocolProtoProtocolIndex }
    ::= { sm16tat2saVclConfigProtocolProtoTable 1 }

SM16TAT2SAVclConfigProtocolProtoEntry ::= SEQUENCE {
    sm16tat2saVclConfigProtocolProtoProtocolIndex Integer32,
    sm16tat2saVclConfigProtocolProtoProtocolType Integer32,
    sm16tat2saVclConfigProtocolProtoProtocolValue DisplayString,
    sm16tat2saVclConfigProtocolProtoProtocolGroupName DisplayString,
    sm16tat2saVclConfigProtocolProtoRowStatus RowStatus
}

sm16tat2saVclConfigProtocolProtoProtocolIndex OBJECT-TYPE
    SYNTAX Integer32 (1..64)
    MAX-ACCESS not-accessible
    STATUS current
    DESCRIPTION
        "The protocol index of the Protocol to Group mapping."
    ::= { sm16tat2saVclConfigProtocolProtoEntry 1 }

sm16tat2saVclConfigProtocolProtoProtocolType OBJECT-TYPE
   SYNTAX Integer32 (1..3)
   MAX-ACCESS read-create
   STATUS current
   DESCRIPTION
       "1: Ethernet II encapsulation, 2: LLC SNAP encapsulation, 3: LLC Other encapsulation"
   ::= { sm16tat2saVclConfigProtocolProtoEntry 2 }

sm16tat2saVclConfigProtocolProtoProtocolValue OBJECT-TYPE
   SYNTAX DisplayString (SIZE (4..11))
   MAX-ACCESS read-create
   STATUS current
   DESCRIPTION
       "Protocol Type is Ethernet(1), value range: 0x600~0xffff,
        Protocol Type is SNAP(2), OID value is 0x000000, value range: 0x0000~0xffff(pid value),
        Protocol Type is LLC(3), value range: 0x0000~0xffff(dsap value:0x00~0xff, ssap value:0x00~0xff)"
   ::= { sm16tat2saVclConfigProtocolProtoEntry 3 }

sm16tat2saVclConfigProtocolProtoProtocolGroupName OBJECT-TYPE
    SYNTAX DisplayString (SIZE(1..16))
    MAX-ACCESS read-create
    STATUS current
    DESCRIPTION
        "This is a name identifying the protocol group."
    ::= { sm16tat2saVclConfigProtocolProtoEntry 4 }

sm16tat2saVclConfigProtocolProtoRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm16tat2saVclConfigProtocolProtoEntry 5 }

sm16tat2saVclConfigProtocolGroup OBJECT IDENTIFIER
    ::= { sm16tat2saVclConfigProtocol 2 }

sm16tat2saVclConfigProtocolGroupTable OBJECT-TYPE
    SYNTAX SEQUENCE OF SM16TAT2SAVclConfigProtocolGroupEntry
    MAX-ACCESS not-accessible
    STATUS current
    DESCRIPTION
        "This is the Protocol Group to VLAN ID configuration table."
    ::= { sm16tat2saVclConfigProtocolGroup 1 }

sm16tat2saVclConfigProtocolGroupEntry OBJECT-TYPE
    SYNTAX SM16TAT2SAVclConfigProtocolGroupEntry
    MAX-ACCESS not-accessible
    STATUS current
    DESCRIPTION
        "Each entry in this table represents a Protocol Group to VLAN ID
         mapping."
    INDEX { sm16tat2saVclConfigProtocolGroupProtocolIndex }
    ::= { sm16tat2saVclConfigProtocolGroupTable 1 }

SM16TAT2SAVclConfigProtocolGroupEntry ::= SEQUENCE {
    sm16tat2saVclConfigProtocolGroupProtocolIndex Integer32,
    sm16tat2saVclConfigProtocolGroupProtocolGroupName DisplayString,
    sm16tat2saVclConfigProtocolGroupVlanId Integer32,
    sm16tat2saVclConfigProtocolGroupPortList PortSelect,
    sm16tat2saVclConfigProtocolGroupRowStatus RowStatus
}

sm16tat2saVclConfigProtocolGroupProtocolIndex OBJECT-TYPE
    SYNTAX Integer32 (1..64)
    MAX-ACCESS not-accessible
    STATUS current
    DESCRIPTION
        "The protocol index of the Protocol to Group mapping."
    ::= { sm16tat2saVclConfigProtocolGroupEntry 1 }

sm16tat2saVclConfigProtocolGroupProtocolGroupName OBJECT-TYPE
    SYNTAX DisplayString (SIZE(1..16))
    MAX-ACCESS read-create
    STATUS current
    DESCRIPTION
        "This is a name identifying the protocol group."
    ::= { sm16tat2saVclConfigProtocolGroupEntry 2 }

sm16tat2saVclConfigProtocolGroupVlanId OBJECT-TYPE
    SYNTAX Integer32 (1..4095)
    MAX-ACCESS read-create
    STATUS current
    DESCRIPTION
        "Vlan id of the mapping."
    ::= { sm16tat2saVclConfigProtocolGroupEntry 3 }

sm16tat2saVclConfigProtocolGroupPortList OBJECT-TYPE
    SYNTAX PortSelect
    MAX-ACCESS read-create
    STATUS current
    DESCRIPTION
        "List of switch ports on which this entry is active."
    ::= { sm16tat2saVclConfigProtocolGroupEntry 4 }

sm16tat2saVclConfigProtocolGroupRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm16tat2saVclConfigProtocolGroupEntry 5 }

sm16tat2saVclConfigIpTable OBJECT-TYPE
    SYNTAX SEQUENCE OF SM16TAT2SAVclConfigIpEntry
    MAX-ACCESS not-accessible
    STATUS current
    DESCRIPTION
        "This is the IP Subnet to VLAN ID configuration table. The key of this
         table is the IP subnet expressed as x.x.x.x/x, where the first 4 octets
         represent the IPv4 address and the last one is the mask length.

         NOTE#1: Inside the VCL module these entries are actually sorted based
         on a priority defined by the mask length, so that subnets with larger
         mask lengths are first in the list, followed by entries with smaller
         mask lengths. SNMP cannot follow this sorting, therefore the order the
         entries are retrieved by the iterator may not be the same as the
         actually stored order. (This is not an issue, but should be taken into
         consideration when using the SNMP interface to create a user interface.

         NOTE#2: Even though only the subnet address is stored in the table
         (i.e. both 192.168.1.0/4 and 192.168.2.0/4 will end up as 192.0.0.0/4),
         the SNMP iterator will NOT take this into consideration. So, when
         searching the next subnet of 192.168.1.0/4, the result could be
         193.0.0.0/4 but not 192.168.1.0/24 (granted that these entries are
         present)"
    ::= { sm16tat2saVclConfig 3 }

sm16tat2saVclConfigIpEntry OBJECT-TYPE
    SYNTAX SM16TAT2SAVclConfigIpEntry
    MAX-ACCESS not-accessible
    STATUS current
    DESCRIPTION
        "Each entry in this table represents a configured IP Subnet-based
         classification."
    INDEX { sm16tat2saVclConfigIpIndex }
    ::= { sm16tat2saVclConfigIpTable 1 }

SM16TAT2SAVclConfigIpEntry ::= SEQUENCE {
    sm16tat2saVclConfigIpIndex Integer32,
    sm16tat2saVclConfigIpIpSubnetAddress IpAddress,
    sm16tat2saVclConfigIpIpSubnetMaskLength Integer32,
    sm16tat2saVclConfigIpVlanId Integer32,
    sm16tat2saVclConfigIpRowStatus RowStatus
}

sm16tat2saVclConfigIpIndex OBJECT-TYPE
   SYNTAX Integer32 (1..64)
   MAX-ACCESS not-accessible
   STATUS current
   DESCRIPTION
       "The VclConfigIp Index."
   ::= { sm16tat2saVclConfigIpEntry 1 }

sm16tat2saVclConfigIpIpSubnetAddress OBJECT-TYPE
    SYNTAX IpAddress
    MAX-ACCESS read-create
    STATUS current
    DESCRIPTION
        "The IP subnet address for which this entry is applicable."
    ::= { sm16tat2saVclConfigIpEntry 2 }

sm16tat2saVclConfigIpIpSubnetMaskLength OBJECT-TYPE
    SYNTAX Integer32 (1..32)
    MAX-ACCESS read-create
    STATUS current
    DESCRIPTION
        "The IP subnet mask length for which this entry is applicable."
    ::= { sm16tat2saVclConfigIpEntry 3 }

sm16tat2saVclConfigIpVlanId OBJECT-TYPE
    SYNTAX Integer32 (1..4095)
    MAX-ACCESS read-create
    STATUS current
    DESCRIPTION
        "Vlan id of the mapping."
    ::= { sm16tat2saVclConfigIpEntry 4 }

sm16tat2saVclConfigIpRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm16tat2saVclConfigIpEntry 5 }

sm16tat2saVlanSelectiveQinQ OBJECT IDENTIFIER ::= { sm16tat2saVLANConf 4 }

sm16tat2saVlanSelectiveTable OBJECT-TYPE
    SYNTAX SEQUENCE OF SM16TAT2SAVlanSelectiveEntry
    MAX-ACCESS not-accessible
    STATUS current
    DESCRIPTION
        "This is the Vlan Selective QinQ configuration table."
    ::= { sm16tat2saVlanSelectiveQinQ 1 }

sm16tat2saVlanSelectiveEntry OBJECT-TYPE
    SYNTAX SM16TAT2SAVlanSelectiveEntry
    MAX-ACCESS not-accessible
    STATUS current
    DESCRIPTION
        "Each entry in this table represents a configured selective qinq."
    INDEX { sm16tat2saVlanSelectiveIndex }
    ::= { sm16tat2saVlanSelectiveTable 1 }

SM16TAT2SAVlanSelectiveEntry ::= SEQUENCE {
    sm16tat2saVlanSelectiveIndex Integer32,
    sm16tat2saVlanSelectiveCVID Integer32,
    sm16tat2saVlanSelectiveSPID Integer32,
    sm16tat2saVlanSelectivePortList PortSelect,
    sm16tat2saVlanSelectiveRowStatus RowStatus
}

sm16tat2saVlanSelectiveIndex OBJECT-TYPE
   SYNTAX Integer32 (1..128)
   MAX-ACCESS not-accessible
   STATUS current
   DESCRIPTION
       "The Vlan Selective QinQ Index."
   ::= { sm16tat2saVlanSelectiveEntry 1 }

sm16tat2saVlanSelectiveCVID OBJECT-TYPE
    SYNTAX Integer32 (1..4094)
    MAX-ACCESS read-create
    STATUS current
    DESCRIPTION
        "The CVID for which this entry is applicable."
    ::= { sm16tat2saVlanSelectiveEntry 2 }

sm16tat2saVlanSelectiveSPID OBJECT-TYPE
    SYNTAX Integer32 (1..4094)
    MAX-ACCESS read-create
    STATUS current
    DESCRIPTION
        "The SPID for which this entry is applicable."
    ::= { sm16tat2saVlanSelectiveEntry 3 }

sm16tat2saVlanSelectivePortList OBJECT-TYPE
    SYNTAX PortSelect
    MAX-ACCESS read-create
    STATUS current
    DESCRIPTION
        "List of switch ports on which this entry is active."
    ::= { sm16tat2saVlanSelectiveEntry 4 }

sm16tat2saVlanSelectiveRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm16tat2saVlanSelectiveEntry 5 }

sm16tat2saPvlanConfig OBJECT IDENTIFIER ::= { sm16tat2saVLANConf 5 }

sm16tat2saPvlanConfigVlanMembershipTable OBJECT-TYPE
    SYNTAX SEQUENCE OF SM16TAT2SAPvlanConfigVlanMembershipEntry
    MAX-ACCESS not-accessible
    STATUS current
    DESCRIPTION
        "This is a table for managing Private VLAN VLAN membership entries."
    ::= { sm16tat2saPvlanConfig 1 }

sm16tat2saPvlanConfigVlanMembershipEntry OBJECT-TYPE
    SYNTAX SM16TAT2SAPvlanConfigVlanMembershipEntry
    MAX-ACCESS not-accessible
    STATUS current
    DESCRIPTION
        "Each entry has a set of parameters."
    INDEX { sm16tat2saPvlanConfigVlanMembershipPvlanIndex }
    ::= { sm16tat2saPvlanConfigVlanMembershipTable 1 }

SM16TAT2SAPvlanConfigVlanMembershipEntry ::= SEQUENCE {
    sm16tat2saPvlanConfigVlanMembershipPvlanIndex Integer32,
    sm16tat2saPvlanConfigVlanMembershipPvlanId Integer32,
    sm16tat2saPvlanConfigVlanMembershipPortList PortSelect,
    sm16tat2saPvlanConfigVlanMembershipRowStatus RowStatus
}

sm16tat2saPvlanConfigVlanMembershipPvlanIndex OBJECT-TYPE
   SYNTAX Integer32 (1..128)
   MAX-ACCESS not-accessible
   STATUS current
   DESCRIPTION
       "Configuration index of the Private VLAN membership table."
   ::= { sm16tat2saPvlanConfigVlanMembershipEntry 1 }

sm16tat2saPvlanConfigVlanMembershipPvlanId OBJECT-TYPE
    SYNTAX Integer32 (1..128)
    MAX-ACCESS read-create
    STATUS current
    DESCRIPTION
        "Configuration Private vlan Id of the Private VLAN membership table."
    ::= { sm16tat2saPvlanConfigVlanMembershipEntry 2 }

sm16tat2saPvlanConfigVlanMembershipPortList OBJECT-TYPE
    SYNTAX PortSelect
    MAX-ACCESS read-create
    STATUS current
    DESCRIPTION
        "It is used to denote the memberships of the specific Private VLAN configuration."
    ::= { sm16tat2saPvlanConfigVlanMembershipEntry 3 }

sm16tat2saPvlanConfigVlanMembershipRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm16tat2saPvlanConfigVlanMembershipEntry 4 }

sm16tat2saPvlanConfigPortIsolatationTable OBJECT-TYPE
    SYNTAX SEQUENCE OF SM16TAT2SAPvlanConfigPortIsolatationEntry
    MAX-ACCESS not-accessible
    STATUS current
    DESCRIPTION
        "This is a table for managing Private VLAN port isolation entries."
    ::= { sm16tat2saPvlanConfig 2 }

sm16tat2saPvlanConfigPortIsolatationEntry OBJECT-TYPE
    SYNTAX SM16TAT2SAPvlanConfigPortIsolatationEntry
    MAX-ACCESS not-accessible
    STATUS current
    DESCRIPTION
        "Each entry has a set of parameters."
    INDEX { sm16tat2saPvlanConfigPortIsolatationPortIndex }
    ::= { sm16tat2saPvlanConfigPortIsolatationTable 1 }

SM16TAT2SAPvlanConfigPortIsolatationEntry ::= SEQUENCE {
    sm16tat2saPvlanConfigPortIsolatationPortIndex Integer32,
    sm16tat2saPvlanConfigPortIsolatationEnabled INTEGER
}

sm16tat2saPvlanConfigPortIsolatationPortIndex OBJECT-TYPE
    SYNTAX Integer32(1..4095)
    MAX-ACCESS not-accessible
    STATUS current
    DESCRIPTION
        "Logical number of the Private VLAN port isolation."
    ::= { sm16tat2saPvlanConfigPortIsolatationEntry 1 }

sm16tat2saPvlanConfigPortIsolatationEnabled OBJECT-TYPE
    SYNTAX INTEGER { disable(0), enable(1) }
    MAX-ACCESS read-write
    STATUS current
    DESCRIPTION
        "Enable/Disable the Private VLAN isolation functionality."
    ::= { sm16tat2saPvlanConfigPortIsolatationEntry 2 }

sm16tat2saVoiceVlanConfig OBJECT IDENTIFIER ::= { sm16tat2saVLANConf 6 }

sm16tat2saVoiceVlanGlobalConfig OBJECT IDENTIFIER ::= { sm16tat2saVoiceVlanConfig 1 }

sm16tat2saVoiceVlanConfigTable OBJECT-TYPE
    SYNTAX SEQUENCE OF SM16TAT2SAVoiceVlanConfigEntry
    MAX-ACCESS not-accessible
    STATUS current
    DESCRIPTION
        "This is the Voice Vlan configuration table."
    ::= { sm16tat2saVoiceVlanGlobalConfig 1 }

sm16tat2saVoiceVlanConfigEntry OBJECT-TYPE
    SYNTAX SM16TAT2SAVoiceVlanConfigEntry
    MAX-ACCESS not-accessible
    STATUS current
    DESCRIPTION
        "Each entry in this table represents a configured Voice Vlan
         classification."
    INDEX { sm16tat2saVoiceVlanConfigGlobalsMgmtIndex }
    ::= { sm16tat2saVoiceVlanConfigTable 1 }

SM16TAT2SAVoiceVlanConfigEntry ::= SEQUENCE {
    sm16tat2saVoiceVlanConfigGlobalsMgmtIndex Integer32,
    sm16tat2saVoiceVlanConfigGlobalsMgmtVlanId Integer32,
    sm16tat2saVoiceVlanConfigGlobalsMgmtAgingTime Integer32,
    sm16tat2saVoiceVlanConfigGlobalsMgmtTrafficClass Integer32,
    sm16tat2saVoiceVlanConfigGlobalsMgmtPortList PortSelect,
    sm16tat2saVoiceVlanConfigGlobalsMgmtRowStatus RowStatus
}

sm16tat2saVoiceVlanConfigGlobalsMgmtIndex OBJECT-TYPE
   SYNTAX Integer32 (1..4)
   MAX-ACCESS not-accessible
   STATUS current
   DESCRIPTION
       "The Voice Vlan Config Global Management Index."
   ::= { sm16tat2saVoiceVlanConfigEntry 1 }

sm16tat2saVoiceVlanConfigGlobalsMgmtVlanId OBJECT-TYPE
    SYNTAX Integer32 (1..4095)
    MAX-ACCESS read-create
    STATUS current
    DESCRIPTION
        "Voice Vlan VlanId."
    ::= { sm16tat2saVoiceVlanConfigEntry 2 }

sm16tat2saVoiceVlanConfigGlobalsMgmtAgingTime OBJECT-TYPE
    SYNTAX Integer32 (10..10000000)
    MAX-ACCESS read-create
    STATUS current
    DESCRIPTION
        "Voice Vlan Vlan Age Time."
    ::= { sm16tat2saVoiceVlanConfigEntry 3 }

sm16tat2saVoiceVlanConfigGlobalsMgmtTrafficClass OBJECT-TYPE
    SYNTAX Integer32 (0..7)
    MAX-ACCESS read-create
    STATUS current
    DESCRIPTION
        "Voice Vlan Vlan Traffic Class."
    ::= { sm16tat2saVoiceVlanConfigEntry 4 }

sm16tat2saVoiceVlanConfigGlobalsMgmtPortList OBJECT-TYPE
    SYNTAX PortSelect
    MAX-ACCESS read-create
    STATUS current
    DESCRIPTION
        "List of switch ports on which this entry is active."
    ::= { sm16tat2saVoiceVlanConfigEntry 5 }

sm16tat2saVoiceVlanConfigGlobalsMgmtRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm16tat2saVoiceVlanConfigEntry 6 }

sm16tat2saVoiceVlanConfigInterface OBJECT IDENTIFIER
    ::= { sm16tat2saVoiceVlanConfig 2 }

sm16tat2saVoiceVlanConfigInterfacePortTable OBJECT-TYPE
    SYNTAX SEQUENCE OF SM16TAT2SAVoiceVlanConfigInterfacePortEntry
    MAX-ACCESS not-accessible
    STATUS current
    DESCRIPTION
        "This is a table for managing per port voice VLAN functions."
    ::= { sm16tat2saVoiceVlanConfigInterface 1 }

sm16tat2saVoiceVlanConfigInterfacePortEntry OBJECT-TYPE
    SYNTAX SM16TAT2SAVoiceVlanConfigInterfacePortEntry
    MAX-ACCESS not-accessible
    STATUS current
    DESCRIPTION
        "Each entry has a set of parameters."
    INDEX { sm16tat2saVoiceVlanConfigInterfacePortIfIndex }
    ::= { sm16tat2saVoiceVlanConfigInterfacePortTable 1 }

SM16TAT2SAVoiceVlanConfigInterfacePortEntry ::= SEQUENCE {
    sm16tat2saVoiceVlanConfigInterfacePortIfIndex Integer32,
    sm16tat2saVoiceVlanConfigInterfacePortMode VoiceVlanPortManagementType,
    sm16tat2saVoiceVlanConfigInterfacePortSecured INTEGER,
    sm16tat2saVoiceVlanConfigInterfacePortDiscoveryProtocol VoiceVlanPortDiscoveryProtocol
}

sm16tat2saVoiceVlanConfigInterfacePortIfIndex OBJECT-TYPE
    SYNTAX Integer32(1..1024)
    MAX-ACCESS not-accessible
    STATUS current
    DESCRIPTION
        "Logical interface number of the Voice VLAN port."
    ::= { sm16tat2saVoiceVlanConfigInterfacePortEntry 1 }

sm16tat2saVoiceVlanConfigInterfacePortMode OBJECT-TYPE
    SYNTAX VoiceVlanPortManagementType
    MAX-ACCESS read-write
    STATUS current
    DESCRIPTION
        "Management mode of the specific port in voice VLAN.
         'forced' will force the port to join voice VLAN.
         'automatic' will join the port in voice VLAN upon detecting
         attached VoIP devices by using DiscoveryProtocol parameter."
    ::= { sm16tat2saVoiceVlanConfigInterfacePortEntry 2 }

sm16tat2saVoiceVlanConfigInterfacePortSecured OBJECT-TYPE
    SYNTAX INTEGER { disable(0), enable(1) }
    MAX-ACCESS read-write
    STATUS current
    DESCRIPTION
        "Manage the security control of this port interface in voice VLAN, TRUE
         is to enable the security control and FALSE is to disable it. When it
         is disabled, all the traffic in voice VLAN will be permit. When it is
         enabled, all non-telephonic MAC addresses in the voice VLAN will be
         blocked for 10 seconds and thus the traffic from these senders will be
         deny."
    ::= { sm16tat2saVoiceVlanConfigInterfacePortEntry 3 }

sm16tat2saVoiceVlanConfigInterfacePortDiscoveryProtocol OBJECT-TYPE
    SYNTAX VoiceVlanPortDiscoveryProtocol
    MAX-ACCESS read-write
    STATUS current
    DESCRIPTION
        "Specify the protocol for detecting attached VoIP devices. It only works
         when 'automatic' is set in Mode parameter, and voice VLAN will restart
         automatic detecting process upon changing the protocol. When 'oui' is
         given, voice VLAN performs VoIP device detection based on checking
         telephony OUI settings via new MAC address notification. When 'lldp' is
         given, voice VLAN performs VoIP device detection based on LLDP
         notifications.When 'both' is given, voice VLAN performs VoIP device
         detection based on either new MAC address notification or LLDP
         notifications.

         In addition, the first come notification will be first served."
    ::= { sm16tat2saVoiceVlanConfigInterfacePortEntry 4 }

sm16tat2saVoiceVlanConfigOui OBJECT IDENTIFIER
    ::= { sm16tat2saVoiceVlanConfig 3 }

sm16tat2saVoiceVlanConfigOuiTable OBJECT-TYPE
    SYNTAX SEQUENCE OF SM16TAT2SAVoiceVlanConfigOuiEntry
    MAX-ACCESS not-accessible
    STATUS current
    DESCRIPTION
        "This is a table for managing the telephony OUI settings that will be
         used for voice VLAN functions."
    ::= { sm16tat2saVoiceVlanConfigOui 1 }

sm16tat2saVoiceVlanConfigOuiEntry OBJECT-TYPE
    SYNTAX SM16TAT2SAVoiceVlanConfigOuiEntry
    MAX-ACCESS not-accessible
    STATUS current
    DESCRIPTION
        "Each entry has a set of parameters."
    INDEX { sm16tat2saVoiceVlanConfigOuiIndex }
    ::= { sm16tat2saVoiceVlanConfigOuiTable 1 }

SM16TAT2SAVoiceVlanConfigOuiEntry ::= SEQUENCE {
    sm16tat2saVoiceVlanConfigOuiIndex Integer32,
    sm16tat2saVoiceVlanConfigOuiPrefix OCTET STRING,
    sm16tat2saVoiceVlanConfigOuiDescription DisplayString,
    sm16tat2saVoiceVlanConfigOuiRowStatus RowStatus
}

sm16tat2saVoiceVlanConfigOuiIndex OBJECT-TYPE
   SYNTAX Integer32 (1..32)
   MAX-ACCESS not-accessible
   STATUS current
   DESCRIPTION
       "The Voice Vlan Config Oui Index."
   ::= { sm16tat2saVoiceVlanConfigOuiEntry 1 }

sm16tat2saVoiceVlanConfigOuiPrefix OBJECT-TYPE
    SYNTAX OCTET STRING (SIZE(3..3))
    MAX-ACCESS read-create
    STATUS current
    DESCRIPTION
        "Address prefix of the telephony OUI. A leading 3 bytes index used to
         denote whether specific MAC address is presenting a voice device."
    ::= { sm16tat2saVoiceVlanConfigOuiEntry 2 }

sm16tat2saVoiceVlanConfigOuiDescription OBJECT-TYPE
    SYNTAX DisplayString (SIZE(0..32))
    MAX-ACCESS read-create
    STATUS current
    DESCRIPTION
        "The description for the specific telephony OUI."
    ::= { sm16tat2saVoiceVlanConfigOuiEntry 3 }

sm16tat2saVoiceVlanConfigOuiRowStatus OBJECT-TYPE
    SYNTAX RowStatus
    MAX-ACCESS read-create
    STATUS current
    DESCRIPTION
        "This object indicates the status of this entry, and is
        used to create/delete entries. Any object in an entry of
        this table may be modified while the value of the
        corresponding instance of this object is active(1).
        notReady(3) and createAndGo(4) not supported."
    ::= { sm16tat2saVoiceVlanConfigOuiEntry 4 }

-- *************************************************************
-- Start sm16tat2saUpnpConfigGlobals group
-- *************************************************************
sm16tat2saUpnpConfigGlobals OBJECT IDENTIFIER ::= { sm16tat2saSystem 11 }

sm16tat2saUpnpConfigGlobalsMode OBJECT-TYPE
    SYNTAX INTEGER { disable(0), enable(1) }
    MAX-ACCESS read-write
    STATUS current
    DESCRIPTION
        "Global mode of UPnP. true is to enable the functions of HTTPS and false
         is to disable it."
    ::= { sm16tat2saUpnpConfigGlobals 1 }

sm16tat2saUpnpConfigGlobalsInterfaceVlan OBJECT-TYPE
    SYNTAX Integer32 (1..4095)
    MAX-ACCESS read-write
    STATUS current
    DESCRIPTION
        "The Interface Vlan is used by UPnP to send SSDP advertisement messages in the Interface.
         Valid values are in the range 1 to 4095. "
    ::= { sm16tat2saUpnpConfigGlobals 2 }

sm16tat2saUpnpConfigGlobalsTtl OBJECT-TYPE
    SYNTAX Integer32 (1..255)
    MAX-ACCESS read-write
    STATUS current
    DESCRIPTION
        "The TTL value is used by UPnP to send SSDP advertisement messages.Valid
         values are in the range 1 to 255. "
    ::= { sm16tat2saUpnpConfigGlobals 3 }

sm16tat2saUpnpConfigGlobalsAdvertisingDuration OBJECT-TYPE
    SYNTAX Integer32 (66..86400)
    MAX-ACCESS read-write
    STATUS current
    DESCRIPTION
        "The duration, carried in SSDP packets, is used to inform a control
         point or control points how often it or they should receive an SSDP
         advertisement message from this switch. If a control point does not
         receive any message within the duration, it will think that the switch
         no longer exists. Due to the unreliable nature of UDP, in the standard
         it is recommended that such refreshing of advertisements to be done at
         less than one-half of the advertising duration. In the implementation,
         the switch sends SSDP messages periodically at the interval one-half of
         the advertising duration minus 30 seconds. Valid values are in the
         range 66 to 86400. "
    ::= { sm16tat2saUpnpConfigGlobals 4 }

-- *************************************************************
-- Start sm16tat2saSystemConformance group
-- *************************************************************
sm16tat2saSystemConformance OBJECT IDENTIFIER ::= { sm16tat2saSystem 200 }
sm16tat2saSystemCompliances OBJECT IDENTIFIER ::= { sm16tat2saSystemConformance 1 }
sm16tat2saSystemGroups OBJECT IDENTIFIER ::= { sm16tat2saSystemConformance 2 }

sm16tat2saSystemInformationGroup OBJECT-GROUP
    OBJECTS {
    --sm16tat2saSystemInformation
        sm16tat2saSystemInfoModelName,
        sm16tat2saSystemInfoSystemDescript,
        sm16tat2saSystemInfoHardwareVersion,
        sm16tat2saSystemInfoMechanicalVersion,
        sm16tat2saSystemInfoFirmwareVersion,
        sm16tat2saSystemInfoHostMACAddress,
        sm16tat2saSystemInfoSeriesNumber,
        sm16tat2saSystemInfoSystemName,
        sm16tat2saSystemInfoLocation,
        sm16tat2saSystemInfoContact,
        sm16tat2saSystemInfoSystemDate,
        sm16tat2saSystemInfoSystemUptime

        ,sm16tat2saSystemInfoPoEFirmwareVersion

    }
    STATUS current
    DESCRIPTION
        "The collection of objects which are used to
        indicate system information."
    ::= { sm16tat2saSystemGroups 1 }

sm16tat2saSystemTimeConfGroup OBJECT-GROUP
    OBJECTS {
    --sm16tat2saSystemTimeConf
      --sm16tat2saSystemTimeManual
        sm16tat2saSystemTimeManualClockSource,
        sm16tat2saSystemTimeManualLocaltime,
        sm16tat2saSystemTimeManualTimeZoneOffset,
        sm16tat2saSystemTimeManualTimeZoneAcronym,
        sm16tat2saSystemTimeManualDaylightSavings,
        sm16tat2saSystemTimeManualTimeSetOffset,
        sm16tat2saSystemTimeManualDaylightSavingsMonthFrom,
        sm16tat2saSystemTimeManualDaylightSavingsWeekFrom,
        sm16tat2saSystemTimeManualDaylightSavingsDayFrom,
        sm16tat2saSystemTimeManualDaylightSavingsHourFrom,
        sm16tat2saSystemTimeManualDaylightSavingsMonthTo,
        sm16tat2saSystemTimeManualDaylightSavingsWeekTo,
        sm16tat2saSystemTimeManualDaylightSavingsDayTo,
        sm16tat2saSystemTimeManualDaylightSavingsHourTo,

      --sm16tat2saSystemTimeNTP
        sm16tat2saSystemTimeNTPInterval,

        --sm16tat2saSystemTimeNTPTable
        sm16tat2saSystemTimeNTPServer
    }
    STATUS current
    DESCRIPTION
        "The collection of objects which are used to
        indicate system time information."
    ::= { sm16tat2saSystemGroups 2 }

sm16tat2saSystemAccountGroup OBJECT-GROUP
    OBJECTS {
    --sm16tat2saSystemAccount
      --sm16tat2saSystemUsersTable
        sm16tat2saUserName,
        sm16tat2saPassword,
        sm16tat2saUserPrivilegeLevel,
        sm16tat2saAccountUserRowStatus
    }
    STATUS current
    DESCRIPTION
        "The collection of objects which are used to
        indicate system account information."
    ::= { sm16tat2saSystemGroups 3 }

sm16tat2saIPGroup OBJECT-GROUP
    OBJECTS {
    --sm16tat2saIP
      --sm16tat2saIPConfiguration
        sm16tat2saDNSServerMode,
        sm16tat2saDNSServerIPAddress,
        sm16tat2saDNSServerVLAN,

        --sm16tat2saIPInterfacesTable
        sm16tat2saIPInterfacesVLAN,
        sm16tat2saIPInterfacesIPv4DHCPEnable,
        sm16tat2saIPInterfacesIPv4DHCPFallback,
        sm16tat2saIPInterfacesIPv4DHCPCurrentLease,
        sm16tat2saIPInterfacesIPv4Address,
        sm16tat2saIPInterfacesIPv4Mask,
        sm16tat2saIPInterfacesIPv6Address,
        sm16tat2saIPInterfacesIPv6Mask,
        sm16tat2saIPInterfacesRowStatus,

        --sm16tat2saIPRoutesTable
        sm16tat2saIPRoutesNetwork,
        sm16tat2saIPRoutesMaskLength,
        sm16tat2saIPRoutesGateway,
        sm16tat2saIPRoutesNextHopVLAN,
        sm16tat2saIPRoutesRowStatus,

        --sm16tat2saIPStatusInterfaceTable
        sm16tat2saIPStatusInterfaceName,
        sm16tat2saIPStatusInterfaceType,
        sm16tat2saIPStatusInterfaceAddress,
        sm16tat2saIPStatusInterfaceStatus,

        --sm16tat2saIPStatusRouteTable
        sm16tat2saIPStatusRouteNetwork,
        sm16tat2saIPStatusRouteGateway,
        sm16tat2saIPStatusRouteStatus,
        sm16tat2saIPStatusRouteInterface,

        --sm16tat2saIPStatusNeighborCacheTable
        sm16tat2saIPStatusNeighborCacheIPAddress,
        sm16tat2saIPStatusNeighborCacheLinkAddress,

      --sm16tat2saIPInterfaces
        --sm16tat2saIPInterfacesDHCPPerPort
        sm16tat2saIPInterfacesDHCPPerPortMode,
        sm16tat2saIPInterfacesDHCPPerPortVlan,
        sm16tat2saIPInterfacesDHCPPerPortIPRangeLow,
        sm16tat2saIPInterfacesDHCPPerPortIPRangeHigh,
        sm16tat2saIPInterfacesDHCPPerPortRowStatus
    }
    STATUS current
    DESCRIPTION
        "The collection of objects which are used to
        indicate IP information."
    ::= { sm16tat2saSystemGroups 4 }

sm16tat2saSyslogGroup OBJECT-GROUP
    OBJECTS {
    --sm16tat2saSyslog
      --sm16tat2saSyslogConf
        sm16tat2saSystemLogServerMode,
        --sm16tat2saSystemLogServerTable
        sm16tat2saSystemLogServerAddress,

      --sm16tat2saSysLogInfo
        sm16tat2saSystemLogInfoClear,
        --sm16tat2saSystemLogDetailedInfoTable
        sm16tat2saSystemLogDetailedInfoLevel,
        sm16tat2saSystemLogDetailedInfoTime,
        sm16tat2saSystemLogDetailedInfoMessage
    }
    STATUS current
    DESCRIPTION
        "The collection of objects which are used to
        indicate syslog information."
    ::= { sm16tat2saSystemGroups 5 }

sm16tat2saSnmpGroup OBJECT-GROUP
    OBJECTS {
    --sm16tat2saSnmp
        sm16tat2saSnmpGetCommunity,
        sm16tat2saSnmpSetCommunityMode,
        sm16tat2saSnmpSetCommunity,
        sm16tat2saSnmpVersion,

      --sm16tat2saSnmpCommunityTable
        sm16tat2saSnmpCommunityName,
        sm16tat2saSnmpCommunityIP,
        sm16tat2saSnmpCommunityMask,
        sm16tat2saSnmpCommunityRowStatus,

      --sm16tat2saTrapHostConfTable
        sm16tat2saTrapHostConfVersion,
        sm16tat2saTrapHostConfMode,
        sm16tat2saTrapHostConfIP,
        sm16tat2saTrapHostConfPort,
        sm16tat2saTrapHostConfCommunity,
        sm16tat2saTrapHostConfSeverityLevel,
        sm16tat2saTrapHostConfCurrentMode
    }
    STATUS current
    DESCRIPTION
        "The collection of objects which are used to
        indicate SNMP information."
    ::= { sm16tat2saSystemGroups 6 }

sm16tat2saPrivilegeLevelGroup OBJECT-GROUP
    OBJECTS {
    --sm16tat2saPrivilegeLevel
      --sm16tat2saPrivilegeLevelConfigTable
        sm16tat2saPrivilegeLevelGroupName,
        sm16tat2saPrivilegeLevelConfigReadOnly,
        sm16tat2saPrivilegeLevelConfigReadWrite
    }
    STATUS current
    DESCRIPTION
        "The collection of objects which are used to
        indicate privilege level information."
    ::= { sm16tat2saSystemGroups 7 }

sm16tat2saLldpConfigGroup OBJECT-GROUP
    OBJECTS {
    --sm16tat2saLldpConfig
      --sm16tat2saLldpConfigTable
        sm16tat2saLldpConfigCdpAware,

      --sm16tat2saLldpMedLocInfo
        sm16tat2saLldpMedLatitude,
        sm16tat2saLldpMedLatitudeDirection,
        sm16tat2saLldpMedLongitude,
        sm16tat2saLldpMedLongitudeDirection,
        sm16tat2saLldpMedAltitude,
        sm16tat2saLldpMedAltitudeType,
        sm16tat2saLldpMedDatum,
        sm16tat2saLldpMedElinAddr,
        sm16tat2saLldpMedCivicAddrLocInfoCountryCode,
        sm16tat2saLldpMedCivicAddrLocInfoState,
        sm16tat2saLldpMedCivicAddrLocInfoCounty,
        sm16tat2saLldpMedCivicAddrLocInfoCity,
        sm16tat2saLldpMedCivicAddrLocInfoDistrict,
        sm16tat2saLldpMedCivicAddrLocInfoBlock,
        sm16tat2saLldpMedCivicAddrLocInfoStreet,
        sm16tat2saLldpMedCivicAddrLocInfoLeadingStreetDirection,
        sm16tat2saLldpMedCivicAddrLocInfoTrailingStreetSuffix,
        sm16tat2saLldpMedCivicAddrLocInfoStreetSuffix,
        sm16tat2saLldpMedCivicAddrLocInfoHouseNo,
        sm16tat2saLldpMedCivicAddrLocInfoHouseNoSuffix,
        sm16tat2saLldpMedCivicAddrLocInfoLandmark,
        sm16tat2saLldpMedCivicAddrLocInfoAdditionalInfo,
        sm16tat2saLldpMedCivicAddrLocInfoName,
        sm16tat2saLldpMedCivicAddrLocInfoZipCode,
        sm16tat2saLldpMedCivicAddrLocInfoBuilding,
        sm16tat2saLldpMedCivicAddrLocInfoApartment,
        sm16tat2saLldpMedCivicAddrLocInfoFloor,
        sm16tat2saLldpMedCivicAddrLocInfoRoomNumber,
        sm16tat2saLldpMedCivicAddrLocInfoPlaceType,
        sm16tat2saLldpMedCivicAddrLocInfoPostalCommunityName,
        sm16tat2saLldpMedCivicAddrLocInfoPoBox,
        sm16tat2saLldpMedCivicAddrLocInfoAdditionalCode
    }
    STATUS current
    DESCRIPTION
        "The collection of objects which are used to
        indicate lldp config information."
    ::= { sm16tat2saSystemGroups 8 }

sm16tat2saVLANConfGroup OBJECT-GROUP
    OBJECTS {
    --sm16tat2saVLANConf
      --sm16tat2saVLAN
        sm16tat2saVlanExistingVLANs,
        sm16tat2saVlanEthertypeforCustomSPorts,

        -- sm16tat2saVlanTable
        sm16tat2saVlanMode,
        sm16tat2saVlanPortVLAN,
        sm16tat2saVlanPortType,
        sm16tat2saVlanIngressFiltering,
        sm16tat2saVlanIngressAcceptance,
        sm16tat2saVlanEgressTagging,
        sm16tat2saVlanAllowedVLANs,

      --sm16tat2saVlanStatus
        --sm16tat2saVLANPortStatusTable
        sm16tat2saVLANPortStatusPortType,
        sm16tat2saVLANPortStatusIngressFiltering,
        sm16tat2saVLANPortStatusFrameType,
        sm16tat2saVLANPortStatusPortVLANID,
        sm16tat2saVLANPortStatusTxTag,

      --sm16tat2saVclConfig
        --sm16tat2saVclConfigMac
          --sm16tat2saVclConfigMacBasedTable
        sm16tat2saVclConfigMacMacAddress,
        sm16tat2saVclConfigMacVlanId,
        sm16tat2saVclConfigMacRowStatus,
          --sm16tat2saVclConfigMacStatusTable
        sm16tat2saVclMacStatusMacAddress,
        sm16tat2saVclMacStatusVlanId,
        sm16tat2saVclMacStatusUser,

        --sm16tat2saVclConfigProtocol
          --sm16tat2saVclConfigProtocolProto
            --sm16tat2saVclConfigProtocolProtoTable
        sm16tat2saVclConfigProtocolProtoProtocolType,
        sm16tat2saVclConfigProtocolProtoProtocolValue,
        sm16tat2saVclConfigProtocolProtoProtocolGroupName,
        sm16tat2saVclConfigProtocolProtoRowStatus,
          --sm16tat2saVclConfigProtocolGroup
            --sm16tat2saVclConfigProtocolGroupTable
        sm16tat2saVclConfigProtocolGroupProtocolGroupName,
        sm16tat2saVclConfigProtocolGroupVlanId,
        sm16tat2saVclConfigProtocolGroupPortList,
        sm16tat2saVclConfigProtocolGroupRowStatus,

        --sm16tat2saVclConfigIpTable
        sm16tat2saVclConfigIpIpSubnetAddress,
        sm16tat2saVclConfigIpIpSubnetMaskLength,
        sm16tat2saVclConfigIpVlanId,
        sm16tat2saVclConfigIpRowStatus,

        --sm16tat2saVlanSelectiveQinQ
          --sm16tat2saVlanSelectiveTable
        sm16tat2saVlanSelectiveCVID,
        sm16tat2saVlanSelectiveSPID,
        sm16tat2saVlanSelectivePortList,
        sm16tat2saVlanSelectiveRowStatus,

        --sm16tat2saPvlanConfig
          --sm16tat2saPvlanConfigVlanMembershipTable
        sm16tat2saPvlanConfigVlanMembershipPvlanId,
        sm16tat2saPvlanConfigVlanMembershipPortList,
        sm16tat2saPvlanConfigVlanMembershipRowStatus,
          --sm16tat2saPvlanConfigPortIsolatationTable
        sm16tat2saPvlanConfigPortIsolatationEnabled,

        --sm16tat2saVoiceVlanConfig
          --sm16tat2saVoiceVlanGlobalConfig
            --sm16tat2saVoiceVlanConfigTable
        sm16tat2saVoiceVlanConfigGlobalsMgmtVlanId,
        sm16tat2saVoiceVlanConfigGlobalsMgmtAgingTime,
        sm16tat2saVoiceVlanConfigGlobalsMgmtTrafficClass,
        sm16tat2saVoiceVlanConfigGlobalsMgmtPortList,
        sm16tat2saVoiceVlanConfigGlobalsMgmtRowStatus,
          --sm16tat2saVoiceVlanConfigInterface
            --sm16tat2saVoiceVlanConfigInterfacePortTable
        sm16tat2saVoiceVlanConfigInterfacePortMode,
        sm16tat2saVoiceVlanConfigInterfacePortSecured,
        sm16tat2saVoiceVlanConfigInterfacePortDiscoveryProtocol,
          --sm16tat2saVoiceVlanConfigOui
            --sm16tat2saVoiceVlanConfigOuiTable
        sm16tat2saVoiceVlanConfigOuiPrefix,
        sm16tat2saVoiceVlanConfigOuiDescription,
        sm16tat2saVoiceVlanConfigOuiRowStatus
    }
    STATUS current
    DESCRIPTION
        "The collection of objects which are used to
        indicate vlan information."
    ::= { sm16tat2saSystemGroups 10 }

sm16tat2saUpnpConfigGroup OBJECT-GROUP
    OBJECTS {
    --sm16tat2saUpnpConfigGlobals
        sm16tat2saUpnpConfigGlobalsMode,
        sm16tat2saUpnpConfigGlobalsInterfaceVlan,
        sm16tat2saUpnpConfigGlobalsTtl,
        sm16tat2saUpnpConfigGlobalsAdvertisingDuration
    }
    STATUS current
    DESCRIPTION
        "The collection of objects which are used to
        indicate upnp config information."
    ::= { sm16tat2saSystemGroups 11 }

sm16tat2saSystemCompliance MODULE-COMPLIANCE
    STATUS current
    DESCRIPTION
        "The compliance statement for devices supporting system."
    MODULE
        MANDATORY-GROUPS {
            sm16tat2saSystemInformationGroup,
            sm16tat2saSystemTimeConfGroup,
            sm16tat2saSystemAccountGroup,
            sm16tat2saIPGroup,
            sm16tat2saSyslogGroup,
            sm16tat2saSnmpGroup,
            sm16tat2saPrivilegeLevelGroup,
            sm16tat2saLldpConfigGroup,
            sm16tat2saVLANConfGroup,
            sm16tat2saUpnpConfigGroup
        }
    ::= { sm16tat2saSystemCompliances 1 }

-- ================================================================================================================

sm16tat2saConfiguration OBJECT IDENTIFIER ::= { sm16tat2saProductId 2 }

-- *************************************************************
-- Start sm16tat2saPort group
-- *************************************************************
sm16tat2saPort OBJECT IDENTIFIER ::= { sm16tat2saConfiguration 1 }

sm16tat2saPortConfigurationTable OBJECT-TYPE
   SYNTAX SEQUENCE OF SM16TAT2SAPortConfigurationEntry
   MAX-ACCESS not-accessible
   STATUS current
   DESCRIPTION
       " Show port configurations. "
   ::= { sm16tat2saPort 1 }

sm16tat2saPortConfigurationEntry OBJECT-TYPE
   SYNTAX SM16TAT2SAPortConfigurationEntry
   MAX-ACCESS not-accessible
   STATUS current
   DESCRIPTION
       " "
   INDEX { sm16tat2saPortConfPort }
   ::= { sm16tat2saPortConfigurationTable 1 }

SM16TAT2SAPortConfigurationEntry ::= SEQUENCE {
   sm16tat2saPortConfPort Integer32,
   sm16tat2saPortConfPortMedia DisplayString,
   sm16tat2saPortConfLink DisplayString,
   sm16tat2saPortConfCurrentSpeed DisplayString,
   sm16tat2saPortConfSpeed INTEGER,
   sm16tat2saPortConfCurrentFlowControlRx INTEGER,
   sm16tat2saPortConfCurrentFlowControlTx INTEGER,
   sm16tat2saPortConfFlowControl INTEGER,
   sm16tat2saPortConfDescription DisplayString
}

sm16tat2saPortConfPort OBJECT-TYPE
   SYNTAX Integer32(1..4095)
   MAX-ACCESS not-accessible
   STATUS current
   DESCRIPTION
       " port, range : 1 - port number. "
   ::= { sm16tat2saPortConfigurationEntry 1 }

sm16tat2saPortConfPortMedia OBJECT-TYPE
   SYNTAX DisplayString(SIZE (1..6))
   MAX-ACCESS read-only
   STATUS current
   DESCRIPTION
       " Show port media. "
   ::= { sm16tat2saPortConfigurationEntry 2 }

sm16tat2saPortConfLink OBJECT-TYPE
   SYNTAX DisplayString(SIZE (2..4))
   MAX-ACCESS read-only
   STATUS current
   DESCRIPTION
       " The current link state. "
   ::= { sm16tat2saPortConfigurationEntry 3 }

sm16tat2saPortConfCurrentSpeed OBJECT-TYPE
   SYNTAX DisplayString(SIZE (6..12))
   MAX-ACCESS read-only
   STATUS current
   DESCRIPTION
       " The current link speed of the port. "
   ::= { sm16tat2saPortConfigurationEntry 4 }

sm16tat2saPortConfSpeed OBJECT-TYPE
   SYNTAX INTEGER {
                    disable(0),
                    auto(1),
                    speed10Half(2),
                    speed10Full(3),
                    speed100Half(4),
                    speed100Full(5),
                    speed1Gfull(6)
                }
   MAX-ACCESS read-write
   STATUS current
   DESCRIPTION
       "default: 1,
        0: disable state,
        1: auto,
        2: 10 Half,
        3: 10 Full,
        4: 100 Half,
        5: 100 Full,
        6: 1G full"
   ::= { sm16tat2saPortConfigurationEntry 5 }

sm16tat2saPortConfCurrentFlowControlRx OBJECT-TYPE
   SYNTAX INTEGER { disable(0), enable(1), noSupport(2) }
   MAX-ACCESS read-only
   STATUS current
   DESCRIPTION
       "0: disable
        1: enable
        2: no support. "
   ::= { sm16tat2saPortConfigurationEntry 6 }

sm16tat2saPortConfCurrentFlowControlTx OBJECT-TYPE
   SYNTAX INTEGER { disable(0), enable(1), noSupport(2) }
   MAX-ACCESS read-only
   STATUS current
   DESCRIPTION
       "0: disable
        1: enable
        2: no support. "
   ::= { sm16tat2saPortConfigurationEntry 7 }

sm16tat2saPortConfFlowControl OBJECT-TYPE
   SYNTAX INTEGER { disable(0), enable(1), noSupport(2) }
   MAX-ACCESS read-write
   STATUS current
   DESCRIPTION
       "default: 0,
        0: disable
        1: enable
        2: no support. (set:not include)"
   ::= { sm16tat2saPortConfigurationEntry 8 }

sm16tat2saPortConfDescription OBJECT-TYPE
   SYNTAX DisplayString
   MAX-ACCESS read-write
   STATUS current
   DESCRIPTION
       " Interface specific description.
         Up to 47 characters describing this interface. "
   ::= { sm16tat2saPortConfigurationEntry 9 }

sm16tat2saSFPInfoTable OBJECT-TYPE
   SYNTAX SEQUENCE OF SM16TAT2SASFPInfoEntry
   MAX-ACCESS not-accessible
   STATUS current
   DESCRIPTION
       " "
   ::= { sm16tat2saPort 4 }

sm16tat2saSFPInfoEntry OBJECT-TYPE
   SYNTAX SM16TAT2SASFPInfoEntry
   MAX-ACCESS not-accessible
   STATUS current
   DESCRIPTION
       " "
   INDEX { sm16tat2saSFPInfoIndex }
   ::= { sm16tat2saSFPInfoTable 1 }

SM16TAT2SASFPInfoEntry ::= SEQUENCE {
   sm16tat2saSFPInfoIndex Integer32,
   sm16tat2saSFPInfoPort DisplayString,
   sm16tat2saSFPConnectorType DisplayString,
   sm16tat2saSFPFiberType DisplayString,
   sm16tat2saSFPTxCentralWavelength DisplayString,
   sm16tat2saSFPBitRate DisplayString,
   sm16tat2saSFPVendorOUI DisplayString,
   sm16tat2saSFPVendorName DisplayString,
   sm16tat2saSFPVendorPN DisplayString,
   sm16tat2saSFPVendorRev DisplayString,
   sm16tat2saSFPVendorSN DisplayString,
   sm16tat2saSFPDateCode DisplayString,
   sm16tat2saSFPTemperature DisplayString,
   sm16tat2saSFPVcc DisplayString,
   sm16tat2saSFPMon1Bias DisplayString,
   sm16tat2saSFPMon2TxPWR DisplayString,
   sm16tat2saSFPMon3RxPWR DisplayString
}

sm16tat2saSFPInfoIndex OBJECT-TYPE
   SYNTAX Integer32(1..4095)
   MAX-ACCESS not-accessible
   STATUS current
   DESCRIPTION
       " "
   ::= { sm16tat2saSFPInfoEntry 1 }

sm16tat2saSFPInfoPort OBJECT-TYPE
   SYNTAX DisplayString
   MAX-ACCESS read-only
   STATUS current
   DESCRIPTION
       " "
   ::= { sm16tat2saSFPInfoEntry 2 }

sm16tat2saSFPConnectorType OBJECT-TYPE
   SYNTAX DisplayString
   MAX-ACCESS read-only
   STATUS current
   DESCRIPTION
       " "
   ::= { sm16tat2saSFPInfoEntry 3 }

sm16tat2saSFPFiberType OBJECT-TYPE
   SYNTAX DisplayString
   MAX-ACCESS read-only
   STATUS current
   DESCRIPTION
       " "
   ::= { sm16tat2saSFPInfoEntry 4 }

sm16tat2saSFPTxCentralWavelength OBJECT-TYPE
   SYNTAX DisplayString
   MAX-ACCESS read-only
   STATUS current
   DESCRIPTION
       " "
   ::= { sm16tat2saSFPInfoEntry 5 }

sm16tat2saSFPBitRate OBJECT-TYPE
   SYNTAX DisplayString
   MAX-ACCESS read-only
   STATUS current
   DESCRIPTION
       " "
   ::= { sm16tat2saSFPInfoEntry 6 }

sm16tat2saSFPVendorOUI OBJECT-TYPE
   SYNTAX DisplayString
   MAX-ACCESS read-only
   STATUS current
   DESCRIPTION
       " "
   ::= { sm16tat2saSFPInfoEntry 7 }

sm16tat2saSFPVendorName OBJECT-TYPE
   SYNTAX DisplayString
   MAX-ACCESS read-only
   STATUS current
   DESCRIPTION
       " "
   ::= { sm16tat2saSFPInfoEntry 8 }

sm16tat2saSFPVendorPN OBJECT-TYPE
   SYNTAX DisplayString
   MAX-ACCESS read-only
   STATUS current
   DESCRIPTION
       " "
   ::= { sm16tat2saSFPInfoEntry 9 }

sm16tat2saSFPVendorRev OBJECT-TYPE
   SYNTAX DisplayString
   MAX-ACCESS read-only
   STATUS current
   DESCRIPTION
       " "
   ::= { sm16tat2saSFPInfoEntry 10 }

sm16tat2saSFPVendorSN OBJECT-TYPE
   SYNTAX DisplayString
   MAX-ACCESS read-only
   STATUS current
   DESCRIPTION
       " "
   ::= { sm16tat2saSFPInfoEntry 11 }

sm16tat2saSFPDateCode OBJECT-TYPE
   SYNTAX DisplayString
   MAX-ACCESS read-only
   STATUS current
   DESCRIPTION
       " "
   ::= { sm16tat2saSFPInfoEntry 12 }

sm16tat2saSFPTemperature OBJECT-TYPE
   SYNTAX DisplayString
   MAX-ACCESS read-only
   STATUS current
   DESCRIPTION
       " "
   ::= { sm16tat2saSFPInfoEntry 13 }

sm16tat2saSFPVcc OBJECT-TYPE
   SYNTAX DisplayString
   MAX-ACCESS read-only
   STATUS current
   DESCRIPTION
       " "
   ::= { sm16tat2saSFPInfoEntry 14 }

sm16tat2saSFPMon1Bias OBJECT-TYPE
   SYNTAX DisplayString
   MAX-ACCESS read-only
   STATUS current
   DESCRIPTION
       " "
   ::= { sm16tat2saSFPInfoEntry 15 }

sm16tat2saSFPMon2TxPWR OBJECT-TYPE
   SYNTAX DisplayString
   MAX-ACCESS read-only
   STATUS current
   DESCRIPTION
       " "
   ::= { sm16tat2saSFPInfoEntry 16 }

sm16tat2saSFPMon3RxPWR OBJECT-TYPE
   SYNTAX DisplayString
   MAX-ACCESS read-only
   STATUS current
   DESCRIPTION
       " "
   ::= { sm16tat2saSFPInfoEntry 17 }

sm16tat2saPortEnergyEfficientTable OBJECT-TYPE
   SYNTAX SEQUENCE OF SM16TAT2SAPortEnergyEfficientEntry
   MAX-ACCESS not-accessible
   STATUS current
   DESCRIPTION
       " "
   ::= { sm16tat2saPort 5 }

sm16tat2saPortEnergyEfficientEntry OBJECT-TYPE
   SYNTAX SM16TAT2SAPortEnergyEfficientEntry
   MAX-ACCESS not-accessible
   STATUS current
   DESCRIPTION
       " "
   INDEX { sm16tat2saPortEnergyEfficientPort }
   ::= { sm16tat2saPortEnergyEfficientTable 1 }

SM16TAT2SAPortEnergyEfficientEntry ::= SEQUENCE {
   sm16tat2saPortEnergyEfficientPort Integer32,
   sm16tat2saPortEnergyEfficientMode INTEGER
}

sm16tat2saPortEnergyEfficientPort OBJECT-TYPE
   SYNTAX Integer32 (1..4095)
   MAX-ACCESS not-accessible
   STATUS current
   DESCRIPTION
       " "
   ::= { sm16tat2saPortEnergyEfficientEntry 1 }

sm16tat2saPortEnergyEfficientMode OBJECT-TYPE
   SYNTAX INTEGER { disable(0), enable(1) }
   MAX-ACCESS read-write
   STATUS current
   DESCRIPTION
       "default: 0
       0: disable
       1: enable"
   ::= { sm16tat2saPortEnergyEfficientEntry 2 }

sm16tat2saPortGlobalConfig
                                                      OBJECT IDENTIFIER ::= { sm16tat2saPort 6 }
sm16tat2saPortMaximumFrameSize OBJECT-TYPE
   SYNTAX Integer32 (1518..10000)
   MAX-ACCESS read-write
   STATUS current
   DESCRIPTION
       "Maximum packet length filtering is examined on both receiving and transmitting ports."
   ::= { sm16tat2saPortGlobalConfig 1 }

-- *************************************************************
-- Start sm16tat2saEventConfig group
-- *************************************************************
sm16tat2saEventConfig OBJECT IDENTIFIER ::= { sm16tat2saConfiguration 7 }

sm16tat2saEventConfigTable OBJECT-TYPE
   SYNTAX SEQUENCE OF SM16TAT2SAEventConfigEntry
   MAX-ACCESS not-accessible
   STATUS current
   DESCRIPTION
       "A list of event configuration entry."
   ::= { sm16tat2saEventConfig 1 }

sm16tat2saEventConfigEntry OBJECT-TYPE
   SYNTAX SM16TAT2SAEventConfigEntry
   MAX-ACCESS not-accessible
   STATUS current
   DESCRIPTION
       "This is the entry information for event configuration."
   INDEX { sm16tat2saEventConfigIndex }
   ::= { sm16tat2saEventConfigTable 1 }

SM16TAT2SAEventConfigEntry ::= SEQUENCE {
    sm16tat2saEventConfigIndex Integer32,
    sm16tat2saEventConfigGroupName DisplayString,
    sm16tat2saEventConfigSeverityLevel SeverityLevel,
    sm16tat2saEventConfigSyslog AdminMode,
    sm16tat2saEventConfigTrap AdminMode,
    sm16tat2saEventConfigSMTP AdminMode
}

sm16tat2saEventConfigIndex OBJECT-TYPE
   SYNTAX Integer32 (1..1024)
   MAX-ACCESS not-accessible
   STATUS current
   DESCRIPTION
       " The index of the event configuration group name entry. "
   ::= { sm16tat2saEventConfigEntry 1 }

sm16tat2saEventConfigGroupName OBJECT-TYPE
   SYNTAX DisplayString
   MAX-ACCESS read-only
   STATUS current
   DESCRIPTION
       "The name identifying the severity group. "
   ::= { sm16tat2saEventConfigEntry 2 }

sm16tat2saEventConfigSeverityLevel OBJECT-TYPE
   SYNTAX SeverityLevel
   MAX-ACCESS read-write
   STATUS current
   DESCRIPTION
       "The severity level. "
   ::= { sm16tat2saEventConfigEntry 3 }

sm16tat2saEventConfigSyslog OBJECT-TYPE
   SYNTAX AdminMode
   MAX-ACCESS read-write
   STATUS current
   DESCRIPTION
       "Enable - Select this Group Name in Syslog. "
   ::= { sm16tat2saEventConfigEntry 4 }

sm16tat2saEventConfigTrap OBJECT-TYPE
   SYNTAX AdminMode
   MAX-ACCESS read-write
   STATUS current
   DESCRIPTION
       "Enable - Select this Group Name in Trap. "
   ::= { sm16tat2saEventConfigEntry 5 }

sm16tat2saEventConfigSMTP OBJECT-TYPE
   SYNTAX AdminMode
   MAX-ACCESS read-write
   STATUS current
   DESCRIPTION
       "Enable - Select this Group Name in SMTP. "
   ::= { sm16tat2saEventConfigEntry 6 }

-- *************************************************************
-- Start sm16tat2saSMTP group
-- *************************************************************
sm16tat2saSMTP OBJECT IDENTIFIER ::= { sm16tat2saConfiguration 8 }

sm16tat2saSMTPMailServer OBJECT-TYPE
   SYNTAX DisplayString
   MAX-ACCESS read-write
   STATUS current
   DESCRIPTION
       " Up to 48 characters describing email server. "
   ::= { sm16tat2saSMTP 1 }

sm16tat2saSMTPUserName OBJECT-TYPE
   SYNTAX DisplayString
   MAX-ACCESS read-write
   STATUS current
   DESCRIPTION
       " Up to 32 characters describing user name. "
   ::= { sm16tat2saSMTP 2 }

sm16tat2saSMTPPassword OBJECT-TYPE
   SYNTAX DisplayString
   MAX-ACCESS read-write
   STATUS current
   DESCRIPTION
       " Up to 32 characters describing password. "
   ::= { sm16tat2saSMTP 3 }

sm16tat2saSMTPSender OBJECT-TYPE
   SYNTAX DisplayString
   MAX-ACCESS read-write
   STATUS current
   DESCRIPTION
       " Up to 48 characters describing sender. "
   ::= { sm16tat2saSMTP 5 }

sm16tat2saSMTPReturnPath OBJECT-TYPE
   SYNTAX DisplayString
   MAX-ACCESS read-write
   STATUS current
   DESCRIPTION
       " Up to 48 characters describing return path. "
   ::= { sm16tat2saSMTP 6 }

sm16tat2saSMTPEmailAddress1 OBJECT-TYPE
   SYNTAX DisplayString
   MAX-ACCESS read-write
   STATUS current
   DESCRIPTION
       " Up to 48 characters describing mail address. "
   ::= { sm16tat2saSMTP 7 }

sm16tat2saSMTPEmailAddress2 OBJECT-TYPE
   SYNTAX DisplayString
   MAX-ACCESS read-write
   STATUS current
   DESCRIPTION
       " Up to 48 characters describing mail address. "
   ::= { sm16tat2saSMTP 8 }

sm16tat2saSMTPEmailAddress3 OBJECT-TYPE
   SYNTAX DisplayString
   MAX-ACCESS read-write
   STATUS current
   DESCRIPTION
       " Up to 48 characters describing mail address. "
   ::= { sm16tat2saSMTP 9 }

sm16tat2saSMTPEmailAddress4 OBJECT-TYPE
   SYNTAX DisplayString
   MAX-ACCESS read-write
   STATUS current
   DESCRIPTION
       " Up to 48 characters describing mail address. "
   ::= { sm16tat2saSMTP 10 }

sm16tat2saSMTPEmailAddress5 OBJECT-TYPE
   SYNTAX DisplayString
   MAX-ACCESS read-write
   STATUS current
   DESCRIPTION
       " Up to 48 characters describing mail address. "
   ::= { sm16tat2saSMTP 11 }

sm16tat2saSMTPEmailAddress6 OBJECT-TYPE
   SYNTAX DisplayString
   MAX-ACCESS read-write
   STATUS current
   DESCRIPTION
       " Up to 48 characters describing mail address. "
   ::= { sm16tat2saSMTP 12 }

-- *************************************************************
-- Start sm16tat2saQosConf group
-- *************************************************************
sm16tat2saQosConf OBJECT IDENTIFIER ::= { sm16tat2saConfiguration 10 }

sm16tat2saQosGobalSettings OBJECT IDENTIFIER ::= { sm16tat2saQosConf 1 }
sm16tat2saQosPortSettings OBJECT IDENTIFIER ::= { sm16tat2saQosConf 2 }
sm16tat2saQosPortPolicing OBJECT IDENTIFIER ::= { sm16tat2saQosConf 3 }
sm16tat2saQosPortShaper OBJECT IDENTIFIER ::= { sm16tat2saQosConf 4 }
sm16tat2saQosStormControl OBJECT IDENTIFIER ::= { sm16tat2saQosConf 5 }
sm16tat2saQosPortScheduler OBJECT IDENTIFIER ::= { sm16tat2saQosConf 6 }
sm16tat2saQosCoS8021pMapping OBJECT IDENTIFIER ::= { sm16tat2saQosConf 7 }
sm16tat2saQosCoS8021pRemarking OBJECT IDENTIFIER ::= { sm16tat2saQosConf 8 }
sm16tat2saQosIPPrecedenceMapping OBJECT IDENTIFIER ::= { sm16tat2saQosConf 9 }
sm16tat2saQosIPPrecedenceRemarking OBJECT IDENTIFIER ::= { sm16tat2saQosConf 10 }
sm16tat2saQosDSCPMapping OBJECT IDENTIFIER ::= { sm16tat2saQosConf 11 }
sm16tat2saQosDSCPRemarking OBJECT IDENTIFIER ::= { sm16tat2saQosConf 12 }

sm16tat2saQosGobalSettingsTrustMode OBJECT-TYPE
    SYNTAX INTEGER { cos8021p(0), dscp(1), ipPrecedence(2), cos8021pdscp(3) }
    MAX-ACCESS read-write
    STATUS current
    DESCRIPTION
        "0: Cos/802.1p,
         1: DSCP,
         2: IP Precedence,
         3: Cos/802.1p-DSCP."
    ::= { sm16tat2saQosGobalSettings 1 }

sm16tat2saQosPortSettingsTable OBJECT-TYPE
    SYNTAX SEQUENCE OF SM16TAT2SAQosPortSettingsEntry
    MAX-ACCESS not-accessible
    STATUS current
    DESCRIPTION
        "The Port Settings."
    ::= { sm16tat2saQosPortSettings 1 }

sm16tat2saQosPortSettingsEntry OBJECT-TYPE
    SYNTAX SM16TAT2SAQosPortSettingsEntry
    MAX-ACCESS not-accessible
    STATUS current
    DESCRIPTION
         "The Port Settings Entry."
    INDEX { ifIndex }
    ::= { sm16tat2saQosPortSettingsTable 1 }

SM16TAT2SAQosPortSettingsEntry ::=
    SEQUENCE {
        sm16tat2saQosPortSettingsMode INTEGER,
        sm16tat2saQosPortSettingsDefaultCoS Integer32,
        sm16tat2saQosPortSettingsSourceCoS INTEGER,
        sm16tat2saQosPortSettingsRemarkCoS AdminMode,
        sm16tat2saQosPortSettingsRemarkDSCP AdminMode,
        sm16tat2saQosPortSettingsRemarkIPPrecedence AdminMode
    }

sm16tat2saQosPortSettingsMode OBJECT-TYPE
    SYNTAX INTEGER { untrust(0), trust(1) }
    MAX-ACCESS read-write
    STATUS current
    DESCRIPTION
        "0: untrust,
         1: trust."
    ::= { sm16tat2saQosPortSettingsEntry 1 }

sm16tat2saQosPortSettingsDefaultCoS OBJECT-TYPE
    SYNTAX Integer32(0..7)
    MAX-ACCESS read-write
    STATUS current
    DESCRIPTION
        "range: 0~7,
         default: 0."
    ::= { sm16tat2saQosPortSettingsEntry 2 }

sm16tat2saQosPortSettingsSourceCoS OBJECT-TYPE
    SYNTAX INTEGER { cTag(0), sTag(1) }
    MAX-ACCESS read-write
    STATUS current
    DESCRIPTION
        "0: cTag,
         1: sTag."
    ::= { sm16tat2saQosPortSettingsEntry 3 }

sm16tat2saQosPortSettingsRemarkCoS OBJECT-TYPE
    SYNTAX AdminMode
    MAX-ACCESS read-write
    STATUS current
    DESCRIPTION
        "Controls whether the remark CoS is enabled on this switch port settings."
    DEFVAL { disable }
    ::= { sm16tat2saQosPortSettingsEntry 4 }

sm16tat2saQosPortSettingsRemarkDSCP OBJECT-TYPE
    SYNTAX AdminMode
    MAX-ACCESS read-write
    STATUS current
    DESCRIPTION
        "Controls whether the remark DSCP is enabled on this switch port settings."
    DEFVAL { disable }
    ::= { sm16tat2saQosPortSettingsEntry 5 }

sm16tat2saQosPortSettingsRemarkIPPrecedence OBJECT-TYPE
    SYNTAX AdminMode
    MAX-ACCESS read-write
    STATUS current
    DESCRIPTION
        "Controls whether the remark IP precedence is enabled on this switch port settings."
    DEFVAL { disable }
    ::= { sm16tat2saQosPortSettingsEntry 6 }

sm16tat2saQosPortPolicingTable OBJECT-TYPE
    SYNTAX SEQUENCE OF SM16TAT2SAQosPortPolicingEntry
    MAX-ACCESS not-accessible
    STATUS current
    DESCRIPTION
        "The Policer settings.
         INDEX for this table is ifIndex which is
         equivalent to the panel port number."
    ::= { sm16tat2saQosPortPolicing 1 }

sm16tat2saQosPortPolicingEntry OBJECT-TYPE
    SYNTAX SM16TAT2SAQosPortPolicingEntry
    MAX-ACCESS not-accessible
    STATUS current
    DESCRIPTION
         "The Policer setting entry."
    INDEX { ifIndex }
    ::= { sm16tat2saQosPortPolicingTable 1 }

SM16TAT2SAQosPortPolicingEntry ::=
    SEQUENCE {
        sm16tat2saQosPortPolicingEnabled AdminMode,
        sm16tat2saQosPortPolicingRate Integer32
    }

sm16tat2saQosPortPolicingEnabled OBJECT-TYPE
    SYNTAX AdminMode
    MAX-ACCESS read-write
    STATUS current
    DESCRIPTION
        "Controls whether the policer is enabled on this switch port."
    DEFVAL { disable }
    ::= { sm16tat2saQosPortPolicingEntry 1 }

sm16tat2saQosPortPolicingRate OBJECT-TYPE
    SYNTAX Integer32(100..10000000)
    MAX-ACCESS read-write
    STATUS current
    DESCRIPTION
        "Controls the rate for the policer.
         range: 100-10000000(kbps/fps),
         default: 10000000(kbps)."
    ::= { sm16tat2saQosPortPolicingEntry 2 }

sm16tat2saQosQueueShaperTable OBJECT-TYPE
    SYNTAX SEQUENCE OF SM16TAT2SAQosQueueShaperEntry
    MAX-ACCESS not-accessible
    STATUS current
    DESCRIPTION
        "The table of QoS Queue Shaper"
    ::= { sm16tat2saQosPortShaper 1 }

sm16tat2saQosQueueShaperEntry OBJECT-TYPE
    SYNTAX SM16TAT2SAQosQueueShaperEntry
    MAX-ACCESS not-accessible
    STATUS current
    DESCRIPTION
        "The entry of QoS Queue Shaper"
    INDEX { ifIndex, sm16tat2saQosQueueShaperQueue }
    ::= { sm16tat2saQosQueueShaperTable 1 }

SM16TAT2SAQosQueueShaperEntry ::=
    SEQUENCE {
        sm16tat2saQosQueueShaperQueue Integer32,
        sm16tat2saQosQueueShaperEnabled AdminMode,
        sm16tat2saQosQueueShaperRate Integer32
    }

sm16tat2saQosQueueShaperQueue OBJECT-TYPE
    SYNTAX Integer32 (1..8)
    MAX-ACCESS not-accessible
    STATUS current
    DESCRIPTION
         "The index of QoS Queue Shaper"
    ::= { sm16tat2saQosQueueShaperEntry 1 }

sm16tat2saQosQueueShaperEnabled OBJECT-TYPE
    SYNTAX AdminMode
    MAX-ACCESS read-write
    STATUS current
    DESCRIPTION
        "Control whether QoS Queue Shaper is enabled."
    DEFVAL { disable }
    ::= { sm16tat2saQosQueueShaperEntry 2 }

sm16tat2saQosQueueShaperRate OBJECT-TYPE
    SYNTAX Integer32 (64..10000000)
    MAX-ACCESS read-write
    STATUS current
    DESCRIPTION
         " The rate of QoS Queue Shaper"
    ::= { sm16tat2saQosQueueShaperEntry 3 }

sm16tat2saQosPortShaperTable OBJECT-TYPE
    SYNTAX SEQUENCE OF SM16TAT2SAQosPortShaperEntry
    MAX-ACCESS not-accessible
    STATUS current
    DESCRIPTION
        "The table of QoS Port Shaper."
    ::= { sm16tat2saQosPortShaper 2 }

sm16tat2saQosPortShaperEntry OBJECT-TYPE
    SYNTAX SM16TAT2SAQosPortShaperEntry
    MAX-ACCESS not-accessible
    STATUS current
    DESCRIPTION
        "The entry of QoS Port Shaper"
    INDEX { ifIndex }
    ::= { sm16tat2saQosPortShaperTable 1 }

SM16TAT2SAQosPortShaperEntry ::=
    SEQUENCE {
        sm16tat2saQosPortShaperEnabled AdminMode,
        sm16tat2saQosPortShaperRate Integer32
    }

sm16tat2saQosPortShaperEnabled OBJECT-TYPE
    SYNTAX AdminMode
    MAX-ACCESS read-write
    STATUS current
    DESCRIPTION
        "Control whether QoS Port Shaper is enable."
    DEFVAL { disable }
    ::= { sm16tat2saQosPortShaperEntry 1 }

sm16tat2saQosPortShaperRate OBJECT-TYPE
    SYNTAX Integer32 (64..10000000)
    MAX-ACCESS read-write
    STATUS current
    DESCRIPTION
         "The rate of QoS Port Shaper"
    ::= { sm16tat2saQosPortShaperEntry 2 }

sm16tat2saQosStormControlTable OBJECT-TYPE
    SYNTAX SEQUENCE OF SM16TAT2SAQosStormControlEntry
    MAX-ACCESS not-accessible
    STATUS current
    DESCRIPTION
        "The basic QoS DSCP Translation settings for all switches."
    ::= { sm16tat2saQosStormControl 1 }

sm16tat2saQosStormControlEntry OBJECT-TYPE
    SYNTAX SM16TAT2SAQosStormControlEntry
    MAX-ACCESS not-accessible
    STATUS current
    DESCRIPTION
        "The Qos Storm Control Entry."
    INDEX { ifIndex }
    ::= { sm16tat2saQosStormControlTable 1 }

SM16TAT2SAQosStormControlEntry ::=
    SEQUENCE {
        sm16tat2saQosStormControlBroadcastEnabled AdminMode,
        sm16tat2saQosStormControlBraoadcastRate Integer32,
        sm16tat2saQosStormControlUnknownMulticastEnabled AdminMode,
        sm16tat2saQosStormControlUnknownMulticastRate Integer32,
        sm16tat2saQosStormControlUnknownUnicastEnabled AdminMode,
        sm16tat2saQosStormControlUnknownUnicastRate Integer32
    }

sm16tat2saQosStormControlBroadcastEnabled OBJECT-TYPE
    SYNTAX AdminMode
    MAX-ACCESS read-write
    STATUS current
    DESCRIPTION
        "Enable or disable the storm control status for the given frame type."
    DEFVAL { disable }
    ::= { sm16tat2saQosStormControlEntry 1 }

sm16tat2saQosStormControlBraoadcastRate OBJECT-TYPE
    SYNTAX Integer32
    MAX-ACCESS read-write
    STATUS current
    DESCRIPTION
        "The rate unit is packets per second (pps).
         default: 500(pps)."
    ::= { sm16tat2saQosStormControlEntry 2 }

sm16tat2saQosStormControlUnknownMulticastEnabled OBJECT-TYPE
    SYNTAX AdminMode
    MAX-ACCESS read-write
    STATUS current
    DESCRIPTION
        "Enable or disable the storm control status for the given frame type."
    DEFVAL { disable }
    ::= { sm16tat2saQosStormControlEntry 3 }

sm16tat2saQosStormControlUnknownMulticastRate OBJECT-TYPE
    SYNTAX Integer32
    MAX-ACCESS read-write
    STATUS current
    DESCRIPTION
        "The rate unit is packets per second (pps).
         default: 500(pps)."
    ::= { sm16tat2saQosStormControlEntry 4 }

sm16tat2saQosStormControlUnknownUnicastEnabled OBJECT-TYPE
    SYNTAX AdminMode
    MAX-ACCESS read-write
    STATUS current
    DESCRIPTION
        "Enable or disable the storm control status for the given frame type."
    DEFVAL { disable }
    ::= { sm16tat2saQosStormControlEntry 5 }

sm16tat2saQosStormControlUnknownUnicastRate OBJECT-TYPE
    SYNTAX Integer32
    MAX-ACCESS read-write
    STATUS current
    DESCRIPTION
        "The rate unit is packets per second (pps).
         default: 500(pps)."
    ::= { sm16tat2saQosStormControlEntry 6 }

sm16tat2saQosPortSchedulerTable OBJECT-TYPE
    SYNTAX SEQUENCE OF SM16TAT2SAQosPortSchedulerEntry
    MAX-ACCESS not-accessible
    STATUS current
    DESCRIPTION
        "The basic QoS Port Scheduler Mode settings.
         INDEX for this table is ifIndex which is
         equivalent to the panel port number."
    ::= { sm16tat2saQosPortScheduler 1 }

sm16tat2saQosPortSchedulerEntry OBJECT-TYPE
    SYNTAX SM16TAT2SAQosPortSchedulerEntry
    MAX-ACCESS not-accessible
    STATUS current
    DESCRIPTION
        "The Qos Port Scheduler Mode entry."
    INDEX { ifIndex, sm16tat2saQosSchedulerWeightIndex }
    ::= { sm16tat2saQosPortSchedulerTable 1 }

SM16TAT2SAQosPortSchedulerEntry ::=
    SEQUENCE {
        sm16tat2saQosSchedulerMode INTEGER,
        sm16tat2saQosSchedulerWeightIndex Integer32,
        sm16tat2saQosSchedulerWeight Integer32
    }

sm16tat2saQosSchedulerMode OBJECT-TYPE
    SYNTAX INTEGER { strictPriority(0), wrr(1), wfq(2) }
    MAX-ACCESS read-write
    STATUS current
    DESCRIPTION
        "Controls whether the scheduler mode is Strict Priority or Weighted on this switch port.
          0: Strict Priority,
          1: WRR,
          2: WFQ."
    DEFVAL { strictPriority }
    ::= { sm16tat2saQosPortSchedulerEntry 1 }

sm16tat2saQosSchedulerWeightIndex OBJECT-TYPE
     SYNTAX Integer32 (1..8)
     MAX-ACCESS not-accessible
     STATUS current
     DESCRIPTION
         "The index of Qos Scheduler Weight"
     ::= { sm16tat2saQosPortSchedulerEntry 2 }

sm16tat2saQosSchedulerWeight OBJECT-TYPE
     SYNTAX Integer32 (1..100)
     MAX-ACCESS read-write
     STATUS current
     DESCRIPTION
         "The weight of Qos Scheduler"
     ::= { sm16tat2saQosPortSchedulerEntry 3 }

sm16tat2saQosCoS8021pMappingTable OBJECT-TYPE
    SYNTAX SEQUENCE OF SM16TAT2SAQosCoS8021pMappingEntry
    MAX-ACCESS not-accessible
    STATUS current
    DESCRIPTION
        "The basic Qos CoS802.1p  Mapping settings for all switches."
    ::= { sm16tat2saQosCoS8021pMapping 1 }

sm16tat2saQosCoS8021pMappingEntry OBJECT-TYPE
    SYNTAX SM16TAT2SAQosCoS8021pMappingEntry
    MAX-ACCESS not-accessible
    STATUS current
    DESCRIPTION
        "The Qos CoS802.1p Mapping Entry."
    INDEX { sm16tat2saQosCoS8021pMappingCoS8021p }
    ::= { sm16tat2saQosCoS8021pMappingTable 1 }

SM16TAT2SAQosCoS8021pMappingEntry ::=
    SEQUENCE {
        sm16tat2saQosCoS8021pMappingCoS8021p Integer32,
        sm16tat2saQosCoS8021pMappingQueueID Integer32
    }

sm16tat2saQosCoS8021pMappingCoS8021p OBJECT-TYPE
    SYNTAX Integer32 (1..8)
    MAX-ACCESS not-accessible
    STATUS current
    DESCRIPTION
         "The index of QoS CoS802.1p Mapping"
    ::= { sm16tat2saQosCoS8021pMappingEntry 1 }

sm16tat2saQosCoS8021pMappingQueueID OBJECT-TYPE
    SYNTAX Integer32 (0..7)
    MAX-ACCESS read-write
    STATUS current
    DESCRIPTION
         "Queue ID of QoS CoS802.1p Mapping"
    ::= { sm16tat2saQosCoS8021pMappingEntry 2 }

sm16tat2saQosCoS8021pRemarkingTable OBJECT-TYPE
    SYNTAX SEQUENCE OF SM16TAT2SAQosCoS8021pRemarkingEntry
    MAX-ACCESS not-accessible
    STATUS current
    DESCRIPTION
        "The basic Qos CoS802.1p  Remarking settings for all switches."
    ::= { sm16tat2saQosCoS8021pRemarking 1 }

sm16tat2saQosCoS8021pRemarkingEntry OBJECT-TYPE
    SYNTAX SM16TAT2SAQosCoS8021pRemarkingEntry
    MAX-ACCESS not-accessible
    STATUS current
    DESCRIPTION
        "The Qos CoS802.1p Remarking Entry."
    INDEX { sm16tat2saQosCoS8021pRemarkingQueueID }
    ::= { sm16tat2saQosCoS8021pRemarkingTable 1 }

SM16TAT2SAQosCoS8021pRemarkingEntry ::=
    SEQUENCE {
        sm16tat2saQosCoS8021pRemarkingQueueID Integer32,
        sm16tat2saQosCoS8021pRemarkingCoS8021p Integer32
    }

sm16tat2saQosCoS8021pRemarkingQueueID OBJECT-TYPE
    SYNTAX Integer32 (1..8)
    MAX-ACCESS not-accessible
    STATUS current
    DESCRIPTION
         "The index of QoS CoS802.1p Remarking"
    ::= { sm16tat2saQosCoS8021pRemarkingEntry 1 }

sm16tat2saQosCoS8021pRemarkingCoS8021p OBJECT-TYPE
    SYNTAX Integer32(0..7)
    MAX-ACCESS read-write
    STATUS current
    DESCRIPTION
         "CoS802.1p of QoS CoS802.1p Remarking"
    ::= { sm16tat2saQosCoS8021pRemarkingEntry 2 }

sm16tat2saQosIPPrecedenceMappingTable OBJECT-TYPE
    SYNTAX SEQUENCE OF SM16TAT2SAQosIPPrecedenceMappingEntry
    MAX-ACCESS not-accessible
    STATUS current
    DESCRIPTION
        "The basic QoS IP Precedence Mapping settings for all switches."
    ::= { sm16tat2saQosIPPrecedenceMapping 1 }

sm16tat2saQosIPPrecedenceMappingEntry OBJECT-TYPE
    SYNTAX SM16TAT2SAQosIPPrecedenceMappingEntry
    MAX-ACCESS not-accessible
    STATUS current
    DESCRIPTION
        "The Qos IP Precedence Mapping Entry."
    INDEX { sm16tat2saQosIPPrecedenceMappingIPPrecedence }
    ::= { sm16tat2saQosIPPrecedenceMappingTable 1 }

SM16TAT2SAQosIPPrecedenceMappingEntry ::=
    SEQUENCE {
        sm16tat2saQosIPPrecedenceMappingIPPrecedence Integer32,
        sm16tat2saQosIPPrecedenceMappingQueueID Integer32
    }

sm16tat2saQosIPPrecedenceMappingIPPrecedence OBJECT-TYPE
    SYNTAX Integer32 (1..8)
    MAX-ACCESS not-accessible
    STATUS current
    DESCRIPTION
         "The index of QoS IP Precedence"
    ::= { sm16tat2saQosIPPrecedenceMappingEntry 1 }

sm16tat2saQosIPPrecedenceMappingQueueID OBJECT-TYPE
    SYNTAX Integer32 (0..7)
    MAX-ACCESS read-write
    STATUS current
    DESCRIPTION
         "Queue ID of QoS IP Precedence"
    ::= { sm16tat2saQosIPPrecedenceMappingEntry 2 }

sm16tat2saQosIPPrecedenceRemarkingTable OBJECT-TYPE
    SYNTAX SEQUENCE OF SM16TAT2SAQosIPPrecedenceRemarkingEntry
    MAX-ACCESS not-accessible
    STATUS current
    DESCRIPTION
        "The basic QoS IP Precedence Remarking settings for all switches."
    ::= { sm16tat2saQosIPPrecedenceRemarking 1 }

sm16tat2saQosIPPrecedenceRemarkingEntry OBJECT-TYPE
    SYNTAX SM16TAT2SAQosIPPrecedenceRemarkingEntry
    MAX-ACCESS not-accessible
    STATUS current
    DESCRIPTION
        "The Qos IP Precedence Remarking Entry."
    INDEX { sm16tat2saQosIPPrecedenceRemarkingQueueID }
    ::= { sm16tat2saQosIPPrecedenceRemarkingTable 1 }

SM16TAT2SAQosIPPrecedenceRemarkingEntry ::=
    SEQUENCE {
        sm16tat2saQosIPPrecedenceRemarkingQueueID Integer32,
        sm16tat2saQosIPPrecedenceRemarkingIPPrecedence Integer32
    }

sm16tat2saQosIPPrecedenceRemarkingQueueID OBJECT-TYPE
    SYNTAX Integer32 (1..8)
    MAX-ACCESS not-accessible
    STATUS current
    DESCRIPTION
         "The index of QoS IP Predence Remarking"
    ::= { sm16tat2saQosIPPrecedenceRemarkingEntry 1 }

sm16tat2saQosIPPrecedenceRemarkingIPPrecedence OBJECT-TYPE
    SYNTAX Integer32 (0..7)
    MAX-ACCESS read-write
    STATUS current
    DESCRIPTION
         "IP Precedence of QoS IP Precedence Remarking"
    ::= { sm16tat2saQosIPPrecedenceRemarkingEntry 2 }

sm16tat2saQosDSCPMappingTable OBJECT-TYPE
    SYNTAX SEQUENCE OF SM16TAT2SAQosDSCPMappingEntry
    MAX-ACCESS not-accessible
    STATUS current
    DESCRIPTION
        "The basic QoS DSCP Mapping settings for all switches."
    ::= { sm16tat2saQosDSCPMapping 1 }

sm16tat2saQosDSCPMappingEntry OBJECT-TYPE
    SYNTAX SM16TAT2SAQosDSCPMappingEntry
    MAX-ACCESS not-accessible
    STATUS current
    DESCRIPTION
        "The Qos DSCP Mapping Entry."
    INDEX { sm16tat2saQosDSCPMappingDSCPBasedId }
    ::= { sm16tat2saQosDSCPMappingTable 1 }

SM16TAT2SAQosDSCPMappingEntry ::=
    SEQUENCE {
        sm16tat2saQosDSCPMappingDSCPBasedId Integer32,
        sm16tat2saQosDSCPMappingQueueID Integer32
    }

sm16tat2saQosDSCPMappingDSCPBasedId OBJECT-TYPE
    SYNTAX Integer32 (1..64)
    MAX-ACCESS not-accessible
    STATUS current
    DESCRIPTION
         "The index of QoS DSCP Mapping"
    ::= { sm16tat2saQosDSCPMappingEntry 1 }

sm16tat2saQosDSCPMappingQueueID OBJECT-TYPE
    SYNTAX Integer32 (0..7)
    MAX-ACCESS read-write
    STATUS current
    DESCRIPTION
        "Queue ID of QoS DSCP Mapping"
    ::= { sm16tat2saQosDSCPMappingEntry 2 }

sm16tat2saQosDSCPRemarkingTable OBJECT-TYPE
    SYNTAX SEQUENCE OF SM16TAT2SAQosDSCPRemarkingEntry
    MAX-ACCESS not-accessible
    STATUS current
    DESCRIPTION
        "The basic QoS DSCP Remarking settings for all switches."
    ::= { sm16tat2saQosDSCPRemarking 1 }

sm16tat2saQosDSCPRemarkingEntry OBJECT-TYPE
    SYNTAX SM16TAT2SAQosDSCPRemarkingEntry
    MAX-ACCESS not-accessible
    STATUS current
    DESCRIPTION
        "The Qos DSCP Remarking Entry."
    INDEX { sm16tat2saQosDSCPRemarkingQueueID }
    ::= { sm16tat2saQosDSCPRemarkingTable 1 }

SM16TAT2SAQosDSCPRemarkingEntry ::=
    SEQUENCE {
        sm16tat2saQosDSCPRemarkingQueueID Integer32,
        sm16tat2saQosDSCPRemarkingDSCP Integer32
    }

sm16tat2saQosDSCPRemarkingQueueID OBJECT-TYPE
    SYNTAX Integer32 (1..8)
    MAX-ACCESS not-accessible
    STATUS current
    DESCRIPTION
         "The index of QoS DSCP Remarking"
    ::= { sm16tat2saQosDSCPRemarkingEntry 1 }

sm16tat2saQosDSCPRemarkingDSCP OBJECT-TYPE
    SYNTAX Integer32 (0..63)
    MAX-ACCESS read-write
    STATUS current
    DESCRIPTION
        "DSCP of QoS DSCP Remarking"
    ::= { sm16tat2saQosDSCPRemarkingEntry 2 }

-- *************************************************************
-- Start sm16tat2saLoopProtection group
-- *************************************************************
sm16tat2saLoopProtection OBJECT IDENTIFIER ::= { sm16tat2saConfiguration 12 }

sm16tat2saLoopProtectionConfig OBJECT IDENTIFIER ::= { sm16tat2saLoopProtection 1 }

sm16tat2saLoopProtectionGlobalEnable OBJECT-TYPE
   SYNTAX INTEGER { disable(0), enable(1) }
   MAX-ACCESS read-write
   STATUS current
   DESCRIPTION
       "Configure loop protection mode.
        0: disable,
        1: enable. "
   ::= { sm16tat2saLoopProtectionConfig 1 }

sm16tat2saLoopProtectionTranmisstionTime OBJECT-TYPE
   SYNTAX Integer32(1..10)
   MAX-ACCESS read-write
   STATUS current
   DESCRIPTION
       "Configure loop protection transmit interval.
        range: 1-10. "
   ::= { sm16tat2saLoopProtectionConfig 2 }

sm16tat2saLoopProtectionShutdownTime OBJECT-TYPE
   SYNTAX Integer32(10..604800)
   MAX-ACCESS read-write
   STATUS current
   DESCRIPTION
       "Configure loop protection shutdown time.
        range: 10-604800. "
   ::= { sm16tat2saLoopProtectionConfig 3 }

sm16tat2saLoopProtectionConfigurationTable OBJECT-TYPE
   SYNTAX SEQUENCE OF SM16TAT2SALoopProtectionConfigurationEntry
   MAX-ACCESS not-accessible
   STATUS current
   DESCRIPTION
       " Show Loop Protection configurations. "
   ::= { sm16tat2saLoopProtectionConfig 4 }

sm16tat2saLoopProtectionConfigurationEntry OBJECT-TYPE
   SYNTAX SM16TAT2SALoopProtectionConfigurationEntry
   MAX-ACCESS not-accessible
   STATUS current
   DESCRIPTION
       " "
   INDEX { sm16tat2saLoopProtectionConfPort }
   ::= { sm16tat2saLoopProtectionConfigurationTable 1 }

SM16TAT2SALoopProtectionConfigurationEntry ::= SEQUENCE {
   sm16tat2saLoopProtectionConfPort Integer32,
   sm16tat2saLoopProtectionConfEnable INTEGER,
   sm16tat2saLoopProtectionConfAction INTEGER,
   sm16tat2saLoopProtectionConfTxmode INTEGER
}

sm16tat2saLoopProtectionConfPort OBJECT-TYPE
   SYNTAX Integer32(1..255)
   MAX-ACCESS not-accessible
   STATUS current
   DESCRIPTION
       " port, range : 1 - port number. "
   ::= { sm16tat2saLoopProtectionConfigurationEntry 1 }

sm16tat2saLoopProtectionConfEnable OBJECT-TYPE
   SYNTAX INTEGER { disable(0), enable(1) }
   MAX-ACCESS read-write
   STATUS current
   DESCRIPTION
       " Configure loop protection port mode.
         0: disable,
         1: enable. "
   ::= { sm16tat2saLoopProtectionConfigurationEntry 2 }

sm16tat2saLoopProtectionConfAction OBJECT-TYPE
   SYNTAX INTEGER { shutdown(0), shutdownLog(1), log(2) }
   MAX-ACCESS read-write
   STATUS current
   DESCRIPTION
       " Configure loop protection port action.
         0: Shutdown port,
         1: Shutdown port and Log,
         2: Log Only. "
   ::= { sm16tat2saLoopProtectionConfigurationEntry 3 }

sm16tat2saLoopProtectionConfTxmode OBJECT-TYPE
   SYNTAX INTEGER { disable(0), enable(1) }
   MAX-ACCESS read-write
   STATUS current
   DESCRIPTION
       " Configure loop protection port transmit mode.
         0: disable,
         1: enable. "
   ::= { sm16tat2saLoopProtectionConfigurationEntry 4 }

sm16tat2saLoopProtectionStatusTable OBJECT-TYPE
   SYNTAX SEQUENCE OF SM16TAT2SALoopProtectionStatusEntry
   MAX-ACCESS not-accessible
   STATUS current
   DESCRIPTION
       " Show Loop Protection Status. "
   ::= { sm16tat2saLoopProtection 2 }

sm16tat2saLoopProtectionStatusEntry OBJECT-TYPE
   SYNTAX SM16TAT2SALoopProtectionStatusEntry
   MAX-ACCESS not-accessible
   STATUS current
   DESCRIPTION
       " "
   INDEX { sm16tat2saLoopProtectionStatusPort }
   ::= { sm16tat2saLoopProtectionStatusTable 1 }

SM16TAT2SALoopProtectionStatusEntry ::= SEQUENCE {
   sm16tat2saLoopProtectionStatusPort Integer32,
   sm16tat2saLoopProtectionStatusLoops Counter32,
   sm16tat2saLoopProtectionStatusStatus DisplayString,
   sm16tat2saLoopProtectionStatusLoop DisplayString,
   sm16tat2saLoopProtectionStatusTimeLastLoop DisplayString
}

sm16tat2saLoopProtectionStatusPort OBJECT-TYPE
   SYNTAX Integer32(1..255)
   MAX-ACCESS not-accessible
   STATUS current
   DESCRIPTION
       " port, range : 1 - port number. "
   ::= { sm16tat2saLoopProtectionStatusEntry 1 }

sm16tat2saLoopProtectionStatusLoops OBJECT-TYPE
   SYNTAX Counter32
   MAX-ACCESS read-only
   STATUS current
   DESCRIPTION
       " The number of loops detected on this port. "
   ::= { sm16tat2saLoopProtectionStatusEntry 2 }

sm16tat2saLoopProtectionStatusStatus OBJECT-TYPE
   SYNTAX DisplayString
   MAX-ACCESS read-only
   STATUS current
   DESCRIPTION
       " The current loop protection status of the port. "
   ::= { sm16tat2saLoopProtectionStatusEntry 3 }

sm16tat2saLoopProtectionStatusLoop OBJECT-TYPE
   SYNTAX DisplayString
   MAX-ACCESS read-only
   STATUS current
   DESCRIPTION
       " Whether a loop is currently detected on the port. "
   ::= { sm16tat2saLoopProtectionStatusEntry 4 }

sm16tat2saLoopProtectionStatusTimeLastLoop OBJECT-TYPE
   SYNTAX DisplayString
   MAX-ACCESS read-only
   STATUS current
   DESCRIPTION
       " The time of the last loop event detected. "
   ::= { sm16tat2saLoopProtectionStatusEntry 5 }

-- *************************************************************
-- Start sm16tat2saPoe group
-- *************************************************************
sm16tat2saPoe OBJECT IDENTIFIER ::= { sm16tat2saConfiguration 13 }

sm16tat2saPoeConfiguration OBJECT IDENTIFIER ::= { sm16tat2saPoe 1 }

sm16tat2saPrimaryPowerSupply OBJECT-TYPE
   SYNTAX Integer32 (0..2000)
   MAX-ACCESS read-only
   STATUS current
   DESCRIPTION
       "It must be defined what amount of power the primary and backup power sources can deliver. "
   ::= { sm16tat2saPoeConfiguration 1 }

sm16tat2saCapacitorDetection OBJECT-TYPE
   SYNTAX AdminMode
   MAX-ACCESS read-write
   STATUS current
   DESCRIPTION
       "The Detection represents the PoE capacitor detection.
         0: disable(default), 1: enable. "
   ::= { sm16tat2saPoeConfiguration 2 }

sm16tat2saPoePortConfigTable OBJECT-TYPE
   SYNTAX SEQUENCE OF SM16TAT2SAPoePortConfigEntry
   MAX-ACCESS not-accessible
   STATUS current
   DESCRIPTION
       "The table of the PoE Port Configuration. "
   ::= { sm16tat2saPoeConfiguration 3 }

sm16tat2saPoePortConfigEntry OBJECT-TYPE
   SYNTAX SM16TAT2SAPoePortConfigEntry
   MAX-ACCESS not-accessible
   STATUS current
   DESCRIPTION
       "The entry of the PoE Port Configuration. "
   INDEX { ifIndex }
   ::= { sm16tat2saPoePortConfigTable 1 }

SM16TAT2SAPoePortConfigEntry ::=
SEQUENCE {
   sm16tat2saPoePortConfigPoeMode INTEGER,
   sm16tat2saPoePortConfigPoeSchedule Integer32,
   sm16tat2saPoePortConfigPriority INTEGER,
   sm16tat2saPoePortConfigMaximumPower Integer32
}

sm16tat2saPoePortConfigPoeMode OBJECT-TYPE

   SYNTAX INTEGER {disable(0), enable(2), force(3)}

   MAX-ACCESS read-write
   STATUS current
   DESCRIPTION

       "The PoE Mode represents the PoE operating mode for the port.
         0: disable, 2: enable(default), 3: force."

   ::= { sm16tat2saPoePortConfigEntry 1 }

sm16tat2saPoePortConfigPoeSchedule OBJECT-TYPE
   SYNTAX Integer32 (-1..16)
   MAX-ACCESS read-write
   STATUS current
   DESCRIPTION
       "Specify a valid PoE schedule profile by profile id. -1: disable(default), 0-15: profile 1~16. "
   ::= { sm16tat2saPoePortConfigEntry 2 }

sm16tat2saPoePortConfigPriority OBJECT-TYPE
   SYNTAX INTEGER {low(0), high(1), critical(2)}
   MAX-ACCESS read-write
   STATUS current
   DESCRIPTION
       "The Priority represents the ports priority. There are three levels of power priority named Low, High and Critical.
         0: Low(default), 1: High, 2: Critical. "
   ::= { sm16tat2saPoePortConfigEntry 3 }

sm16tat2saPoePortConfigMaximumPower OBJECT-TYPE
   SYNTAX Integer32 (1..30)
   MAX-ACCESS read-write
   STATUS current
   DESCRIPTION
       "The Maximum Power value contains a numerical value that indicates the maximum power in watts that can be delivered to a remote device.
         default: 30"
   ::= { sm16tat2saPoePortConfigEntry 4 }
sm16tat2saPoEManagementMode OBJECT-TYPE
   SYNTAX INTEGER {classConsump(1), allocatedConsump(3), lldpmedConsump(5)}
   MAX-ACCESS read-write
   STATUS current
   DESCRIPTION
       "The power management mode for PoE port.
        1: Class consumption,
        3: Allocated consumption,
        5: LLDP-Med consumption. "
   ::= { sm16tat2saPoeConfiguration 5 }

sm16tat2saPoEAlwaysOnPoE OBJECT-TYPE

   SYNTAX ActivateCmd
   MAX-ACCESS read-write
   STATUS current
   DESCRIPTION
       "When the switch restart, it will retain PoE sourcing."
   ::= { sm16tat2saPoeConfiguration 8 }

sm16tat2saPoeStatus OBJECT IDENTIFIER ::= { sm16tat2saPoe 2 }

sm16tat2saPoeStatusTable OBJECT-TYPE
   SYNTAX SEQUENCE OF SM16TAT2SAPoeStatusEntry
   MAX-ACCESS not-accessible
   STATUS current
   DESCRIPTION
       "Configure PoE Scheduling Table. "
   ::= { sm16tat2saPoeStatus 1 }

sm16tat2saPoeStatusEntry OBJECT-TYPE
   SYNTAX SM16TAT2SAPoeStatusEntry
   MAX-ACCESS not-accessible
   STATUS current
   DESCRIPTION
       " "
   INDEX { ifIndex }
   ::= { sm16tat2saPoeStatusTable 1 }

SM16TAT2SAPoeStatusEntry ::= SEQUENCE {
   sm16tat2saPoeStatusPDClass DisplayString,
   sm16tat2saPoeStatusPowerAllocated DisplayString,
   sm16tat2saPoeStatusPowerUsed DisplayString,
   sm16tat2saPoeStatusCurrentUsed DisplayString,
   sm16tat2saPoeStatusPriority DisplayString,
   sm16tat2saPoeStatusPortStatus DisplayString
}

sm16tat2saPoeStatusPDClass OBJECT-TYPE
   SYNTAX DisplayString
   MAX-ACCESS read-only
   STATUS current
   DESCRIPTION
       "Indicates the QCL user."
   ::= { sm16tat2saPoeStatusEntry 1 }

sm16tat2saPoeStatusPowerAllocated OBJECT-TYPE
   SYNTAX DisplayString
   MAX-ACCESS read-only
   STATUS current
   DESCRIPTION
      "The Power Allocated shows the amount of power the switch has allocated for the PD."
   ::= { sm16tat2saPoeStatusEntry 2 }

sm16tat2saPoeStatusPowerUsed OBJECT-TYPE
   SYNTAX DisplayString
   MAX-ACCESS read-only
   STATUS current
   DESCRIPTION
      "The Power Used shows how much power the PD currently is using. "
   ::= { sm16tat2saPoeStatusEntry 3 }

sm16tat2saPoeStatusCurrentUsed OBJECT-TYPE
   SYNTAX DisplayString
   MAX-ACCESS read-only
   STATUS current
   DESCRIPTION
      "The Power Used shows how much current the PD currently is using. "
   ::= { sm16tat2saPoeStatusEntry 4 }

sm16tat2saPoeStatusPriority OBJECT-TYPE
   SYNTAX DisplayString
   MAX-ACCESS read-only
   STATUS current
   DESCRIPTION
      "The Priority shows the port's priority configured by the user. "
   ::= { sm16tat2saPoeStatusEntry 5 }

sm16tat2saPoeStatusPortStatus OBJECT-TYPE
   SYNTAX DisplayString
   MAX-ACCESS read-only
   STATUS current
   DESCRIPTION
      "The Port Status shows the port's status. "
   ::= { sm16tat2saPoeStatusEntry 6 }

sm16tat2saPoePowerDelay OBJECT IDENTIFIER ::= { sm16tat2saPoe 3 }

sm16tat2saPoePowerDelayTable OBJECT-TYPE
   SYNTAX SEQUENCE OF SM16TAT2SAPoePowerDelayEntry
   MAX-ACCESS not-accessible
   STATUS current
   DESCRIPTION
       "Configure PoE Power Delay mode. "
   ::= { sm16tat2saPoePowerDelay 1 }

sm16tat2saPoePowerDelayEntry OBJECT-TYPE
   SYNTAX SM16TAT2SAPoePowerDelayEntry
   MAX-ACCESS not-accessible
   STATUS current
   DESCRIPTION
       " "
   INDEX { ifIndex }
   ::= { sm16tat2saPoePowerDelayTable 1 }

SM16TAT2SAPoePowerDelayEntry ::=
SEQUENCE {
   sm16tat2saPoePowerDelayMode AdminMode,
   sm16tat2saPoePowerDelayTime Integer32
}

sm16tat2saPoePowerDelayMode OBJECT-TYPE
   SYNTAX AdminMode
   MAX-ACCESS read-write
   STATUS current
   DESCRIPTION
       "Turn on / off the power delay function,
         0: disable(default), 1: enable. "
   ::= { sm16tat2saPoePowerDelayEntry 1 }

sm16tat2saPoePowerDelayTime OBJECT-TYPE
   SYNTAX Integer32 (0..300)
   MAX-ACCESS read-write
   STATUS current
   DESCRIPTION
       "set Delay Time,
         default: 0,
         range: 0-300 sec. "
   ::= { sm16tat2saPoePowerDelayEntry 2 }

sm16tat2saPoeAutoCheck OBJECT IDENTIFIER ::= { sm16tat2saPoe 4 }

sm16tat2saPoeAutoCheckPingCheck OBJECT-TYPE
   SYNTAX INTEGER {off(0), on(1)}
   MAX-ACCESS read-write
   STATUS current
   DESCRIPTION
       "connection between PoE port and power device.
         0: off(default), 1: on. "
   ::= { sm16tat2saPoeAutoCheck 1 }

sm16tat2saPoeAutoCheckTable OBJECT-TYPE
   SYNTAX SEQUENCE OF SM16TAT2SAPoeAutoCheckEntry
   MAX-ACCESS not-accessible
   STATUS current
   DESCRIPTION
       " Configure PoE Auto check mode. "
   ::= { sm16tat2saPoeAutoCheck 2 }

sm16tat2saPoeAutoCheckEntry OBJECT-TYPE
   SYNTAX SM16TAT2SAPoeAutoCheckEntry
   MAX-ACCESS not-accessible
   STATUS current
   DESCRIPTION
       " "
   INDEX { ifIndex }
   ::= { sm16tat2saPoeAutoCheckTable 1 }

SM16TAT2SAPoeAutoCheckEntry ::=
SEQUENCE {
   sm16tat2saPoeAutoCheckPingIPAddress DisplayString,
   sm16tat2saPoeAutoCheckStartupTime Integer32,
   sm16tat2saPoeAutoCheckIntervalTime Integer32,
   sm16tat2saPoeAutoCheckRetryTime Integer32,
   sm16tat2saPoeAutoCheckFailureLog DisplayString,
   sm16tat2saPoeAutoCheckFailureAction INTEGER,
   sm16tat2saPoeAutoCheckRebootTime Integer32,
   sm16tat2saPoeAutoCheckMaxRebootTimes Integer32
}

sm16tat2saPoeAutoCheckPingIPAddress OBJECT-TYPE
   SYNTAX DisplayString
   MAX-ACCESS read-write
   STATUS current
   DESCRIPTION
       "IP Address the system should ping.
         default: 0.0.0.0 . "
   ::= { sm16tat2saPoeAutoCheckEntry 1 }

sm16tat2saPoeAutoCheckStartupTime OBJECT-TYPE
   SYNTAX Integer32 (30..600)
   MAX-ACCESS read-write
   STATUS current
   DESCRIPTION
       "When PD has been start up, the Switch will wait Start up time to do PoE Auto Checking.
         default: 60, range: 30-600 sec. "
   ::= { sm16tat2saPoeAutoCheckEntry 2 }

sm16tat2saPoeAutoCheckIntervalTime OBJECT-TYPE
   SYNTAX Integer32 (10..120)
   MAX-ACCESS read-write
   STATUS current
   DESCRIPTION
       "Device will send checking message to PD each interval time.
         default: 30, range: 10-120 sec. "
   ::= { sm16tat2saPoeAutoCheckEntry 3 }

sm16tat2saPoeAutoCheckRetryTime OBJECT-TYPE
   SYNTAX Integer32 (1..5)
   MAX-ACCESS read-write
   STATUS current
   DESCRIPTION
       "It will retry to send detection again.
         default: 3, range: 1-5. "
   ::= { sm16tat2saPoeAutoCheckEntry 4 }

sm16tat2saPoeAutoCheckFailureLog OBJECT-TYPE
   SYNTAX DisplayString
   MAX-ACCESS read-only
   STATUS current
   DESCRIPTION
       "Failure loggings counter. "
   ::= { sm16tat2saPoeAutoCheckEntry 5 }

sm16tat2saPoeAutoCheckFailureAction OBJECT-TYPE
   SYNTAX INTEGER {nothing(0), reboot(1)}
   MAX-ACCESS read-write
   STATUS current
   DESCRIPTION
       "It will retry to send detection again,
         0: Nothing(default), 1: Reboot Remote PD. "
   ::= { sm16tat2saPoeAutoCheckEntry 6 }

sm16tat2saPoeAutoCheckRebootTime OBJECT-TYPE
   SYNTAX Integer32 (3..120)
   MAX-ACCESS read-write
   STATUS current
   DESCRIPTION
       "When PD has been rebooted, the PoE port restored power after the specified time.
         default: 15, range: 3-120 sec. "
   ::= { sm16tat2saPoeAutoCheckEntry 7 }

sm16tat2saPoeAutoCheckMaxRebootTimes OBJECT-TYPE
   SYNTAX Integer32 (0..10)
   MAX-ACCESS read-write
   STATUS current
   DESCRIPTION
       "When action happen reboot times over max reboot times,
       auto checking will stop on this port until user change
       PoE mode without disable in PoE configurtion.
       If max reboot times is 0, auto checking will not stop.
       Default: 0, range: 0-10 times."
   ::= { sm16tat2saPoeAutoCheckEntry 8 }

sm16tat2saPoeSchedulingProfile OBJECT IDENTIFIER ::= { sm16tat2saPoe 5 }

sm16tat2saPoeSchedulingNameTable OBJECT-TYPE
   SYNTAX SEQUENCE OF SM16TAT2SAPoeSchedulingNameEntry
   MAX-ACCESS not-accessible
   STATUS current
   DESCRIPTION
       " Show Poe Scheduling Name Config. "
   ::= { sm16tat2saPoeSchedulingProfile 1 }

sm16tat2saPoeSchedulingNameEntry OBJECT-TYPE
   SYNTAX SM16TAT2SAPoeSchedulingNameEntry
   MAX-ACCESS not-accessible
   STATUS current
   DESCRIPTION
       " "
   INDEX { sm16tat2saPoeSchedulingNumberIndex }
   ::= { sm16tat2saPoeSchedulingNameTable 1 }

SM16TAT2SAPoeSchedulingNameEntry ::=
SEQUENCE {
   sm16tat2saPoeSchedulingNumberIndex Integer32,
   sm16tat2saPoeSchedulingName DisplayString
}

sm16tat2saPoeSchedulingNumberIndex OBJECT-TYPE
   SYNTAX Integer32 (1..16)
   MAX-ACCESS not-accessible
   STATUS current
   DESCRIPTION
       "The index of the PoE Profile Number. number 1~16 "
   ::= { sm16tat2saPoeSchedulingNameEntry 1 }

sm16tat2saPoeSchedulingName OBJECT-TYPE
   SYNTAX DisplayString
   MAX-ACCESS read-write
   STATUS current
   DESCRIPTION
       "Profile Name. maximum length:32. profile 1~16"
   ::= { sm16tat2saPoeSchedulingNameEntry 2 }

sm16tat2saPoeSchedulingTimeTable OBJECT-TYPE
   SYNTAX SEQUENCE OF SM16TAT2SAPoeSchedulingTimeEntry
   MAX-ACCESS not-accessible
   STATUS current
   DESCRIPTION
       " Show Poe Scheduling Time Config. "
   ::= { sm16tat2saPoeSchedulingProfile 2 }

sm16tat2saPoeSchedulingTimeEntry OBJECT-TYPE
   SYNTAX SM16TAT2SAPoeSchedulingTimeEntry
   MAX-ACCESS not-accessible
   STATUS current
   DESCRIPTION
       " "
   INDEX { sm16tat2saPoeSchedulingNumberIndex, sm16tat2saPoeSchedulingTimeWeekIndex }
   ::= { sm16tat2saPoeSchedulingTimeTable 1 }

SM16TAT2SAPoeSchedulingTimeEntry ::=
SEQUENCE {
   sm16tat2saPoeSchedulingTimeWeekIndex Integer32,
   sm16tat2saPoeSchedulingTimeStartTimeHour Integer32,
   sm16tat2saPoeSchedulingTimeStartTimeMinute Integer32,
   sm16tat2saPoeSchedulingTimeEndTimeHour Integer32,
   sm16tat2saPoeSchedulingTimeEndTimeMinute Integer32
}

sm16tat2saPoeSchedulingTimeWeekIndex OBJECT-TYPE
   SYNTAX Integer32 (1..7)
   MAX-ACCESS not-accessible
   STATUS current
   DESCRIPTION
       "Week Index.
     1: Mon, 2:Tue, 3: Wed, 4: Thu, 5: Fri, 6: Sat, 7: Sun "
   ::= { sm16tat2saPoeSchedulingTimeEntry 1 }

sm16tat2saPoeSchedulingTimeStartTimeHour OBJECT-TYPE
   SYNTAX Integer32
   MAX-ACCESS read-write
   STATUS current
   DESCRIPTION
       "PoE Scheduling Start Hour. Range: 0-23. "
   ::= { sm16tat2saPoeSchedulingTimeEntry 2 }

sm16tat2saPoeSchedulingTimeStartTimeMinute OBJECT-TYPE
   SYNTAX Integer32
   MAX-ACCESS read-write
   STATUS current
   DESCRIPTION
       "PoE Scheduling Start Minute. Range:0,5,10,...,55. "
   ::= { sm16tat2saPoeSchedulingTimeEntry 3 }

sm16tat2saPoeSchedulingTimeEndTimeHour OBJECT-TYPE
   SYNTAX Integer32
   MAX-ACCESS read-write
   STATUS current
   DESCRIPTION
       "PoE Scheduling End Hour. Range: 0-23. "
   ::= { sm16tat2saPoeSchedulingTimeEntry 4 }

sm16tat2saPoeSchedulingTimeEndTimeMinute OBJECT-TYPE
   SYNTAX Integer32
   MAX-ACCESS read-write
   STATUS current
   DESCRIPTION
       "PoE Scheduling End Minute. Range:0,5,10,...,55. "
   ::= { sm16tat2saPoeSchedulingTimeEntry 5 }

-- *************************************************************
-- Start sm16tat2saMstp group
-- *************************************************************
sm16tat2saMstpGroup OBJECT IDENTIFIER ::= { sm16tat2saConfiguration 18 }

sm16tat2saMstpMiscellaneousConfig OBJECT IDENTIFIER ::= { sm16tat2saMstpGroup 1 }

sm16tat2saMstpMibGlobalEnable OBJECT-TYPE
   SYNTAX INTEGER { disable(0), enable(1) }
   MAX-ACCESS read-write
   STATUS current
   DESCRIPTION
       "This variable is used to start or stop the spanning tree protocol.
        0: disable,
        1: enable. "
   ::= { sm16tat2saMstpMiscellaneousConfig 1 }

sm16tat2saMstpMstiAddVlans OBJECT-TYPE
   SYNTAX DisplayString (SIZE (0..200))
   MAX-ACCESS read-write
   STATUS current
   DESCRIPTION
       "This DisplayString represents a vid list to be mapped to an MSTI instance.
        ieee8021MstpRowStatus in the ieee8021MstpTable of IEEE8021-MSTP-MIB is used
        to add a new MSTI instance. Only legal VID numbers (1-4094) are allowed.
        Consecutive VIDs can be represented as for example 31-40(Between Vlan 31 and 40 is hyphen).
        The other legal symbol is comma.
        for example: 1,3,4,5,31-40,4094 "
   ::= { sm16tat2saMstpMiscellaneousConfig 2 }

-- *************************************************************
-- Start sm16tat2saLinkAggregation group
-- *************************************************************
sm16tat2saLinkAggregationGroup OBJECT IDENTIFIER ::= { sm16tat2saConfiguration 23 }

sm16tat2saLagMiscellaneousConfig OBJECT IDENTIFIER ::= { sm16tat2saLinkAggregationGroup 1 }

sm16tat2saLagTrafficDistributionMode OBJECT-TYPE
   SYNTAX INTEGER { srcmac(1), dstmac(2), srcdstmac(3),srcip(4), dstip(5), srcdstip(6) }
   MAX-ACCESS read-write
   STATUS current
   DESCRIPTION
       "This variable is used to specify the port selection hash algorithm
       for traffic distribution."
   ::= { sm16tat2saLagMiscellaneousConfig 1 }

sm16tat2saLagLacpSystemPriority OBJECT-TYPE
   SYNTAX Integer32 (1..65535)
   MAX-ACCESS read-write
   STATUS current
   DESCRIPTION
        "A 2-octet read-write value indicating the priority value
        associated with the Actor's System ID."
   ::= { sm16tat2saLagMiscellaneousConfig 2 }

sm16tat2saLagPortTable OBJECT-TYPE
    SYNTAX SEQUENCE OF SM16TAT2SALagPortEntry
    MAX-ACCESS not-accessible
    STATUS current
    DESCRIPTION
        "A table that contains Link Aggregation Control
        configuration information about every
        Aggregation Port associated with this device.
        A row appears in this table for each physical port."
    ::= { sm16tat2saLinkAggregationGroup 2 }

sm16tat2saLagPortEntry OBJECT-TYPE
    SYNTAX SM16TAT2SALagPortEntry
    MAX-ACCESS not-accessible
    STATUS current
    DESCRIPTION
        "A list of Link Aggregation Control configuration
        parameters for each Aggregation Port on this device."
    INDEX { sm16tat2saLagPortIndex }
    ::= { sm16tat2saLagPortTable 1 }

SM16TAT2SALagPortEntry ::=
    SEQUENCE {
        sm16tat2saLagPortIndex Integer32,
        sm16tat2saLagPortLacpAggAdminKey Integer32,
        sm16tat2saLagPortStaticAggAdminKey Integer32,
        sm16tat2saLagPortLacpActivity INTEGER,
        sm16tat2saLagPortLacpTimeout INTEGER,
        sm16tat2saLagPortAggregatorPort Integer32,
        sm16tat2saLagPortReadyState INTEGER
    }

sm16tat2saLagPortIndex OBJECT-TYPE
    SYNTAX Integer32 (1..52)
    MAX-ACCESS not-accessible
    STATUS current
    DESCRIPTION
        "The switch port number"
    ::= { sm16tat2saLagPortEntry 1 }

sm16tat2saLagPortLacpAggAdminKey OBJECT-TYPE
    SYNTAX Integer32 (0..8)
    MAX-ACCESS read-write
    STATUS current
    DESCRIPTION
        "The current administrative value of the Key for a LACP aggregation port.
        A non-zero value will force the port to participate in a LACP aggregation
        group and force the value of LagPortStaticAggAdminKey to be 0.
        A zero value setting will let the port turn to be an Individual port and
        force the value of LagPortStaticAggAdminKey to be 0 at the same time."
    ::= { sm16tat2saLagPortEntry 2 }

sm16tat2saLagPortStaticAggAdminKey OBJECT-TYPE
    SYNTAX Integer32 (0..8)
    MAX-ACCESS read-write
    STATUS current
    DESCRIPTION
        "The current administrative value of the key for a Static aggregation port.
        A non-zero value will force the port to participate in a Static aggregation
        group and force the value of LagPortLacpAggAdminKey to be 0.
        A zero value setting will let the port turn to be an Individual port and
        force the value of LagPortLacpAggAdminKey to be 0 at the same time."
    ::= { sm16tat2saLagPortEntry 3 }

sm16tat2saLagPortLacpActivity OBJECT-TYPE
    SYNTAX INTEGER { passive(0), active(1)}
    MAX-ACCESS read-write
    STATUS current
    DESCRIPTION
        "The LACP Activity value locally assigned to a LACP Aggregation Port.
        This value has effect only on ports whose aggregation method is LACP"
    ::= { sm16tat2saLagPortEntry 4 }

sm16tat2saLagPortLacpTimeout OBJECT-TYPE
    SYNTAX INTEGER { slowtimeout(0), fasttimeout(1)}
    MAX-ACCESS read-write
    STATUS current
    DESCRIPTION
        "The LACP Timeout value locally assigned to a LACP Aggregation Port.
        This value has effect only on ports whose aggregation method is LACP"
    ::= { sm16tat2saLagPortEntry 5 }

sm16tat2saLagPortAggregatorPort OBJECT-TYPE
    SYNTAX Integer32(1..52)
    MAX-ACCESS read-only
    STATUS current
    DESCRIPTION
        "The identifier value of the Aggregator that this Aggregation
        Port is currently attached to."
    ::= { sm16tat2saLagPortEntry 6 }

sm16tat2saLagPortReadyState OBJECT-TYPE
    SYNTAX INTEGER { notready(0), ready(1)}
    MAX-ACCESS read-only
    STATUS current
    DESCRIPTION
        "A status value indicating whether the Aggregation Port
         is ready for packet forwarding (1) or not ready (0)."
    ::= { sm16tat2saLagPortEntry 7 }

sm16tat2saLagAggregatorTable OBJECT-TYPE
    SYNTAX SEQUENCE OF SM16TAT2SALagAggregatorEntry
    MAX-ACCESS not-accessible
    STATUS current
    DESCRIPTION
        "A table that contains status information about every aggregator
        associated with this device. Each physical port can be deemed as
        an aggregator."
    ::= { sm16tat2saLinkAggregationGroup 3 }

sm16tat2saLagAggregatorEntry OBJECT-TYPE
    SYNTAX SM16TAT2SALagAggregatorEntry
    MAX-ACCESS not-accessible
    STATUS current
    DESCRIPTION
        "A list of aggregator status information for each aggregator on this device."
    INDEX { sm16tat2saLagAggregatorPortIndex }
    ::= { sm16tat2saLagAggregatorTable 1 }

SM16TAT2SALagAggregatorEntry ::=
    SEQUENCE {
        sm16tat2saLagAggregatorPortIndex Integer32,
        sm16tat2saLagPortAggregationMethod INTEGER,
        sm16tat2saLagAggregatorMemberPorts DisplayString,
        sm16tat2saLagAggregatorReadyPorts DisplayString
    }

sm16tat2saLagAggregatorPortIndex OBJECT-TYPE
    SYNTAX Integer32 (1..52)
    MAX-ACCESS not-accessible
    STATUS current
    DESCRIPTION
        "The aggregator port number"
    ::= { sm16tat2saLagAggregatorEntry 1 }

sm16tat2saLagPortAggregationMethod OBJECT-TYPE
    SYNTAX INTEGER { none(0), lacp(1), static(2)}
    MAX-ACCESS read-only
    STATUS current
    DESCRIPTION
        "The method the aggrgator uses to aggregate physical Port.
        In the LagPortTable if both LagPortLacpAggAdminKey and LagPortStaticAggAdminKey
        are zero for a port then the field will be 0 (none) for this corresponding
        aggregator port."
    ::= { sm16tat2saLagAggregatorEntry 2 }

sm16tat2saLagAggregatorMemberPorts OBJECT-TYPE
    SYNTAX DisplayString
    MAX-ACCESS read-only
    STATUS current
    DESCRIPTION
        "The port members that are attached to this aggregator port"
    ::= { sm16tat2saLagAggregatorEntry 3 }

sm16tat2saLagAggregatorReadyPorts OBJECT-TYPE
    SYNTAX DisplayString
    MAX-ACCESS read-only
    STATUS current
    DESCRIPTION
        "The ready-to-service port members that are attached to
        this aggregator port"
    ::= { sm16tat2saLagAggregatorEntry 4 }

sm16tat2saLagLacpPortTable OBJECT-TYPE
    SYNTAX SEQUENCE OF SM16TAT2SALagLacpPortEntry
    MAX-ACCESS not-accessible
    STATUS current
    DESCRIPTION
        "A table that contains additional aggregation status information
        about every LACP Aggregation Port associated with this device."
    ::= { sm16tat2saLinkAggregationGroup 4 }

sm16tat2saLagLacpPortEntry OBJECT-TYPE
    SYNTAX SM16TAT2SALagLacpPortEntry
    MAX-ACCESS not-accessible
    STATUS current
    DESCRIPTION
        "A list of Link Aggregation Control configuration
        parameters for each Aggregation Port on this device."
    INDEX { sm16tat2saLagLacpAggregator, sm16tat2saLagLacpActorPort}
    ::= { sm16tat2saLagLacpPortTable 1 }

SM16TAT2SALagLacpPortEntry ::=
    SEQUENCE {
        sm16tat2saLagLacpAggregator Integer32,
        sm16tat2saLagLacpActorPort Integer32,
        sm16tat2saLagLacpActorOperKey Integer32,
        sm16tat2saLagLacpPartnerPort Integer32,
        sm16tat2saLagLacpPartnerOperKey Integer32,
        sm16tat2saLagLacpActorSystemPriority Integer32,
        sm16tat2saLagLacpActorSystemID MacAddress,
        sm16tat2saLagLacpPartnerSystemPriority Integer32,
        sm16tat2saLagLacpPartnerSystemID MacAddress,
        sm16tat2saLagLacpPortReadyState INTEGER
    }

sm16tat2saLagLacpAggregator OBJECT-TYPE
    SYNTAX Integer32 (1..1024)
    MAX-ACCESS not-accessible
    STATUS current
    DESCRIPTION
        "The identifier value of the Aggregator that this Aggregation
        Port is currently attached to."
    ::= { sm16tat2saLagLacpPortEntry 1 }

sm16tat2saLagLacpActorPort OBJECT-TYPE
    SYNTAX Integer32 (1..52)
    MAX-ACCESS not-accessible
    STATUS current
    DESCRIPTION
        "The switch port number of the LACP port"
    ::= { sm16tat2saLagLacpPortEntry 2 }

sm16tat2saLagLacpActorOperKey OBJECT-TYPE
    SYNTAX Integer32 (1..16)
    MAX-ACCESS read-only
    STATUS current
    DESCRIPTION
        "The current operational value of the Key for the
        Aggregation Port. This is a 16-bit, read-only value."
    ::= { sm16tat2saLagLacpPortEntry 3 }

sm16tat2saLagLacpPartnerPort OBJECT-TYPE
    SYNTAX Integer32 (1..52)
    MAX-ACCESS read-only
    STATUS current
    DESCRIPTION
        "The switch port number of the LACP port"
    ::= { sm16tat2saLagLacpPortEntry 4 }

sm16tat2saLagLacpPartnerOperKey OBJECT-TYPE
    SYNTAX Integer32 (1..16)
    MAX-ACCESS read-only
    STATUS current
    DESCRIPTION
        "The current operational value of the Key for the
        protocol Partner. The value of this attribute may contain
        the manually configured value if there is no protocol Partner.
        This is a 16-bit, read-only value."
    ::= { sm16tat2saLagLacpPortEntry 5 }

sm16tat2saLagLacpActorSystemPriority OBJECT-TYPE
    SYNTAX Integer32 (1..65535)
    MAX-ACCESS read-only
    STATUS current
    DESCRIPTION
        "A 2-octet value representing the priority value associated
        with the Actor's System ID."
    ::= { sm16tat2saLagLacpPortEntry 6 }

sm16tat2saLagLacpActorSystemID OBJECT-TYPE
    SYNTAX MacAddress
    MAX-ACCESS read-only
    STATUS current
    DESCRIPTION
        "A 6-octet read-only MAC address value that defines
        the value of the System ID for the System that contains this
        Aggregation Port."
    ::= { sm16tat2saLagLacpPortEntry 7 }

sm16tat2saLagLacpPartnerSystemPriority OBJECT-TYPE
    SYNTAX Integer32 (1..65535)
    MAX-ACCESS read-only
    STATUS current
    DESCRIPTION
        "A 2-octet read-only value indicating the operational value
        of priority associated with the Partner's System ID. The
        value of this attribute may contain the manually configured value
        if there is no protocol Partner."
    ::= { sm16tat2saLagLacpPortEntry 8 }

sm16tat2saLagLacpPartnerSystemID OBJECT-TYPE
    SYNTAX MacAddress
    MAX-ACCESS read-only
    STATUS current
    DESCRIPTION
        "A 6-octet read-only MACAddress value representing
        the current value of the Aggregation Port's protocol Partner's
        System ID. A value of zero indicates that there is no known
        protocol Partner. The value of this attribute may contain the
        manually configured value if there is no protocol Partner."
    ::= { sm16tat2saLagLacpPortEntry 9 }

sm16tat2saLagLacpPortReadyState OBJECT-TYPE
    SYNTAX INTEGER { notready(0), ready(1)}
    MAX-ACCESS read-only
    STATUS current
    DESCRIPTION
        "A status value indicating whether the Aggregation Port
         is ready for packet forwarding (1) or not ready (0)."
    ::= { sm16tat2saLagLacpPortEntry 10 }

-- *************************************************************
-- Start sm16tat2saIpmc group
-- *************************************************************
sm16tat2saIpmc OBJECT IDENTIFIER ::= { sm16tat2saConfiguration 24 }

sm16tat2saIgmpConfig OBJECT IDENTIFIER ::= { sm16tat2saIpmc 1 }

sm16tat2saIgmpSnoopingEnable OBJECT-TYPE
   SYNTAX INTEGER { disable(0), enable(1) }
   MAX-ACCESS read-write
   STATUS current
   DESCRIPTION
       "Configure igmp mode.
        0: disable,
        1: enable. "
   ::= { sm16tat2saIgmpConfig 1 }

sm16tat2saIgmpUnkownFlooding OBJECT-TYPE
   SYNTAX INTEGER { disable(0), enable(1) }
   MAX-ACCESS read-write
   STATUS current
   DESCRIPTION
       "Configure Unregistered IPMCv4 Flooding Enabled.
        0: disable,
        1: enable. "
   ::= { sm16tat2saIgmpConfig 2 }

sm16tat2saIgmpSsmRangeAddress OBJECT-TYPE
   SYNTAX IpAddress
   MAX-ACCESS read-write
   STATUS current
   DESCRIPTION
       "Configure IGMP SSM Range Address.
        range: 224.0.0.0 - 239.255.255.255. "
   ::= { sm16tat2saIgmpConfig 3 }

sm16tat2saIgmpSsmRangeLen OBJECT-TYPE
   SYNTAX Integer32 (4..32)
   MAX-ACCESS read-write
   STATUS current
   DESCRIPTION
       "Configure IGMP SSM Range Length.
        range: 4 - 32. "
   ::= { sm16tat2saIgmpConfig 4 }

sm16tat2saIgmpProxyEnable OBJECT-TYPE
   SYNTAX INTEGER { disable(0), enable(1) }
   MAX-ACCESS read-write
   STATUS current
   DESCRIPTION
       "Configure IGMP Proxy Enabled.
        0: disable,
        1: enable. "
   ::= { sm16tat2saIgmpConfig 5 }

sm16tat2saIgmpConfigurationTable OBJECT-TYPE
   SYNTAX SEQUENCE OF SM16TAT2SAIgmpConfigurationEntry
   MAX-ACCESS not-accessible
   STATUS current
   DESCRIPTION
       " Show IPMC port configurations. "
   ::= { sm16tat2saIgmpConfig 6 }

sm16tat2saIgmpConfigurationEntry OBJECT-TYPE
   SYNTAX SM16TAT2SAIgmpConfigurationEntry
   MAX-ACCESS not-accessible
   STATUS current
   DESCRIPTION
       " "
   INDEX { sm16tat2saIgmpConfPort }
   ::= { sm16tat2saIgmpConfigurationTable 1 }

SM16TAT2SAIgmpConfigurationEntry ::= SEQUENCE {
   sm16tat2saIgmpConfPort Integer32,
   sm16tat2saIgmpConfRouterPort INTEGER,
   sm16tat2saIgmpConfFastLeave INTEGER,
   sm16tat2saIgmpConfThrottling Integer32,
   sm16tat2saIgmpConfProfile DisplayString
}

sm16tat2saIgmpConfPort OBJECT-TYPE
   SYNTAX Integer32(1..255)
   MAX-ACCESS not-accessible
   STATUS current
   DESCRIPTION
       " port, range : 1 - port number. "
   ::= { sm16tat2saIgmpConfigurationEntry 1 }

sm16tat2saIgmpConfRouterPort OBJECT-TYPE
   SYNTAX INTEGER { disable(0), enable(1) }
   MAX-ACCESS read-write
   STATUS current
   DESCRIPTION
       " Configure IPMC router port mode.
         0: disable,
         1: enable. "
   ::= { sm16tat2saIgmpConfigurationEntry 2 }

sm16tat2saIgmpConfFastLeave OBJECT-TYPE
   SYNTAX INTEGER { disable(0), enable(1) }
   MAX-ACCESS read-write
   STATUS current
   DESCRIPTION
       " Configure IPMC fast leave mode.
         0: disable,
         1: enable. "
   ::= { sm16tat2saIgmpConfigurationEntry 3 }

sm16tat2saIgmpConfThrottling OBJECT-TYPE
   SYNTAX Integer32(0..10)
   MAX-ACCESS read-write
   STATUS current
   DESCRIPTION
       " Configure IPMC throttling numbers .
         0: unlimited. "
   ::= { sm16tat2saIgmpConfigurationEntry 4 }

sm16tat2saIgmpConfProfile OBJECT-TYPE
   SYNTAX DisplayString
   MAX-ACCESS read-write
   STATUS current
   DESCRIPTION
       " Configure IPMC Profile . "
   ::= { sm16tat2saIgmpConfigurationEntry 5 }

sm16tat2saIgmpVlanConfiguration OBJECT IDENTIFIER ::= { sm16tat2saIpmc 2 }

sm16tat2saIgmpVlanConfigTable OBJECT-TYPE
   SYNTAX SEQUENCE OF SM16TAT2SAIgmpVlanConfigEntry
   MAX-ACCESS not-accessible
   STATUS current
   DESCRIPTION
       " "
   ::= { sm16tat2saIgmpVlanConfiguration 1 }

sm16tat2saIgmpVlanConfigEntry OBJECT-TYPE
   SYNTAX SM16TAT2SAIgmpVlanConfigEntry
   MAX-ACCESS not-accessible
   STATUS current
   DESCRIPTION
       " "
   INDEX { sm16tat2saIgmpVlanIndex }
   ::= { sm16tat2saIgmpVlanConfigTable 1 }

SM16TAT2SAIgmpVlanConfigEntry ::= SEQUENCE {
   sm16tat2saIgmpVlanIndex Integer32,
   sm16tat2saIgmpVlanVid Integer32,
   sm16tat2saIgmpVlanSnoopingMode INTEGER,
   sm16tat2saIgmpVlanQuerier INTEGER,
   sm16tat2saIgmpVlanCompatibility INTEGER,
   sm16tat2saIgmpVlanRV Integer32,
   sm16tat2saIgmpVlanQI Integer32,
   sm16tat2saIgmpVlanQRI Integer32,
   sm16tat2saIgmpVlanLLQI Integer32,
   sm16tat2saIgmpVlanURI Integer32,
   sm16tat2saIgmpVlanRowStatus RowStatus
}

sm16tat2saIgmpVlanIndex OBJECT-TYPE
   SYNTAX Integer32 (1..32)
   MAX-ACCESS not-accessible
   STATUS current
   DESCRIPTION
       "The Igmp Vlan Config Index."
   ::= { sm16tat2saIgmpVlanConfigEntry 1 }

sm16tat2saIgmpVlanVid OBJECT-TYPE
   SYNTAX Integer32 (1..4094)
   MAX-ACCESS read-create
   STATUS current
   DESCRIPTION
       "Igmp vlan config's vid.
        range: 1-4094. "
   ::= { sm16tat2saIgmpVlanConfigEntry 2 }

sm16tat2saIgmpVlanSnoopingMode OBJECT-TYPE
   SYNTAX INTEGER { disable(0), enable(1) }
   MAX-ACCESS read-create
   STATUS current
   DESCRIPTION
       "Igmp vlan config's snooping mode.
        0: disable,
        1: enable. "
   ::= { sm16tat2saIgmpVlanConfigEntry 3 }

sm16tat2saIgmpVlanQuerier OBJECT-TYPE
   SYNTAX INTEGER { disable(0), enable(1) }
   MAX-ACCESS read-create
   STATUS current
   DESCRIPTION
       "Igmp vlan config's querier mode.
        0: disable,
        1: enable. "
   ::= { sm16tat2saIgmpVlanConfigEntry 4 }

sm16tat2saIgmpVlanCompatibility OBJECT-TYPE
   SYNTAX INTEGER { igmpauto(0), forcedigmpv1(1), forcedigmpv2(2), forcedigmpv3(3) }
   MAX-ACCESS read-create
   STATUS current
   DESCRIPTION
       "Igmp vlan config's Compatibility.
        0: IGMP-Auto,
        1: Forced IGMPv1,
        2: Forced IGMPv2,
        3: Forced IGMPv3. "
   ::= { sm16tat2saIgmpVlanConfigEntry 5 }

sm16tat2saIgmpVlanRV OBJECT-TYPE
   SYNTAX Integer32 (1..255)
   MAX-ACCESS read-create
   STATUS current
   DESCRIPTION
       "Igmp vlan config's RV.
        default: 2, range: 1-255. "
   ::= { sm16tat2saIgmpVlanConfigEntry 6 }

sm16tat2saIgmpVlanQI OBJECT-TYPE
   SYNTAX Integer32 (1..31744)
   MAX-ACCESS read-create
   STATUS current
   DESCRIPTION
       "Igmp vlan config's QI.
        default: 125, range: 1-31744. "
   ::= { sm16tat2saIgmpVlanConfigEntry 7 }

sm16tat2saIgmpVlanQRI OBJECT-TYPE
   SYNTAX Integer32 (0..31744)
   MAX-ACCESS read-create
   STATUS current
   DESCRIPTION
       "Igmp vlan config's QRI.
        default: 100, range: 0-31744. "
   ::= { sm16tat2saIgmpVlanConfigEntry 8 }

sm16tat2saIgmpVlanLLQI OBJECT-TYPE
   SYNTAX Integer32 (0..31744)
   MAX-ACCESS read-create
   STATUS current
   DESCRIPTION
       "Igmp vlan config's LLQI.
        default: 10, range: 0-31744. "
   ::= { sm16tat2saIgmpVlanConfigEntry 9 }

sm16tat2saIgmpVlanURI OBJECT-TYPE
   SYNTAX Integer32 (0..31744)
   MAX-ACCESS read-create
   STATUS current
   DESCRIPTION
       "Igmp vlan config's URI.
        default: 1, range: 0-31744. "
   ::= { sm16tat2saIgmpVlanConfigEntry 10 }

sm16tat2saIgmpVlanRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm16tat2saIgmpVlanConfigEntry 11 }

sm16tat2saIgmpVlanStatus OBJECT IDENTIFIER ::= { sm16tat2saIpmc 3 }

sm16tat2saIgmpVlanStatusTable OBJECT-TYPE
   SYNTAX SEQUENCE OF SM16TAT2SAIgmpVlanStatusEntry
   MAX-ACCESS not-accessible
   STATUS current
   DESCRIPTION
       " "
   ::= { sm16tat2saIgmpVlanStatus 1 }

sm16tat2saIgmpVlanStatusEntry OBJECT-TYPE
   SYNTAX SM16TAT2SAIgmpVlanStatusEntry
   MAX-ACCESS not-accessible
   STATUS current
   DESCRIPTION
       " "
   INDEX { sm16tat2saIgmpVlanStatusIndex }
   ::= { sm16tat2saIgmpVlanStatusTable 1 }

SM16TAT2SAIgmpVlanStatusEntry ::= SEQUENCE {
   sm16tat2saIgmpVlanStatusIndex Integer32,
   sm16tat2saIgmpVlanStatusVid Integer32,
   sm16tat2saIgmpVlanStatusQuerierVersion DisplayString,
   sm16tat2saIgmpVlanStatusHostVersion DisplayString,
   sm16tat2saIgmpVlanStatusQuerierStatus DisplayString,
   sm16tat2saIgmpVlanStatusQuerierTransmitted Integer32,
   sm16tat2saIgmpVlanStatusQuerierReceived Integer32,
   sm16tat2saIgmpVlanStatusV1ReportsReceived Integer32,
   sm16tat2saIgmpVlanStatusV2ReportsReceived Integer32,
   sm16tat2saIgmpVlanStatusV3ReportsReceived Integer32,
   sm16tat2saIgmpVlanStatusV2LeavesReceived Integer32
}

sm16tat2saIgmpVlanStatusIndex OBJECT-TYPE
   SYNTAX Integer32 (1..64)
   MAX-ACCESS not-accessible
   STATUS current
   DESCRIPTION
       "The Igmp Vlan Status Index."
   ::= { sm16tat2saIgmpVlanStatusEntry 1 }

sm16tat2saIgmpVlanStatusVid OBJECT-TYPE
   SYNTAX Integer32 (1..4094)
   MAX-ACCESS read-only
   STATUS current
   DESCRIPTION
       "Igmp vlan status's vid.
        range: 1-4094. "
   ::= { sm16tat2saIgmpVlanStatusEntry 2 }

sm16tat2saIgmpVlanStatusQuerierVersion OBJECT-TYPE
   SYNTAX DisplayString
   MAX-ACCESS read-only
   STATUS current
   DESCRIPTION
       "Igmp vlan status's querier version. "
   ::= { sm16tat2saIgmpVlanStatusEntry 3 }

sm16tat2saIgmpVlanStatusHostVersion OBJECT-TYPE
   SYNTAX DisplayString
   MAX-ACCESS read-only
   STATUS current
   DESCRIPTION
       "Igmp vlan status's host version. "
   ::= { sm16tat2saIgmpVlanStatusEntry 4 }

sm16tat2saIgmpVlanStatusQuerierStatus OBJECT-TYPE
   SYNTAX DisplayString
   MAX-ACCESS read-only
   STATUS current
   DESCRIPTION
       "Igmp vlan status's querier status. "
   ::= { sm16tat2saIgmpVlanStatusEntry 5 }

sm16tat2saIgmpVlanStatusQuerierTransmitted OBJECT-TYPE
   SYNTAX Integer32 (0..2147483647)
   MAX-ACCESS read-only
   STATUS current
   DESCRIPTION
       "Igmp vlan status's querier transmitted packets. "
   ::= { sm16tat2saIgmpVlanStatusEntry 6 }

sm16tat2saIgmpVlanStatusQuerierReceived OBJECT-TYPE
   SYNTAX Integer32 (0..2147483647)
   MAX-ACCESS read-only
   STATUS current
   DESCRIPTION
       "Igmp vlan status's querier received packets. "
   ::= { sm16tat2saIgmpVlanStatusEntry 7 }

sm16tat2saIgmpVlanStatusV1ReportsReceived OBJECT-TYPE
   SYNTAX Integer32 (0..2147483647)
   MAX-ACCESS read-only
   STATUS current
   DESCRIPTION
       "Igmp vlan status's v1 report received packets. "
   ::= { sm16tat2saIgmpVlanStatusEntry 8 }

sm16tat2saIgmpVlanStatusV2ReportsReceived OBJECT-TYPE
   SYNTAX Integer32 (0..2147483647)
   MAX-ACCESS read-only
   STATUS current
   DESCRIPTION
       "Igmp vlan status's v2 report received packets. "
   ::= { sm16tat2saIgmpVlanStatusEntry 9 }

sm16tat2saIgmpVlanStatusV3ReportsReceived OBJECT-TYPE
   SYNTAX Integer32 (0..2147483647)
   MAX-ACCESS read-only
   STATUS current
   DESCRIPTION
       "Igmp vlan status's V3 report received packets. "
   ::= { sm16tat2saIgmpVlanStatusEntry 10 }

sm16tat2saIgmpVlanStatusV2LeavesReceived OBJECT-TYPE
   SYNTAX Integer32 (0..2147483647)
   MAX-ACCESS read-only
   STATUS current
   DESCRIPTION
       "Igmp vlan status's v2 leave received packets. "
   ::= { sm16tat2saIgmpVlanStatusEntry 11 }

sm16tat2saIgmpRouterPortStatusTable OBJECT-TYPE
   SYNTAX SEQUENCE OF SM16TAT2SAIgmpRouterPortStatusEntry
   MAX-ACCESS not-accessible
   STATUS current
   DESCRIPTION
       " "
   ::= { sm16tat2saIgmpVlanStatus 2 }

sm16tat2saIgmpRouterPortStatusEntry OBJECT-TYPE
   SYNTAX SM16TAT2SAIgmpRouterPortStatusEntry
   MAX-ACCESS not-accessible
   STATUS current
   DESCRIPTION
       " "
   INDEX { sm16tat2saIgmpRouterPort }
   ::= { sm16tat2saIgmpRouterPortStatusTable 1 }

SM16TAT2SAIgmpRouterPortStatusEntry ::= SEQUENCE {
   sm16tat2saIgmpRouterPort Integer32,
   sm16tat2saIgmpRouterPortStatus DisplayString
}

sm16tat2saIgmpRouterPort OBJECT-TYPE
   SYNTAX Integer32(1..255)
   MAX-ACCESS not-accessible
   STATUS current
   DESCRIPTION
       " port, range : 1 - port number. "
   ::= { sm16tat2saIgmpRouterPortStatusEntry 1 }

sm16tat2saIgmpRouterPortStatus OBJECT-TYPE
   SYNTAX DisplayString
   MAX-ACCESS read-only
   STATUS current
   DESCRIPTION
       " Router Port Status. "
   ::= { sm16tat2saIgmpRouterPortStatusEntry 2 }

sm16tat2saIgmpGroupsInformation OBJECT IDENTIFIER ::= { sm16tat2saIpmc 4 }

sm16tat2saIgmpGroupsTable OBJECT-TYPE
   SYNTAX SEQUENCE OF SM16TAT2SAIgmpGroupsEntry
   MAX-ACCESS not-accessible
   STATUS current
   DESCRIPTION
       " "
   ::= { sm16tat2saIgmpGroupsInformation 1 }

sm16tat2saIgmpGroupsEntry OBJECT-TYPE
   SYNTAX SM16TAT2SAIgmpGroupsEntry
   MAX-ACCESS not-accessible
   STATUS current
   DESCRIPTION
       " "
   INDEX { sm16tat2saIgmpGroupsIndex }
   ::= { sm16tat2saIgmpGroupsTable 1 }

SM16TAT2SAIgmpGroupsEntry ::= SEQUENCE {
   sm16tat2saIgmpGroupsIndex Integer32,
   sm16tat2saIgmpGroupsVid Integer32,
   sm16tat2saIgmpGroupsAddress IpAddress,
   sm16tat2saIgmpGroupsPort DisplayString
}

sm16tat2saIgmpGroupsIndex OBJECT-TYPE
   SYNTAX Integer32 (1..4094)
   MAX-ACCESS not-accessible
   STATUS current
   DESCRIPTION
       "The Igmp Group Index."
   ::= { sm16tat2saIgmpGroupsEntry 1 }

sm16tat2saIgmpGroupsVid OBJECT-TYPE
   SYNTAX Integer32 (1..4094)
   MAX-ACCESS read-only
   STATUS current
   DESCRIPTION
       "Igmp group's vid.
        range: 1-4094. "
   ::= { sm16tat2saIgmpGroupsEntry 2 }

sm16tat2saIgmpGroupsAddress OBJECT-TYPE
   SYNTAX IpAddress
   MAX-ACCESS read-only
   STATUS current
   DESCRIPTION
       "Igmp group's address. "
   ::= { sm16tat2saIgmpGroupsEntry 3 }

sm16tat2saIgmpGroupsPort OBJECT-TYPE
   SYNTAX DisplayString
   MAX-ACCESS read-only
   STATUS current
   DESCRIPTION
       "Igmp group's port member. "
   ::= { sm16tat2saIgmpGroupsEntry 4 }

sm16tat2saIgmpSFMInformation OBJECT IDENTIFIER ::= { sm16tat2saIpmc 5 }

sm16tat2saIgmpSFMTable OBJECT-TYPE
   SYNTAX SEQUENCE OF SM16TAT2SAIgmpSFMEntry
   MAX-ACCESS not-accessible
   STATUS current
   DESCRIPTION
       " "
   ::= { sm16tat2saIgmpSFMInformation 1 }

sm16tat2saIgmpSFMEntry OBJECT-TYPE
   SYNTAX SM16TAT2SAIgmpSFMEntry
   MAX-ACCESS not-accessible
   STATUS current
   DESCRIPTION
       " "
   INDEX { sm16tat2saIgmpSFMIndex }
   ::= { sm16tat2saIgmpSFMTable 1 }

SM16TAT2SAIgmpSFMEntry ::= SEQUENCE {
   sm16tat2saIgmpSFMIndex Integer32,
   sm16tat2saIgmpSFMVid Integer32,
   sm16tat2saIgmpSFMAddress IpAddress,
   sm16tat2saIgmpSFMPort Integer32,
   sm16tat2saIgmpSFMMode DisplayString,
   sm16tat2saIgmpSFMSourceAddress IpAddress,
   sm16tat2saIgmpSFMType DisplayString
}

sm16tat2saIgmpSFMIndex OBJECT-TYPE
   SYNTAX Integer32 (1..4094)
   MAX-ACCESS not-accessible
   STATUS current
   DESCRIPTION
       "The Igmp SFM Index."
   ::= { sm16tat2saIgmpSFMEntry 1 }

sm16tat2saIgmpSFMVid OBJECT-TYPE
   SYNTAX Integer32 (1..4094)
   MAX-ACCESS read-only
   STATUS current
   DESCRIPTION
       "Igmp SFM's vid.
        range: 1-4094. "
   ::= { sm16tat2saIgmpSFMEntry 2 }

sm16tat2saIgmpSFMAddress OBJECT-TYPE
   SYNTAX IpAddress
   MAX-ACCESS read-only
   STATUS current
   DESCRIPTION
       "Igmp SFM's group address. "
   ::= { sm16tat2saIgmpSFMEntry 3 }

sm16tat2saIgmpSFMPort OBJECT-TYPE
   SYNTAX Integer32 (1..100)
   MAX-ACCESS read-only
   STATUS current
   DESCRIPTION
       "Igmp group's port member. "
   ::= { sm16tat2saIgmpSFMEntry 4 }

sm16tat2saIgmpSFMMode OBJECT-TYPE
   SYNTAX DisplayString
   MAX-ACCESS read-only
   STATUS current
   DESCRIPTION
       "Igmp SFM's mode. "
   ::= { sm16tat2saIgmpSFMEntry 5 }

sm16tat2saIgmpSFMSourceAddress OBJECT-TYPE
   SYNTAX IpAddress
   MAX-ACCESS read-only
   STATUS current
   DESCRIPTION
       "Igmp SFM's source address. "
   ::= { sm16tat2saIgmpSFMEntry 6 }

sm16tat2saIgmpSFMType OBJECT-TYPE
   SYNTAX DisplayString
   MAX-ACCESS read-only
   STATUS current
   DESCRIPTION
       "Igmp SFM's type. "
   ::= { sm16tat2saIgmpSFMEntry 7 }

sm16tat2saMldConfig OBJECT IDENTIFIER ::= { sm16tat2saIpmc 6 }

sm16tat2saMldSnoopingEnable OBJECT-TYPE
   SYNTAX INTEGER { disable(0), enable(1) }
   MAX-ACCESS read-write
   STATUS current
   DESCRIPTION
       "Configure igmp mode.
        0: disable,
        1: enable. "
   ::= { sm16tat2saMldConfig 1 }

sm16tat2saMldUnkownFlooding OBJECT-TYPE
   SYNTAX INTEGER { disable(0), enable(1) }
   MAX-ACCESS read-write
   STATUS current
   DESCRIPTION
       "Configure Unregistered IPMCv6  Flooding Enabled.
        0: disable,
        1: enable. "
   ::= { sm16tat2saMldConfig 2 }

sm16tat2saMldSsmRangeAddress OBJECT-TYPE
   SYNTAX DisplayString
   MAX-ACCESS read-write
   STATUS current
   DESCRIPTION
       " Configure MLD SSM Range Address. "
   ::= { sm16tat2saMldConfig 3 }

sm16tat2saMldSsmRangeLen OBJECT-TYPE
   SYNTAX Integer32 (8..128)
   MAX-ACCESS read-write
   STATUS current
   DESCRIPTION
       "Configure MLD SSM Range Length.
        range: 8 - 128. "
   ::= { sm16tat2saMldConfig 4 }

sm16tat2saMldProxyEnable OBJECT-TYPE
   SYNTAX INTEGER { disable(0), enable(1) }
   MAX-ACCESS read-write
   STATUS current
   DESCRIPTION
       "Configure MLD Proxy Enabled.
        0: disable,
        1: enable. "
   ::= { sm16tat2saMldConfig 5 }

sm16tat2saMldConfigurationTable OBJECT-TYPE
   SYNTAX SEQUENCE OF SM16TAT2SAMldConfigurationEntry
   MAX-ACCESS not-accessible
   STATUS current
   DESCRIPTION
       " Show MLD port configurations. "
   ::= { sm16tat2saMldConfig 6 }

sm16tat2saMldConfigurationEntry OBJECT-TYPE
   SYNTAX SM16TAT2SAMldConfigurationEntry
   MAX-ACCESS not-accessible
   STATUS current
   DESCRIPTION
       " "
   INDEX { sm16tat2saMldConfPort }
   ::= { sm16tat2saMldConfigurationTable 1 }

SM16TAT2SAMldConfigurationEntry ::= SEQUENCE {
   sm16tat2saMldConfPort Integer32,
   sm16tat2saMldConfRouterPort INTEGER,
   sm16tat2saMldConfFastLeave INTEGER,
   sm16tat2saMldConfThrottling Integer32,
   sm16tat2saMldConfProfile DisplayString
}

sm16tat2saMldConfPort OBJECT-TYPE
   SYNTAX Integer32(1..255)
   MAX-ACCESS not-accessible
   STATUS current
   DESCRIPTION
       " port, range : 1 - port number. "
   ::= { sm16tat2saMldConfigurationEntry 1 }

sm16tat2saMldConfRouterPort OBJECT-TYPE
   SYNTAX INTEGER { disable(0), enable(1) }
   MAX-ACCESS read-write
   STATUS current
   DESCRIPTION
       " Configure IPMC router port mode.
         0: disable,
         1: enable. "
   ::= { sm16tat2saMldConfigurationEntry 2 }

sm16tat2saMldConfFastLeave OBJECT-TYPE
   SYNTAX INTEGER { disable(0), enable(1) }
   MAX-ACCESS read-write
   STATUS current
   DESCRIPTION
       " Configure IPMC fast leave mode.
         0: disable,
         1: enable. "
   ::= { sm16tat2saMldConfigurationEntry 3 }

sm16tat2saMldConfThrottling OBJECT-TYPE
   SYNTAX Integer32(0..10)
   MAX-ACCESS read-write
   STATUS current
   DESCRIPTION
       " Configure MLD throttling numbers .
         0: unlimited. "
   ::= { sm16tat2saMldConfigurationEntry 4 }

sm16tat2saMldConfProfile OBJECT-TYPE
   SYNTAX DisplayString
   MAX-ACCESS read-write
   STATUS current
   DESCRIPTION
       " Configure MLD Profile . "
   ::= { sm16tat2saMldConfigurationEntry 5 }

sm16tat2saMldVlanConfiguration OBJECT IDENTIFIER ::= { sm16tat2saIpmc 7 }

sm16tat2saMldVlanConfigTable OBJECT-TYPE
   SYNTAX SEQUENCE OF SM16TAT2SAMldVlanConfigEntry
   MAX-ACCESS not-accessible
   STATUS current
   DESCRIPTION
       " "
   ::= { sm16tat2saMldVlanConfiguration 1 }

sm16tat2saMldVlanConfigEntry OBJECT-TYPE
   SYNTAX SM16TAT2SAMldVlanConfigEntry
   MAX-ACCESS not-accessible
   STATUS current
   DESCRIPTION
       " "
   INDEX { sm16tat2saMldVlanIndex }
   ::= { sm16tat2saMldVlanConfigTable 1 }

SM16TAT2SAMldVlanConfigEntry ::= SEQUENCE {
   sm16tat2saMldVlanIndex Integer32,
   sm16tat2saMldVlanVid Integer32,
   sm16tat2saMldVlanSnoopingMode INTEGER,
   sm16tat2saMldVlanQuerier INTEGER,
   sm16tat2saMldVlanCompatibility INTEGER,
   sm16tat2saMldVlanRV Integer32,
   sm16tat2saMldVlanQI Integer32,
   sm16tat2saMldVlanQRI Integer32,
   sm16tat2saMldVlanLLQI Integer32,
   sm16tat2saMldVlanURI Integer32,
   sm16tat2saMldVlanRowStatus RowStatus
}

sm16tat2saMldVlanIndex OBJECT-TYPE
   SYNTAX Integer32 (1..32)
   MAX-ACCESS not-accessible
   STATUS current
   DESCRIPTION
       "The Mld Vlan Config Index."
   ::= { sm16tat2saMldVlanConfigEntry 1 }

sm16tat2saMldVlanVid OBJECT-TYPE
   SYNTAX Integer32 (1..4094)
   MAX-ACCESS read-create
   STATUS current
   DESCRIPTION
       "Mld vlan config's vid.
        range: 1-4094. "
   ::= { sm16tat2saMldVlanConfigEntry 2 }

sm16tat2saMldVlanSnoopingMode OBJECT-TYPE
   SYNTAX INTEGER { disable(0), enable(1) }
   MAX-ACCESS read-create
   STATUS current
   DESCRIPTION
       "Mld vlan config's snooping mode.
        0: disable,
        1: enable. "
   ::= { sm16tat2saMldVlanConfigEntry 3 }

sm16tat2saMldVlanQuerier OBJECT-TYPE
   SYNTAX INTEGER { disable(0), enable(1) }
   MAX-ACCESS read-create
   STATUS current
   DESCRIPTION
       "Mld vlan config's querier mode.
        0: disable,
        1: enable. "
   ::= { sm16tat2saMldVlanConfigEntry 4 }

sm16tat2saMldVlanCompatibility OBJECT-TYPE
   SYNTAX INTEGER { igmpauto(0), forcedigmpv1(1), forcedigmpv2(2), forcedigmpv3(3) }
   MAX-ACCESS read-create
   STATUS current
   DESCRIPTION
       "Mld vlan config's Compatibility.
        0: IGMP-Auto,
        1: Forced IGMPv1,
        2: Forced IGMPv2,
        3: Forced IGMPv3. "
   ::= { sm16tat2saMldVlanConfigEntry 5 }

sm16tat2saMldVlanRV OBJECT-TYPE
   SYNTAX Integer32 (1..255)
   MAX-ACCESS read-create
   STATUS current
   DESCRIPTION
       "Mld vlan config's RV.
        default: 2, range: 1-255. "
   ::= { sm16tat2saMldVlanConfigEntry 6 }

sm16tat2saMldVlanQI OBJECT-TYPE
   SYNTAX Integer32 (1..31744)
   MAX-ACCESS read-create
   STATUS current
   DESCRIPTION
       "Mld vlan config's QI.
        default: 125, range: 1-31744. "
   ::= { sm16tat2saMldVlanConfigEntry 7 }

sm16tat2saMldVlanQRI OBJECT-TYPE
   SYNTAX Integer32 (0..31744)
   MAX-ACCESS read-create
   STATUS current
   DESCRIPTION
       "Mld vlan config's QRI.
        default: 100, range: 0-31744. "
   ::= { sm16tat2saMldVlanConfigEntry 8 }

sm16tat2saMldVlanLLQI OBJECT-TYPE
   SYNTAX Integer32 (0..31744)
   MAX-ACCESS read-create
   STATUS current
   DESCRIPTION
       "Mld vlan config's LLQI.
        default: 10, range: 0-31744. "
   ::= { sm16tat2saMldVlanConfigEntry 9 }

sm16tat2saMldVlanURI OBJECT-TYPE
   SYNTAX Integer32 (0..31744)
   MAX-ACCESS read-create
   STATUS current
   DESCRIPTION
       "Mld vlan config's URI.
        default: 1, range: 0-31744. "
   ::= { sm16tat2saMldVlanConfigEntry 10 }

sm16tat2saMldVlanRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm16tat2saMldVlanConfigEntry 11 }

sm16tat2saMldVlanStatus OBJECT IDENTIFIER ::= { sm16tat2saIpmc 8 }

sm16tat2saMldVlanStatusTable OBJECT-TYPE
   SYNTAX SEQUENCE OF SM16TAT2SAMldVlanStatusEntry
   MAX-ACCESS not-accessible
   STATUS current
   DESCRIPTION
       " "
   ::= { sm16tat2saMldVlanStatus 1 }

sm16tat2saMldVlanStatusEntry OBJECT-TYPE
   SYNTAX SM16TAT2SAMldVlanStatusEntry
   MAX-ACCESS not-accessible
   STATUS current
   DESCRIPTION
       " "
   INDEX { sm16tat2saMldVlanStatusIndex }
   ::= { sm16tat2saMldVlanStatusTable 1 }

SM16TAT2SAMldVlanStatusEntry ::= SEQUENCE {
   sm16tat2saMldVlanStatusIndex Integer32,
   sm16tat2saMldVlanStatusVid Integer32,
   sm16tat2saMldVlanStatusQuerierVersion DisplayString,
   sm16tat2saMldVlanStatusHostVersion DisplayString,
   sm16tat2saMldVlanStatusQuerierStatus DisplayString,
   sm16tat2saMldVlanStatusQuerierTransmitted Integer32,
   sm16tat2saMldVlanStatusQuerierReceived Integer32,
   sm16tat2saMldVlanStatusV1ReportsReceived Integer32,
   sm16tat2saMldVlanStatusV2ReportsReceived Integer32,
   sm16tat2saMldVlanStatusV1LeavesReceived Integer32
}

sm16tat2saMldVlanStatusIndex OBJECT-TYPE
   SYNTAX Integer32 (1..64)
   MAX-ACCESS not-accessible
   STATUS current
   DESCRIPTION
       "The Mld Vlan Status Index."
   ::= { sm16tat2saMldVlanStatusEntry 1 }

sm16tat2saMldVlanStatusVid OBJECT-TYPE
   SYNTAX Integer32 (1..4094)
   MAX-ACCESS read-only
   STATUS current
   DESCRIPTION
       "Mld vlan status's vid.
        range: 1-4094. "
   ::= { sm16tat2saMldVlanStatusEntry 2 }

sm16tat2saMldVlanStatusQuerierVersion OBJECT-TYPE
   SYNTAX DisplayString
   MAX-ACCESS read-only
   STATUS current
   DESCRIPTION
       "Mld vlan status's querier version. "
   ::= { sm16tat2saMldVlanStatusEntry 3 }

sm16tat2saMldVlanStatusHostVersion OBJECT-TYPE
   SYNTAX DisplayString
   MAX-ACCESS read-only
   STATUS current
   DESCRIPTION
       "Mld vlan status's host version. "
   ::= { sm16tat2saMldVlanStatusEntry 4 }

sm16tat2saMldVlanStatusQuerierStatus OBJECT-TYPE
   SYNTAX DisplayString
   MAX-ACCESS read-only
   STATUS current
   DESCRIPTION
       "Mld vlan status's querier status. "
   ::= { sm16tat2saMldVlanStatusEntry 5 }

sm16tat2saMldVlanStatusQuerierTransmitted OBJECT-TYPE
   SYNTAX Integer32 (0..2147483647)
   MAX-ACCESS read-only
   STATUS current
   DESCRIPTION
       "Mld vlan status's querier transmitted packets. "
   ::= { sm16tat2saMldVlanStatusEntry 6 }

sm16tat2saMldVlanStatusQuerierReceived OBJECT-TYPE
   SYNTAX Integer32 (0..2147483647)
   MAX-ACCESS read-only
   STATUS current
   DESCRIPTION
       "Mld vlan status's querier received packets. "
   ::= { sm16tat2saMldVlanStatusEntry 7 }

sm16tat2saMldVlanStatusV1ReportsReceived OBJECT-TYPE
   SYNTAX Integer32 (0..2147483647)
   MAX-ACCESS read-only
   STATUS current
   DESCRIPTION
       "Mld vlan status's v1 report received packets. "
   ::= { sm16tat2saMldVlanStatusEntry 8 }

sm16tat2saMldVlanStatusV2ReportsReceived OBJECT-TYPE
   SYNTAX Integer32 (0..2147483647)
   MAX-ACCESS read-only
   STATUS current
   DESCRIPTION
       "Mld vlan status's v2 report received packets. "
   ::= { sm16tat2saMldVlanStatusEntry 9 }

sm16tat2saMldVlanStatusV1LeavesReceived OBJECT-TYPE
   SYNTAX Integer32 (0..2147483647)
   MAX-ACCESS read-only
   STATUS current
   DESCRIPTION
       "Mld vlan status's v2 leave received packets. "
   ::= { sm16tat2saMldVlanStatusEntry 10 }

sm16tat2saMldRouterPortStatusTable OBJECT-TYPE
   SYNTAX SEQUENCE OF SM16TAT2SAMldRouterPortStatusEntry
   MAX-ACCESS not-accessible
   STATUS current
   DESCRIPTION
       " "
   ::= { sm16tat2saMldVlanStatus 2 }

sm16tat2saMldRouterPortStatusEntry OBJECT-TYPE
   SYNTAX SM16TAT2SAMldRouterPortStatusEntry
   MAX-ACCESS not-accessible
   STATUS current
   DESCRIPTION
       " "
   INDEX { sm16tat2saMldRouterPort }
   ::= { sm16tat2saMldRouterPortStatusTable 1 }

SM16TAT2SAMldRouterPortStatusEntry ::= SEQUENCE {
   sm16tat2saMldRouterPort Integer32,
   sm16tat2saMldRouterPortStatus DisplayString
}

sm16tat2saMldRouterPort OBJECT-TYPE
   SYNTAX Integer32(1..255)
   MAX-ACCESS not-accessible
   STATUS current
   DESCRIPTION
       " port, range : 1 - port number. "
   ::= { sm16tat2saMldRouterPortStatusEntry 1 }

sm16tat2saMldRouterPortStatus OBJECT-TYPE
   SYNTAX DisplayString
   MAX-ACCESS read-only
   STATUS current
   DESCRIPTION
       " Router Port Status. "
   ::= { sm16tat2saMldRouterPortStatusEntry 2 }

sm16tat2saMldGroupsInformation OBJECT IDENTIFIER ::= { sm16tat2saIpmc 9 }

sm16tat2saMldGroupsTable OBJECT-TYPE
   SYNTAX SEQUENCE OF SM16TAT2SAMldGroupsEntry
   MAX-ACCESS not-accessible
   STATUS current
   DESCRIPTION
       " "
   ::= { sm16tat2saMldGroupsInformation 1 }

sm16tat2saMldGroupsEntry OBJECT-TYPE
   SYNTAX SM16TAT2SAMldGroupsEntry
   MAX-ACCESS not-accessible
   STATUS current
   DESCRIPTION
       " "
   INDEX { sm16tat2saMldGroupsIndex }
   ::= { sm16tat2saMldGroupsTable 1 }

SM16TAT2SAMldGroupsEntry ::= SEQUENCE {
   sm16tat2saMldGroupsIndex Integer32,
   sm16tat2saMldGroupsVid Integer32,
   sm16tat2saMldGroupsAddress DisplayString,
   sm16tat2saMldGroupsPort DisplayString
}

sm16tat2saMldGroupsIndex OBJECT-TYPE
   SYNTAX Integer32 (1..4094)
   MAX-ACCESS not-accessible
   STATUS current
   DESCRIPTION
       "The Mld Group Index."
   ::= { sm16tat2saMldGroupsEntry 1 }

sm16tat2saMldGroupsVid OBJECT-TYPE
   SYNTAX Integer32 (1..4094)
   MAX-ACCESS read-only
   STATUS current
   DESCRIPTION
       "Mld group's vid.
        range: 1-4094. "
   ::= { sm16tat2saMldGroupsEntry 2 }

sm16tat2saMldGroupsAddress OBJECT-TYPE
   SYNTAX DisplayString
   MAX-ACCESS read-only
   STATUS current
   DESCRIPTION
       "Mld group's address. "
   ::= { sm16tat2saMldGroupsEntry 3 }

sm16tat2saMldGroupsPort OBJECT-TYPE
   SYNTAX DisplayString
   MAX-ACCESS read-only
   STATUS current
   DESCRIPTION
       "Mld group's port member. "
   ::= { sm16tat2saMldGroupsEntry 4 }

sm16tat2saMldSFMInformation OBJECT IDENTIFIER ::= { sm16tat2saIpmc 10 }

sm16tat2saMldSFMTable OBJECT-TYPE
   SYNTAX SEQUENCE OF SM16TAT2SAMldSFMEntry
   MAX-ACCESS not-accessible
   STATUS current
   DESCRIPTION
       " "
   ::= { sm16tat2saMldSFMInformation 1 }

sm16tat2saMldSFMEntry OBJECT-TYPE
   SYNTAX SM16TAT2SAMldSFMEntry
   MAX-ACCESS not-accessible
   STATUS current
   DESCRIPTION
       " "
   INDEX { sm16tat2saMldSFMIndex }
   ::= { sm16tat2saMldSFMTable 1 }

SM16TAT2SAMldSFMEntry ::= SEQUENCE {
   sm16tat2saMldSFMIndex Integer32,
   sm16tat2saMldSFMVid Integer32,
   sm16tat2saMldSFMAddress DisplayString,
   sm16tat2saMldSFMPort Integer32,
   sm16tat2saMldSFMMode DisplayString,
   sm16tat2saMldSFMSourceAddress DisplayString,
   sm16tat2saMldSFMType DisplayString
}

sm16tat2saMldSFMIndex OBJECT-TYPE
   SYNTAX Integer32 (1..4094)
   MAX-ACCESS not-accessible
   STATUS current
   DESCRIPTION
       "The Mld SFM Index."
   ::= { sm16tat2saMldSFMEntry 1 }

sm16tat2saMldSFMVid OBJECT-TYPE
   SYNTAX Integer32 (1..4094)
   MAX-ACCESS read-only
   STATUS current
   DESCRIPTION
       "Mld SFM's vid.
        range: 1-4094. "
   ::= { sm16tat2saMldSFMEntry 2 }

sm16tat2saMldSFMAddress OBJECT-TYPE
   SYNTAX DisplayString
   MAX-ACCESS read-only
   STATUS current
   DESCRIPTION
       "Mld SFM's group address. "
   ::= { sm16tat2saMldSFMEntry 3 }

sm16tat2saMldSFMPort OBJECT-TYPE
   SYNTAX Integer32 (1..100)
   MAX-ACCESS read-only
   STATUS current
   DESCRIPTION
       "Mld group's port member. "
   ::= { sm16tat2saMldSFMEntry 4 }

sm16tat2saMldSFMMode OBJECT-TYPE
   SYNTAX DisplayString
   MAX-ACCESS read-only
   STATUS current
   DESCRIPTION
       "Mld SFM's mode. "
   ::= { sm16tat2saMldSFMEntry 5 }

sm16tat2saMldSFMSourceAddress OBJECT-TYPE
   SYNTAX DisplayString
   MAX-ACCESS read-only
   STATUS current
   DESCRIPTION
       "Mld SFM's source address. "
   ::= { sm16tat2saMldSFMEntry 6 }

sm16tat2saMldSFMType OBJECT-TYPE
   SYNTAX DisplayString
   MAX-ACCESS read-only
   STATUS current
   DESCRIPTION
       "Mld SFM's type. "
   ::= { sm16tat2saMldSFMEntry 7 }

sm16tat2saMulticastFilteringProfile OBJECT IDENTIFIER ::= { sm16tat2saIpmc 11 }

sm16tat2saMulticastProfileEnable OBJECT-TYPE
   SYNTAX INTEGER { disable(0), enable(1) }
   MAX-ACCESS read-write
   STATUS current
   DESCRIPTION
       "Configure profile mode.
        0: disable,
        1: enable. "
   ::= { sm16tat2saMulticastFilteringProfile 1 }

sm16tat2saMulticastProfileTable OBJECT-TYPE
   SYNTAX SEQUENCE OF SM16TAT2SAMulticastProfileEntry
   MAX-ACCESS not-accessible
   STATUS current
   DESCRIPTION
       "Multicast Profile Table. "
   ::= { sm16tat2saMulticastFilteringProfile 2 }

sm16tat2saMulticastProfileEntry OBJECT-TYPE
   SYNTAX SM16TAT2SAMulticastProfileEntry
   MAX-ACCESS not-accessible
   STATUS current
   DESCRIPTION
       " "
   INDEX { sm16tat2saMulticastProfileIndex }
   ::= { sm16tat2saMulticastProfileTable 1 }

SM16TAT2SAMulticastProfileEntry ::= SEQUENCE {
   sm16tat2saMulticastProfileIndex Integer32,
   sm16tat2saMulticastProfileName DisplayString,
   sm16tat2saMulticastProfileDescription DisplayString,
   sm16tat2saMulticastProfileRowStatus RowStatus
}

sm16tat2saMulticastProfileIndex OBJECT-TYPE
   SYNTAX Integer32(1..64)
   MAX-ACCESS not-accessible
   STATUS current
   DESCRIPTION
       " Multicast Profile Index. "
   ::= { sm16tat2saMulticastProfileEntry 1 }

sm16tat2saMulticastProfileName OBJECT-TYPE
   SYNTAX DisplayString
   MAX-ACCESS read-create
   STATUS current
   DESCRIPTION
       " Multicast Profile Name. "
   ::= { sm16tat2saMulticastProfileEntry 2 }

sm16tat2saMulticastProfileDescription OBJECT-TYPE
   SYNTAX DisplayString
   MAX-ACCESS read-create
   STATUS current
   DESCRIPTION
       " Multicast Profile Description. "
   ::= { sm16tat2saMulticastProfileEntry 3 }

sm16tat2saMulticastProfileRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm16tat2saMulticastProfileEntry 4 }

sm16tat2saFilteringAddressTable OBJECT-TYPE
   SYNTAX SEQUENCE OF SM16TAT2SAFilteringAddressEntry
   MAX-ACCESS not-accessible
   STATUS current
   DESCRIPTION
       " "
   ::= { sm16tat2saMulticastFilteringProfile 3 }

sm16tat2saFilteringAddressEntry OBJECT-TYPE
   SYNTAX SM16TAT2SAFilteringAddressEntry
   MAX-ACCESS not-accessible
   STATUS current
   DESCRIPTION
       " "
   INDEX { sm16tat2saFilteringAddressIndex }
   ::= { sm16tat2saFilteringAddressTable 1 }

SM16TAT2SAFilteringAddressEntry ::= SEQUENCE {
   sm16tat2saFilteringAddressIndex Integer32,
   sm16tat2saFilteringAddressEntryName DisplayString,
   sm16tat2saFilteringAddressStartAddress DisplayString,
   sm16tat2saFilteringAddressEndAddress DisplayString,
   sm16tat2saFilteringAddressRowStatus RowStatus
}

sm16tat2saFilteringAddressIndex OBJECT-TYPE
   SYNTAX Integer32 (1..32)
   MAX-ACCESS not-accessible
   STATUS current
   DESCRIPTION
       "Multicast Filtering Address Table Index. "
   ::= { sm16tat2saFilteringAddressEntry 1 }

sm16tat2saFilteringAddressEntryName OBJECT-TYPE
   SYNTAX DisplayString
   MAX-ACCESS read-create
   STATUS current
   DESCRIPTION
       "Multicast Filtering Address Table Name. "
   ::= { sm16tat2saFilteringAddressEntry 2 }

sm16tat2saFilteringAddressStartAddress OBJECT-TYPE
   SYNTAX DisplayString
   MAX-ACCESS read-create
   STATUS current
   DESCRIPTION
       "Multicast Filtering Address Table Start Address. "
   ::= { sm16tat2saFilteringAddressEntry 3 }

sm16tat2saFilteringAddressEndAddress OBJECT-TYPE
   SYNTAX DisplayString
   MAX-ACCESS read-create
   STATUS current
   DESCRIPTION
       "Multicast Filtering Address Table End Address. "
   ::= { sm16tat2saFilteringAddressEntry 4 }

sm16tat2saFilteringAddressRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm16tat2saFilteringAddressEntry 5 }

sm16tat2saMulticastProfileRuleTable OBJECT-TYPE
   SYNTAX SEQUENCE OF SM16TAT2SAMulticastProfileRuleEntry
   MAX-ACCESS not-accessible
   STATUS current
   DESCRIPTION
       " "
   ::= { sm16tat2saMulticastFilteringProfile 4 }

sm16tat2saMulticastProfileRuleEntry OBJECT-TYPE
   SYNTAX SM16TAT2SAMulticastProfileRuleEntry
   MAX-ACCESS not-accessible
   STATUS current
   DESCRIPTION
       " "
   INDEX { sm16tat2saMulticastProfileRuleIndex }
   ::= { sm16tat2saMulticastProfileRuleTable 1 }

SM16TAT2SAMulticastProfileRuleEntry ::= SEQUENCE {
   sm16tat2saMulticastProfileRuleIndex Integer32,
   sm16tat2saMulticastProfileRuleProfileName DisplayString,
   sm16tat2saMulticastProfileRuleEntryName DisplayString,
   sm16tat2saMulticastProfileRuleAction INTEGER,
   sm16tat2saMulticastProfileRuleLog INTEGER,
   sm16tat2saMulticastProfileRuleRowStatus RowStatus
}

sm16tat2saMulticastProfileRuleIndex OBJECT-TYPE
   SYNTAX Integer32 (1..32)
   MAX-ACCESS not-accessible
   STATUS current
   DESCRIPTION
       "Multicast Profile Rule Table Index. "
   ::= { sm16tat2saMulticastProfileRuleEntry 1 }

sm16tat2saMulticastProfileRuleProfileName OBJECT-TYPE
   SYNTAX DisplayString
   MAX-ACCESS read-create
   STATUS current
   DESCRIPTION
       "Multicast Profile Rule Table Profile Name. "
   ::= { sm16tat2saMulticastProfileRuleEntry 2 }

sm16tat2saMulticastProfileRuleEntryName OBJECT-TYPE
   SYNTAX DisplayString
   MAX-ACCESS read-create
   STATUS current
   DESCRIPTION
       "Multicast Profile Rule Table Entry Name. "
   ::= { sm16tat2saMulticastProfileRuleEntry 3 }

sm16tat2saMulticastProfileRuleAction OBJECT-TYPE
   SYNTAX INTEGER { deny(0), permit(1) }
   MAX-ACCESS read-create
   STATUS current
   DESCRIPTION
       "Multicast Profile Rule Table Action. "
   ::= { sm16tat2saMulticastProfileRuleEntry 4 }

sm16tat2saMulticastProfileRuleLog OBJECT-TYPE
   SYNTAX INTEGER { disable(0), enable(1) }
   MAX-ACCESS read-create
   STATUS current
   DESCRIPTION
       "Multicast Profile Rule Table Log. "
   ::= { sm16tat2saMulticastProfileRuleEntry 5 }

sm16tat2saMulticastProfileRuleRowStatus OBJECT-TYPE
   SYNTAX RowStatus
   MAX-ACCESS read-create
   STATUS current
   DESCRIPTION
       "This object indicates the status of this entry, and is
        used to create/delete entries. Any object in an entry of
        this table may be modified while the value of the
        corresponding instance of this object is active(1).
        notReady(3) and createAndGo(4) not supported."
   ::= { sm16tat2saMulticastProfileRuleEntry 6 }

-- *************************************************************
-- Start sm16tat2saSystemAccount group
-- *************************************************************
sm16tat2saConfigurationConformance OBJECT IDENTIFIER ::= { sm16tat2saConfiguration 200 }
sm16tat2saConfigurationCompliances OBJECT IDENTIFIER ::= { sm16tat2saConfigurationConformance 1 }
sm16tat2saConfigurationGroups OBJECT IDENTIFIER ::= { sm16tat2saConfigurationConformance 2 }

sm16tat2saPortGroup OBJECT-GROUP
    OBJECTS {
    --sm16tat2saPort
      --sm16tat2saPortConfigurationTable
        sm16tat2saPortConfPortMedia,
        sm16tat2saPortConfLink,
        sm16tat2saPortConfCurrentSpeed,
        sm16tat2saPortConfSpeed,
        sm16tat2saPortConfCurrentFlowControlRx,
        sm16tat2saPortConfCurrentFlowControlTx,
        sm16tat2saPortConfFlowControl,
        sm16tat2saPortConfDescription,

      --sm16tat2saSFPInfoTable
        sm16tat2saSFPInfoPort,
        sm16tat2saSFPConnectorType,
        sm16tat2saSFPFiberType,
        sm16tat2saSFPTxCentralWavelength,
        sm16tat2saSFPBitRate,
        sm16tat2saSFPVendorOUI,
        sm16tat2saSFPVendorName,
        sm16tat2saSFPVendorPN,
        sm16tat2saSFPVendorRev,
        sm16tat2saSFPVendorSN,
        sm16tat2saSFPDateCode,
        sm16tat2saSFPTemperature,
        sm16tat2saSFPVcc,
        sm16tat2saSFPMon1Bias,
        sm16tat2saSFPMon2TxPWR,
        sm16tat2saSFPMon3RxPWR,

      --sm16tat2saPortEnergyEfficientTable
        sm16tat2saPortEnergyEfficientMode

        ,sm16tat2saPortMaximumFrameSize

    }
    STATUS current
    DESCRIPTION
        "The collection of objects which are used to
        indicate port information."
    ::= { sm16tat2saConfigurationGroups 1 }

sm16tat2saEventConfigGroup OBJECT-GROUP
    OBJECTS {
    --sm16tat2saEventConfig
      --sm16tat2saEventConfigTable
        sm16tat2saEventConfigGroupName,
        sm16tat2saEventConfigSeverityLevel,
        sm16tat2saEventConfigSyslog,
        sm16tat2saEventConfigTrap,
        sm16tat2saEventConfigSMTP
    }
    STATUS current
    DESCRIPTION
        "The collection of objects which are used to
        indicate event config information."
    ::= { sm16tat2saConfigurationGroups 7 }

sm16tat2saSMTPGroup OBJECT-GROUP
    OBJECTS {
    --sm16tat2saSMTP
        sm16tat2saSMTPMailServer,
        sm16tat2saSMTPUserName,
        sm16tat2saSMTPPassword,
        sm16tat2saSMTPSender,
        sm16tat2saSMTPReturnPath,
        sm16tat2saSMTPEmailAddress1,
        sm16tat2saSMTPEmailAddress2,
        sm16tat2saSMTPEmailAddress3,
        sm16tat2saSMTPEmailAddress4,
        sm16tat2saSMTPEmailAddress5,
        sm16tat2saSMTPEmailAddress6
    }
    STATUS current
    DESCRIPTION
        "The collection of objects which are used to
        indicate event config information."
    ::= { sm16tat2saConfigurationGroups 8 }

sm16tat2saQosConfGroup OBJECT-GROUP
    OBJECTS {
    --sm16tat2saQosConf
      --sm16tat2saQosGobalSettings
        sm16tat2saQosGobalSettingsTrustMode,

      --sm16tat2saQosPortSettings
        --sm16tat2saQosPortSettingsTable
        sm16tat2saQosPortSettingsMode,
        sm16tat2saQosPortSettingsDefaultCoS,
        sm16tat2saQosPortSettingsSourceCoS,
        sm16tat2saQosPortSettingsRemarkCoS,
        sm16tat2saQosPortSettingsRemarkDSCP,
        sm16tat2saQosPortSettingsRemarkIPPrecedence,

      --sm16tat2saQosPortPolicing
        --sm16tat2saQosPortPolicingTable
        sm16tat2saQosPortPolicingEnabled,
        sm16tat2saQosPortPolicingRate,

      --sm16tat2saQosPortShaper
        --sm16tat2saQosQueueShaperTable
        sm16tat2saQosQueueShaperEnabled,
        sm16tat2saQosQueueShaperRate,
        --sm16tat2saQosPortShaperTable
        sm16tat2saQosPortShaperEnabled,
        sm16tat2saQosPortShaperRate,

      --sm16tat2saQosStormControl
        --sm16tat2saQosStormControlTable
        sm16tat2saQosStormControlBroadcastEnabled,
        sm16tat2saQosStormControlBraoadcastRate,
        sm16tat2saQosStormControlUnknownMulticastEnabled,
        sm16tat2saQosStormControlUnknownMulticastRate,
        sm16tat2saQosStormControlUnknownUnicastEnabled,
        sm16tat2saQosStormControlUnknownUnicastRate,

      --sm16tat2saQosPortScheduler
        --sm16tat2saQosPortSchedulerTable
        sm16tat2saQosSchedulerMode,
        sm16tat2saQosSchedulerWeight,

      --sm16tat2saQosCoS8021pMapping
        --sm16tat2saQosCoS8021pMappingTable
        sm16tat2saQosCoS8021pMappingQueueID,

      --sm16tat2saQosCoS8021pRemarking
        --sm16tat2saQosCoS8021pRemarkingTable
        sm16tat2saQosCoS8021pRemarkingCoS8021p,

      --sm16tat2saQosIPPrecedenceMapping
        --sm16tat2saQosIPPrecedenceMappingTable
        sm16tat2saQosIPPrecedenceMappingQueueID,

      --sm16tat2saQosIPPrecedenceRemarking
        --sm16tat2saQosIPPrecedenceRemarkingTable
        sm16tat2saQosIPPrecedenceRemarkingIPPrecedence,

      --sm16tat2saQosDSCPMapping
        --sm16tat2saQosDSCPMappingTable
        sm16tat2saQosDSCPMappingQueueID,

      --sm16tat2saQosDSCPRemarking
        --sm16tat2saQosDSCPRemarkingTable
        sm16tat2saQosDSCPRemarkingDSCP
    }
    STATUS current
    DESCRIPTION
        "The collection of objects which are used to
        indicate qos config information."
    ::= { sm16tat2saConfigurationGroups 10 }

sm16tat2saLoopProtectionGroup OBJECT-GROUP
    OBJECTS {
    --sm16tat2saLoopProtection
      --sm16tat2saLoopProtectionConfig
        sm16tat2saLoopProtectionGlobalEnable,
        sm16tat2saLoopProtectionTranmisstionTime,
        sm16tat2saLoopProtectionShutdownTime,

        --sm16tat2saLoopProtectionConfigurationTable
        sm16tat2saLoopProtectionConfEnable,
        sm16tat2saLoopProtectionConfAction,
        sm16tat2saLoopProtectionConfTxmode,

        --sm16tat2saLoopProtectionStatusTable
        sm16tat2saLoopProtectionStatusLoops,
        sm16tat2saLoopProtectionStatusStatus,
        sm16tat2saLoopProtectionStatusLoop,
        sm16tat2saLoopProtectionStatusTimeLastLoop
    }
    STATUS current
    DESCRIPTION
        "The collection of objects which are used to
        indicate loop protection information."
    ::= { sm16tat2saConfigurationGroups 12 }

sm16tat2saPoeGroup OBJECT-GROUP
    OBJECTS {
    --sm16tat2saPoe
      --sm16tat2saPoeConfiguration
        sm16tat2saPrimaryPowerSupply,
        sm16tat2saCapacitorDetection,

        --sm16tat2saPoePortConfigTable
        sm16tat2saPoePortConfigPoeMode,
        sm16tat2saPoePortConfigPoeSchedule,
        sm16tat2saPoePortConfigPriority,
        sm16tat2saPoePortConfigMaximumPower,

        sm16tat2saPoEManagementMode,

        sm16tat2saPoEAlwaysOnPoE,

        --sm16tat2saPoeStatus
        --sm16tat2saPoeStatusTable
        sm16tat2saPoeStatusPDClass,
        sm16tat2saPoeStatusPowerAllocated,
        sm16tat2saPoeStatusPowerUsed,
        sm16tat2saPoeStatusCurrentUsed,
        sm16tat2saPoeStatusPriority,
        sm16tat2saPoeStatusPortStatus,

      --sm16tat2saPoePowerDelay
        --sm16tat2saPoePowerDelayTable
        sm16tat2saPoePowerDelayMode,
        sm16tat2saPoePowerDelayTime,

      --sm16tat2saPoeAutoCheck
        sm16tat2saPoeAutoCheckPingCheck,

        --sm16tat2saPoeAutoCheckTable
        sm16tat2saPoeAutoCheckPingIPAddress,
        sm16tat2saPoeAutoCheckStartupTime,
        sm16tat2saPoeAutoCheckIntervalTime,
        sm16tat2saPoeAutoCheckRetryTime,
        sm16tat2saPoeAutoCheckFailureLog,
        sm16tat2saPoeAutoCheckFailureAction,
        sm16tat2saPoeAutoCheckRebootTime,
        sm16tat2saPoeAutoCheckMaxRebootTimes,

      --sm16tat2saPoeSchedulingProfile
        --sm16tat2saPoeSchedulingNameTable
        sm16tat2saPoeSchedulingName,

        --sm16tat2saPoeSchedulingTimeTable
        sm16tat2saPoeSchedulingTimeStartTimeHour,
        sm16tat2saPoeSchedulingTimeStartTimeMinute,
        sm16tat2saPoeSchedulingTimeEndTimeHour,
        sm16tat2saPoeSchedulingTimeEndTimeMinute
    }
    STATUS current
    DESCRIPTION
        "The collection of objects which are used to
        indicate PoE information."
    ::= { sm16tat2saConfigurationGroups 13 }

sm16tat2saMstpGroupGroup OBJECT-GROUP
    OBJECTS {
    --sm16tat2saMstpGroup
      --sm16tat2saMstpMiscellaneousConfig
        sm16tat2saMstpMibGlobalEnable,
        sm16tat2saMstpMstiAddVlans
    }
    STATUS current
    DESCRIPTION
        "The collection of objects which are used to
        indicate mstp information."
    ::= { sm16tat2saConfigurationGroups 18 }

sm16tat2saLinkAggregationGroupGroup OBJECT-GROUP
    OBJECTS {
    --sm16tat2saLinkAggregationGroup
      --sm16tat2saLagMiscellaneousConfig,
        sm16tat2saLagTrafficDistributionMode,
        sm16tat2saLagLacpSystemPriority,

      --sm16tat2saLagPortTable
        sm16tat2saLagPortLacpAggAdminKey,
        sm16tat2saLagPortStaticAggAdminKey,
        sm16tat2saLagPortLacpActivity,
        sm16tat2saLagPortLacpTimeout,
        sm16tat2saLagPortAggregatorPort,
        sm16tat2saLagPortReadyState,

      --sm16tat2saLagAggregatorTable
        sm16tat2saLagPortAggregationMethod,
        sm16tat2saLagAggregatorMemberPorts,
        sm16tat2saLagAggregatorReadyPorts,

      --sm16tat2saLagLacpPortTable
        sm16tat2saLagLacpActorOperKey,
        sm16tat2saLagLacpPartnerPort,
        sm16tat2saLagLacpPartnerOperKey,
        sm16tat2saLagLacpActorSystemPriority,
        sm16tat2saLagLacpActorSystemID,
        sm16tat2saLagLacpPartnerSystemPriority,
        sm16tat2saLagLacpPartnerSystemID,
        sm16tat2saLagLacpPortReadyState
    }
    STATUS current
    DESCRIPTION
        "The collection of objects which are used to
        indicate link aggregation information."
    ::= { sm16tat2saConfigurationGroups 23 }

sm16tat2saIpmcGroup OBJECT-GROUP
    OBJECTS {
    --sm16tat2saIpmc
      --sm16tat2saIgmpConfig
        sm16tat2saIgmpSnoopingEnable,
        sm16tat2saIgmpUnkownFlooding,
        sm16tat2saIgmpSsmRangeAddress,
        sm16tat2saIgmpSsmRangeLen,
        sm16tat2saIgmpProxyEnable,

        --sm16tat2saIgmpConfigurationTable
        sm16tat2saIgmpConfRouterPort,
        sm16tat2saIgmpConfFastLeave,
        sm16tat2saIgmpConfThrottling,
        sm16tat2saIgmpConfProfile,

      --sm16tat2saIgmpVlanConfiguration
        --sm16tat2saIgmpVlanConfigTable
        sm16tat2saIgmpVlanVid,
        sm16tat2saIgmpVlanSnoopingMode,
        sm16tat2saIgmpVlanQuerier,
        sm16tat2saIgmpVlanCompatibility,
        sm16tat2saIgmpVlanRV,
        sm16tat2saIgmpVlanQI,
        sm16tat2saIgmpVlanQRI,
        sm16tat2saIgmpVlanLLQI,
        sm16tat2saIgmpVlanURI,
        sm16tat2saIgmpVlanRowStatus,

      --sm16tat2saIgmpVlanStatus
        --sm16tat2saIgmpVlanStatusTable
        sm16tat2saIgmpVlanStatusVid,
        sm16tat2saIgmpVlanStatusQuerierVersion,
        sm16tat2saIgmpVlanStatusHostVersion,
        sm16tat2saIgmpVlanStatusQuerierStatus,
        sm16tat2saIgmpVlanStatusQuerierTransmitted,
        sm16tat2saIgmpVlanStatusQuerierReceived,
        sm16tat2saIgmpVlanStatusV1ReportsReceived,
        sm16tat2saIgmpVlanStatusV2ReportsReceived,
        sm16tat2saIgmpVlanStatusV3ReportsReceived,
        sm16tat2saIgmpVlanStatusV2LeavesReceived,

        --sm16tat2saIgmpRouterPortStatusTable
        sm16tat2saIgmpRouterPortStatus,

      --sm16tat2saIgmpGroupsInformation
        --sm16tat2saIgmpGroupsTable
        sm16tat2saIgmpGroupsVid,
        sm16tat2saIgmpGroupsAddress,
        sm16tat2saIgmpGroupsPort,

      --sm16tat2saIgmpSFMInformation
        --sm16tat2saIgmpSFMTable
        sm16tat2saIgmpSFMVid,
        sm16tat2saIgmpSFMAddress,
        sm16tat2saIgmpSFMPort,
        sm16tat2saIgmpSFMMode,
        sm16tat2saIgmpSFMSourceAddress,
        sm16tat2saIgmpSFMType,

      --sm16tat2saMldConfig
        sm16tat2saMldSnoopingEnable,
        sm16tat2saMldUnkownFlooding,
        sm16tat2saMldSsmRangeAddress,
        sm16tat2saMldSsmRangeLen,
        sm16tat2saMldProxyEnable,

        --sm16tat2saMldConfigurationTable
        sm16tat2saMldConfRouterPort,
        sm16tat2saMldConfFastLeave,
        sm16tat2saMldConfThrottling,
        sm16tat2saMldConfProfile,

      --sm16tat2saMldVlanConfiguration
        --sm16tat2saMldVlanConfigTable
        sm16tat2saMldVlanVid,
        sm16tat2saMldVlanSnoopingMode,
        sm16tat2saMldVlanQuerier,
        sm16tat2saMldVlanCompatibility,
        sm16tat2saMldVlanRV,
        sm16tat2saMldVlanQI,
        sm16tat2saMldVlanQRI,
        sm16tat2saMldVlanLLQI,
        sm16tat2saMldVlanURI,
        sm16tat2saMldVlanRowStatus,

      --sm16tat2saMldVlanStatus
        --sm16tat2saMldVlanStatusTable
        sm16tat2saMldVlanStatusVid,
        sm16tat2saMldVlanStatusQuerierVersion,
        sm16tat2saMldVlanStatusHostVersion,
        sm16tat2saMldVlanStatusQuerierStatus,
        sm16tat2saMldVlanStatusQuerierTransmitted,
        sm16tat2saMldVlanStatusQuerierReceived,
        sm16tat2saMldVlanStatusV1ReportsReceived,
        sm16tat2saMldVlanStatusV2ReportsReceived,
        sm16tat2saMldVlanStatusV1LeavesReceived,

        --sm16tat2saMldRouterPortStatusTable
        sm16tat2saMldRouterPortStatus,

      --sm16tat2saMldGroupsInformation
        --sm16tat2saMldGroupsTable
        sm16tat2saMldGroupsVid,
        sm16tat2saMldGroupsAddress,
        sm16tat2saMldGroupsPort,

      --sm16tat2saMldSFMInformation
        --sm16tat2saMldSFMTable
        sm16tat2saMldSFMVid,
        sm16tat2saMldSFMAddress,
        sm16tat2saMldSFMPort,
        sm16tat2saMldSFMMode,
        sm16tat2saMldSFMSourceAddress,
        sm16tat2saMldSFMType,

      --sm16tat2saMulticastFilteringProfile
        sm16tat2saMulticastProfileEnable,

        --sm16tat2saMulticastProfileTable
        sm16tat2saMulticastProfileName,
        sm16tat2saMulticastProfileDescription,
        sm16tat2saMulticastProfileRowStatus,

        --sm16tat2saFilteringAddressTable
        sm16tat2saFilteringAddressEntryName,
        sm16tat2saFilteringAddressStartAddress,
        sm16tat2saFilteringAddressEndAddress,
        sm16tat2saFilteringAddressRowStatus,

        --sm16tat2saMulticastProfileRuleTable
        sm16tat2saMulticastProfileRuleProfileName,
        sm16tat2saMulticastProfileRuleEntryName,
        sm16tat2saMulticastProfileRuleAction,
        sm16tat2saMulticastProfileRuleLog,
        sm16tat2saMulticastProfileRuleRowStatus
    }
    STATUS current
    DESCRIPTION
        "The collection of objects which are used to
        indicate ipmc information."
    ::= { sm16tat2saConfigurationGroups 24 }

sm16tat2saConfigurationCompliance MODULE-COMPLIANCE
    STATUS current
    DESCRIPTION
        "The compliance statement for devices supporting configuration."
    MODULE
        MANDATORY-GROUPS {
            sm16tat2saPortGroup,
            sm16tat2saEventConfigGroup,
            sm16tat2saSMTPGroup,
            sm16tat2saQosConfGroup,
            sm16tat2saLoopProtectionGroup,
            sm16tat2saPoeGroup,
            sm16tat2saMstpGroupGroup,
            sm16tat2saLinkAggregationGroupGroup,
            sm16tat2saIpmcGroup
        }
    ::= { sm16tat2saConfigurationCompliances 1 }

-- ================================================================================================================

sm16tat2saSecurity OBJECT IDENTIFIER ::= { sm16tat2saProductId 3 }

-- *************************************************************
-- Start sm16tat2saIPSourceGuard group
-- *************************************************************
sm16tat2saIPSourceGuard OBJECT IDENTIFIER ::= { sm16tat2saSecurity 1 }

sm16tat2saIPSourceGuardMode OBJECT-TYPE
   SYNTAX INTEGER {off(0), on(1)}
   MAX-ACCESS read-write
   STATUS current
   DESCRIPTION
      "Enable the Global IP Source Guard or disable the Global IP Source Guard.
        default: 0,
        0: off(diable,
        1: on(enable)"
   ::= { sm16tat2saIPSourceGuard 1 }

sm16tat2saIPSourceGuardPortConfigTable OBJECT-TYPE
   SYNTAX SEQUENCE OF SM16TAT2SAIPSourceGuardPortConfigEntry
   MAX-ACCESS not-accessible
   STATUS current
   DESCRIPTION
      "The IP Source Guard Port Configuration Table.
       INDEX for this table is ifIndex which is equivalent to the panel port number."
   ::= { sm16tat2saIPSourceGuard 2 }

sm16tat2saIPSourceGuardPortConfigEntry OBJECT-TYPE
   SYNTAX SM16TAT2SAIPSourceGuardPortConfigEntry
   MAX-ACCESS not-accessible
   STATUS current
   DESCRIPTION
      "The IP Source Guard Port Configuration Entry."
   INDEX { ifIndex }
   ::= { sm16tat2saIPSourceGuardPortConfigTable 1 }

SM16TAT2SAIPSourceGuardPortConfigEntry ::= SEQUENCE {
   sm16tat2saIPSourceGuardPortConfigMode AdminMode,
   sm16tat2saIPSourceGuardPortMaxDynamicClients Integer32
}

sm16tat2saIPSourceGuardPortConfigMode OBJECT-TYPE
   SYNTAX AdminMode
   MAX-ACCESS read-write
   STATUS current
   DESCRIPTION
      "Specify IP Source Guard is enabled on which ports."
   ::= { sm16tat2saIPSourceGuardPortConfigEntry 1 }

sm16tat2saIPSourceGuardPortMaxDynamicClients OBJECT-TYPE
   SYNTAX Integer32(0..2|65535)
   MAX-ACCESS read-write
   STATUS current
   DESCRIPTION
      "Specify the maximum number of dynamic clients that can
       be learned on given port.
       default: 65535
       0~2: Max Dynamic clients
       65535:Unlimited "
   ::= { sm16tat2saIPSourceGuardPortConfigEntry 2 }

sm16tat2saIPSourceGuardStaticTable OBJECT-TYPE
   SYNTAX SEQUENCE OF SM16TAT2SAIPSourceGuardStaticEntry
   MAX-ACCESS not-accessible
   STATUS current
   DESCRIPTION
      "The IP Source Guard Static Table."
   ::= { sm16tat2saIPSourceGuard 3 }

sm16tat2saIPSourceGuardStaticEntry OBJECT-TYPE
   SYNTAX SM16TAT2SAIPSourceGuardStaticEntry
   MAX-ACCESS not-accessible
   STATUS current
   DESCRIPTION
      "The IP Source Guard Static Entry."
   INDEX { sm16tat2saIPSourceGuardStaticIndex }
   ::= { sm16tat2saIPSourceGuardStaticTable 1 }

SM16TAT2SAIPSourceGuardStaticEntry ::= SEQUENCE {
   sm16tat2saIPSourceGuardStaticIndex Integer32,
   sm16tat2saIPSourceGuardStaticPort Integer32,
   sm16tat2saIPSourceGuardStaticIPAddress DisplayString,
   sm16tat2saIPSourceGuardStaticMACAddress DisplayString,
   sm16tat2saIPSourceGuardStaticRowStatus RowStatus
}

sm16tat2saIPSourceGuardStaticIndex OBJECT-TYPE
   SYNTAX Integer32 (1..4095)
   MAX-ACCESS not-accessible
   STATUS current
   DESCRIPTION
      "The entry of table."
   ::= { sm16tat2saIPSourceGuardStaticEntry 1 }

sm16tat2saIPSourceGuardStaticPort OBJECT-TYPE
   SYNTAX Integer32 (1..26)
   MAX-ACCESS read-create
   STATUS current
   DESCRIPTION
      "The port number of table. range: 1 - port number."
   ::= { sm16tat2saIPSourceGuardStaticEntry 2 }

sm16tat2saIPSourceGuardStaticIPAddress OBJECT-TYPE
   SYNTAX DisplayString
   MAX-ACCESS read-create
   STATUS current
   DESCRIPTION
      "IP address allowed for doing IP source guard."
   ::= { sm16tat2saIPSourceGuardStaticEntry 3 }

sm16tat2saIPSourceGuardStaticMACAddress OBJECT-TYPE
   SYNTAX DisplayString
   MAX-ACCESS read-create
   STATUS current
   DESCRIPTION
      "Allowed Source MAC address, format: 0a 1b 2c 3d 4e 5f."
   ::= { sm16tat2saIPSourceGuardStaticEntry 4 }

sm16tat2saIPSourceGuardStaticRowStatus OBJECT-TYPE
   SYNTAX RowStatus
   MAX-ACCESS read-create
   STATUS current
   DESCRIPTION
      "This object indicates the status of this entry, and is
       used to create/delete entries. Any object in an entry of
       this table may be modified while the value of the
       corresponding instance of this object is active(1).
       createAndGo, notReady not supported."
   ::= { sm16tat2saIPSourceGuardStaticEntry 5 }

sm16tat2saIPSourceGuardDynamicTable OBJECT-TYPE
   SYNTAX SEQUENCE OF SM16TAT2SAIPSourceGuardDynamicEntry
   MAX-ACCESS not-accessible
   STATUS current
   DESCRIPTION
      "The IP Source Guard Dynamic Table."
   ::= { sm16tat2saIPSourceGuard 4 }

sm16tat2saIPSourceGuardDynamicEntry OBJECT-TYPE
   SYNTAX SM16TAT2SAIPSourceGuardDynamicEntry
   MAX-ACCESS not-accessible
   STATUS current
   DESCRIPTION
      "The IP Source Guard Dynamic Entry."
   INDEX { sm16tat2saIPSourceGuardDynamicIndex }
   ::= { sm16tat2saIPSourceGuardDynamicTable 1 }

SM16TAT2SAIPSourceGuardDynamicEntry ::= SEQUENCE {
   sm16tat2saIPSourceGuardDynamicIndex Integer32,
   sm16tat2saIPSourceGuardDynamicPort Integer32,
   sm16tat2saIPSourceGuardDynamicIPAddress DisplayString,
   sm16tat2saIPSourceGuardDynamicMACAddress DisplayString
}

sm16tat2saIPSourceGuardDynamicIndex OBJECT-TYPE
   SYNTAX Integer32 (1..4095)
   MAX-ACCESS not-accessible
   STATUS current
   DESCRIPTION
      "The entry of table."
   ::= { sm16tat2saIPSourceGuardDynamicEntry 1 }

sm16tat2saIPSourceGuardDynamicPort OBJECT-TYPE
   SYNTAX Integer32 (1..26)
   MAX-ACCESS read-only
   STATUS current
   DESCRIPTION
      "The logical port for the settings."
   ::= { sm16tat2saIPSourceGuardDynamicEntry 2 }

sm16tat2saIPSourceGuardDynamicIPAddress OBJECT-TYPE
   SYNTAX DisplayString
   MAX-ACCESS read-only
   STATUS current
   DESCRIPTION
      "Allowed Source IP address."
   ::= { sm16tat2saIPSourceGuardDynamicEntry 3 }

sm16tat2saIPSourceGuardDynamicMACAddress OBJECT-TYPE
   SYNTAX DisplayString
   MAX-ACCESS read-only
   STATUS current
   DESCRIPTION
      "Allowed Source MAC address."
   ::= { sm16tat2saIPSourceGuardDynamicEntry 4 }

-- *************************************************************
-- Start sm16tat2saARPInspection group
-- *************************************************************
sm16tat2saARPInspection OBJECT IDENTIFIER ::= { sm16tat2saSecurity 2 }

sm16tat2saARPInspectionMode OBJECT-TYPE
   SYNTAX INTEGER {off(0), on(1)}
   MAX-ACCESS read-write
   STATUS current
   DESCRIPTION
      "Enable the Global ARP Inspection or disable the Global ARP Inspection."
   ::= { sm16tat2saARPInspection 1 }

sm16tat2saARPPortConfigTable OBJECT-TYPE
   SYNTAX SEQUENCE OF SM16TAT2SAARPPortConfigEntry
   MAX-ACCESS not-accessible
   STATUS current
   DESCRIPTION
      "The ARP Port Configuration Table."
   ::= { sm16tat2saARPInspection 2 }

sm16tat2saARPPortConfigEntry OBJECT-TYPE
   SYNTAX SM16TAT2SAARPPortConfigEntry
   MAX-ACCESS not-accessible
   STATUS current
   DESCRIPTION
      "The ARP Port Configuration Entry."
   INDEX { ifIndex }
   ::= { sm16tat2saARPPortConfigTable 1 }

SM16TAT2SAARPPortConfigEntry ::= SEQUENCE {
   sm16tat2saARPPortConfigMode AdminMode,
   sm16tat2saARPPortConfigCheckVLAN AdminMode,
   sm16tat2saARPPortConfigLogType INTEGER
}

sm16tat2saARPPortConfigMode OBJECT-TYPE
   SYNTAX AdminMode
   MAX-ACCESS read-write
   STATUS current
   DESCRIPTION
      "Specify ARP Inspection is enabled on which ports."
   ::= { sm16tat2saARPPortConfigEntry 1 }

sm16tat2saARPPortConfigCheckVLAN OBJECT-TYPE
   SYNTAX AdminMode
   MAX-ACCESS read-write
   STATUS current
   DESCRIPTION
      "When the setting of 'Check VLAN' is disabled, the log type of ARP Inspection will refer to the port setting.
       And the setting of 'Check VLAN' is enabled, the log type of ARP Inspection will refer to the VLAN setting."
   ::= { sm16tat2saARPPortConfigEntry 2 }

sm16tat2saARPPortConfigLogType OBJECT-TYPE
   SYNTAX INTEGER { none(0), deny(1), permit(2), all(3) }
   MAX-ACCESS read-write
   STATUS current
   DESCRIPTION
      "The log type of ARP Inspection will refer to the port setting.
       0: none,
       1: deny,
       2: permit,
       3: all,
       range: 0-3."
   ::= { sm16tat2saARPPortConfigEntry 3 }

sm16tat2saARPVlanConfigTable OBJECT-TYPE
   SYNTAX SEQUENCE OF SM16TAT2SAARPVlanConfigEntry
   MAX-ACCESS not-accessible
   STATUS current
   DESCRIPTION
      "The ARP Vlan Configuration Table."
   ::= { sm16tat2saARPInspection 3 }

sm16tat2saARPVlanConfigEntry OBJECT-TYPE
   SYNTAX SM16TAT2SAARPVlanConfigEntry
   MAX-ACCESS not-accessible
   STATUS current
   DESCRIPTION
      "The ARP Vlan Configuration Entry."
   INDEX { sm16tat2saARPVlanConfigIndex }
   ::= { sm16tat2saARPVlanConfigTable 1 }

SM16TAT2SAARPVlanConfigEntry ::= SEQUENCE {
   sm16tat2saARPVlanConfigIndex Integer32,
   sm16tat2saARPVlanConfigVlanID Integer32,
   sm16tat2saARPVlanConfigLogType INTEGER,
   sm16tat2saARPVlanConfigRowStatus RowStatus
}

sm16tat2saARPVlanConfigIndex OBJECT-TYPE
   SYNTAX Integer32 (1..4095)
   MAX-ACCESS not-accessible
   STATUS current
   DESCRIPTION
      "The entry of table."
   ::= { sm16tat2saARPVlanConfigEntry 1 }

sm16tat2saARPVlanConfigVlanID OBJECT-TYPE
   SYNTAX Integer32(1..4095)
   MAX-ACCESS read-create
   STATUS current
   DESCRIPTION
      "Specify ARP Inspection is enabled on which VLANs.
       range: 1 - 4095."
   ::= { sm16tat2saARPVlanConfigEntry 2 }

sm16tat2saARPVlanConfigLogType OBJECT-TYPE
   SYNTAX INTEGER {none(0), deny(1), permit(2), all(3)}
   MAX-ACCESS read-create
   STATUS current
   DESCRIPTION
      "The log type also can be configured on per VLAN setting.
       0: none,
       1: deny,
       2: permit,
       3: all,
       range: 0-3."
   ::= { sm16tat2saARPVlanConfigEntry 3 }

sm16tat2saARPVlanConfigRowStatus OBJECT-TYPE
   SYNTAX RowStatus
   MAX-ACCESS read-create
   STATUS current
   DESCRIPTION
      "This object indicates the status of this entry, and is used to create/delete entries.
       Any object in an entry of this table may be modified while the value of the corresponding instance of this object is active(1).
       createAndGo, notReady not supported."
   ::= { sm16tat2saARPVlanConfigEntry 4 }

sm16tat2saARPStaticTable OBJECT-TYPE
   SYNTAX SEQUENCE OF SM16TAT2SAARPStaticEntry
   MAX-ACCESS not-accessible
   STATUS current
   DESCRIPTION
      "The ARP Static Table."
   ::= { sm16tat2saARPInspection 4 }

sm16tat2saARPStaticEntry OBJECT-TYPE
   SYNTAX SM16TAT2SAARPStaticEntry
   MAX-ACCESS not-accessible
   STATUS current
   DESCRIPTION
      "The ARP Static Entry."
   INDEX { sm16tat2saARPStaticIndex }
   ::= { sm16tat2saARPStaticTable 1 }

SM16TAT2SAARPStaticEntry ::= SEQUENCE {
   sm16tat2saARPStaticIndex Integer32,
   sm16tat2saARPStaticPort Integer32,
   sm16tat2saARPStaticVlanID Integer32,
   sm16tat2saARPStaticMACAddress DisplayString,
   sm16tat2saARPStaticIPAddress DisplayString,
   sm16tat2saARPStaticRowStatus RowStatus
}

sm16tat2saARPStaticIndex OBJECT-TYPE
   SYNTAX Integer32 (1..4095)
   MAX-ACCESS not-accessible
   STATUS current
   DESCRIPTION
      "The entry of table."
   ::= { sm16tat2saARPStaticEntry 1 }

sm16tat2saARPStaticPort OBJECT-TYPE
   SYNTAX Integer32 (1..26)
   MAX-ACCESS read-create
   STATUS current
   DESCRIPTION
      "The logical port for the settings."
   ::= { sm16tat2saARPStaticEntry 2 }

sm16tat2saARPStaticVlanID OBJECT-TYPE
   SYNTAX Integer32 (1..4095)
   MAX-ACCESS read-create
   STATUS current
   DESCRIPTION
      "The vlan id for the settings."
   ::= { sm16tat2saARPStaticEntry 3 }

sm16tat2saARPStaticMACAddress OBJECT-TYPE
   SYNTAX DisplayString
   MAX-ACCESS read-create
   STATUS current
   DESCRIPTION
      "Allowed Source MAC address in ARP request packets."
   ::= { sm16tat2saARPStaticEntry 4 }

sm16tat2saARPStaticIPAddress OBJECT-TYPE
   SYNTAX DisplayString
   MAX-ACCESS read-create
   STATUS current
   DESCRIPTION
      "Allowed Source IP address in ARP request packets."
   ::= { sm16tat2saARPStaticEntry 5 }

sm16tat2saARPStaticRowStatus OBJECT-TYPE
   SYNTAX RowStatus
   MAX-ACCESS read-create
   STATUS current
   DESCRIPTION
      "This object indicates the status of this entry, and is used to create/delete entries.
       Any object in an entry of this table may be modified while the value of the corresponding instance of this object is active(1).
       createAndGo, notReady not supported."
   ::= { sm16tat2saARPStaticEntry 6 }

sm16tat2saARPDynamicTable OBJECT-TYPE
   SYNTAX SEQUENCE OF SM16TAT2SAARPDynamicEntry
   MAX-ACCESS not-accessible
   STATUS current
   DESCRIPTION
      "The ARP Dynamic Table."
   ::= { sm16tat2saARPInspection 5 }

sm16tat2saARPDynamicEntry OBJECT-TYPE
   SYNTAX SM16TAT2SAARPDynamicEntry
   MAX-ACCESS not-accessible
   STATUS current
   DESCRIPTION
      "The ARP Dynamic Entry."
   INDEX { sm16tat2saARPDynamicIndex }
   ::= { sm16tat2saARPDynamicTable 1 }

SM16TAT2SAARPDynamicEntry ::= SEQUENCE {
   sm16tat2saARPDynamicIndex Integer32,
   sm16tat2saARPDynamicPort Integer32,
   sm16tat2saARPDynamicVLANId Integer32,
   sm16tat2saARPDynamicMACAddress DisplayString,
   sm16tat2saARPDynamicIPAddress DisplayString
}

sm16tat2saARPDynamicIndex OBJECT-TYPE
   SYNTAX Integer32(1..4095)
   MAX-ACCESS not-accessible
   STATUS current
   DESCRIPTION
      "The entry of table."
   ::= { sm16tat2saARPDynamicEntry 1 }

sm16tat2saARPDynamicPort OBJECT-TYPE
   SYNTAX Integer32(1..255)
   MAX-ACCESS read-only
   STATUS current
   DESCRIPTION
      "Switch Port Number for which the entries are displayed."
   ::= { sm16tat2saARPDynamicEntry 2 }

sm16tat2saARPDynamicVLANId OBJECT-TYPE
   SYNTAX Integer32(1..4095)
   MAX-ACCESS read-only
   STATUS current
   DESCRIPTION
      "VLAN-ID in which the ARP traffic is permitted."
   ::= { sm16tat2saARPDynamicEntry 3 }

sm16tat2saARPDynamicMACAddress OBJECT-TYPE
   SYNTAX DisplayString
   MAX-ACCESS read-only
   STATUS current
   DESCRIPTION
      "User MAC address of the entry."
   ::= { sm16tat2saARPDynamicEntry 4 }

sm16tat2saARPDynamicIPAddress OBJECT-TYPE
   SYNTAX DisplayString
   MAX-ACCESS read-only
   STATUS current
   DESCRIPTION
      "User IP address of the entry."
   ::= { sm16tat2saARPDynamicEntry 5 }

-- *************************************************************
-- Start sm16tat2saDHCPSnooping group
-- *************************************************************
sm16tat2saDHCPSnooping OBJECT IDENTIFIER ::= { sm16tat2saSecurity 3}

sm16tat2saDHCPSnoopingConfiguration OBJECT IDENTIFIER ::= { sm16tat2saDHCPSnooping 1 }

sm16tat2saDHCPSnoopingMode OBJECT-TYPE
   SYNTAX INTEGER {off(0), on(1)}
   MAX-ACCESS read-write
   STATUS current
   DESCRIPTION
      "default: 0
       0: off(diable)
       1: on(enable)"
   ::= { sm16tat2saDHCPSnoopingConfiguration 1 }

sm16tat2saDHCPSnoopingPortModeConfigurationTable OBJECT-TYPE
   SYNTAX SEQUENCE OF SM16TAT2SADHCPSnoopingPortModeConfigurationEntry
   MAX-ACCESS not-accessible
   STATUS current
   DESCRIPTION
       " "
   ::= { sm16tat2saDHCPSnoopingConfiguration 2 }

sm16tat2saDHCPSnoopingPortModeConfigurationEntry OBJECT-TYPE
   SYNTAX SM16TAT2SADHCPSnoopingPortModeConfigurationEntry
   MAX-ACCESS not-accessible
   STATUS current
   DESCRIPTION
       " "
   INDEX { sm16tat2saDHCPSnoopingPortModeConfigurationPort }
   ::= { sm16tat2saDHCPSnoopingPortModeConfigurationTable 1 }

SM16TAT2SADHCPSnoopingPortModeConfigurationEntry ::= SEQUENCE {
   sm16tat2saDHCPSnoopingPortModeConfigurationPort Integer32,
   sm16tat2saDHCPSnoopingPortModeConfigurationMode Integer32
}

sm16tat2saDHCPSnoopingPortModeConfigurationPort OBJECT-TYPE
   SYNTAX Integer32(1..26)
   MAX-ACCESS not-accessible
   STATUS current
   DESCRIPTION
       " "
   ::= { sm16tat2saDHCPSnoopingPortModeConfigurationEntry 1 }

sm16tat2saDHCPSnoopingPortModeConfigurationMode OBJECT-TYPE
   SYNTAX Integer32 (0|1)
   MAX-ACCESS read-write
   STATUS current
   DESCRIPTION
       "default: 1
       0: trust port mode
       1: untrust port mode"
   ::= { sm16tat2saDHCPSnoopingPortModeConfigurationEntry 2 }

sm16tat2saDynamicDHCPSnoopingTable OBJECT-TYPE
   SYNTAX SEQUENCE OF SM16TAT2SADynamicDHCPSnoopingEntry
   MAX-ACCESS not-accessible
   STATUS current
   DESCRIPTION
       " "
   ::= { sm16tat2saDHCPSnooping 2 }

sm16tat2saDynamicDHCPSnoopingEntry OBJECT-TYPE
   SYNTAX SM16TAT2SADynamicDHCPSnoopingEntry
   MAX-ACCESS not-accessible
   STATUS current
   DESCRIPTION
       " "
   INDEX { sm16tat2saDynamicDHCPSnoopingIndex }
   ::= { sm16tat2saDynamicDHCPSnoopingTable 1 }

SM16TAT2SADynamicDHCPSnoopingEntry ::= SEQUENCE {
   sm16tat2saDynamicDHCPSnoopingIndex Integer32,
   sm16tat2saDynamicDHCPSnoopingMACAddress DisplayString,
   sm16tat2saDynamicDHCPSnoopingVLANID Integer32,
   sm16tat2saDynamicDHCPSnoopingPort Integer32,
   sm16tat2saDynamicDHCPSnoopingIPAddress DisplayString,
   sm16tat2saDynamicDHCPSnoopingIPSubnetMask DisplayString,
   sm16tat2saDynamicDHCPSnoopingDHCPServer DisplayString
}

sm16tat2saDynamicDHCPSnoopingIndex OBJECT-TYPE
   SYNTAX Integer32(1..4095)
   MAX-ACCESS not-accessible
   STATUS current
   DESCRIPTION
       " "
   ::= { sm16tat2saDynamicDHCPSnoopingEntry 1 }

sm16tat2saDynamicDHCPSnoopingMACAddress OBJECT-TYPE
   SYNTAX DisplayString
   MAX-ACCESS read-only
   STATUS current
   DESCRIPTION
       " "
   ::= { sm16tat2saDynamicDHCPSnoopingEntry 2 }

sm16tat2saDynamicDHCPSnoopingVLANID OBJECT-TYPE
   SYNTAX Integer32(1..4095)
   MAX-ACCESS read-only
   STATUS current
   DESCRIPTION
       " "
   ::= { sm16tat2saDynamicDHCPSnoopingEntry 3 }

sm16tat2saDynamicDHCPSnoopingPort OBJECT-TYPE
   SYNTAX Integer32(1..26)
   MAX-ACCESS read-only
   STATUS current
   DESCRIPTION
       " "
   ::= { sm16tat2saDynamicDHCPSnoopingEntry 4 }

sm16tat2saDynamicDHCPSnoopingIPAddress OBJECT-TYPE
   SYNTAX DisplayString
   MAX-ACCESS read-only
   STATUS current
   DESCRIPTION
       " "
   ::= { sm16tat2saDynamicDHCPSnoopingEntry 5 }

sm16tat2saDynamicDHCPSnoopingIPSubnetMask OBJECT-TYPE
   SYNTAX DisplayString
   MAX-ACCESS read-only
   STATUS current
   DESCRIPTION
       " "
   ::= { sm16tat2saDynamicDHCPSnoopingEntry 6 }

sm16tat2saDynamicDHCPSnoopingDHCPServer OBJECT-TYPE
   SYNTAX DisplayString
   MAX-ACCESS read-only
   STATUS current
   DESCRIPTION
       " "
   ::= { sm16tat2saDynamicDHCPSnoopingEntry 7 }

sm16tat2saPortSecLimitCtrl OBJECT IDENTIFIER ::= { sm16tat2saSecurity 5}

sm16tat2saPortSecLimitCtrlSystemConf OBJECT IDENTIFIER ::= { sm16tat2saPortSecLimitCtrl 1 }

sm16tat2saPortSecurityMode OBJECT-TYPE
   SYNTAX INTEGER { disable(0), enable(1) }
   MAX-ACCESS read-write
   STATUS current
   DESCRIPTION
       "default: 0
       0: disable
       1: enable "
   ::= { sm16tat2saPortSecLimitCtrlSystemConf 1 }

sm16tat2saPortSecLimitCtrlTable OBJECT-TYPE
   SYNTAX SEQUENCE OF SM16TAT2SAPortSecLimitCtrlEntry
   MAX-ACCESS not-accessible
   STATUS current
   DESCRIPTION
       " "
   ::= { sm16tat2saPortSecLimitCtrlSystemConf 2 }

sm16tat2saPortSecLimitCtrlEntry OBJECT-TYPE
   SYNTAX SM16TAT2SAPortSecLimitCtrlEntry
   MAX-ACCESS not-accessible
   STATUS current
   DESCRIPTION
       " "
   INDEX { sm16tat2saPortSecLimitCtrlPort }
   ::= { sm16tat2saPortSecLimitCtrlTable 1 }

SM16TAT2SAPortSecLimitCtrlEntry ::= SEQUENCE {
   sm16tat2saPortSecLimitCtrlPort Integer32,
   sm16tat2saPortSecLimitCtrlPortMode INTEGER,
   sm16tat2saPortSecLimitCtrlPortLimit Integer32,
   sm16tat2saPortSecLimitCtrlPortAction INTEGER,
   sm16tat2saPortSecLimitCtrlPortState DisplayString,
   sm16tat2saPortSecLimitCtrlPortReOpen INTEGER
}

sm16tat2saPortSecLimitCtrlPort OBJECT-TYPE
   SYNTAX Integer32 (1..4095)
   MAX-ACCESS not-accessible
   STATUS current
   DESCRIPTION
       " "
   ::= { sm16tat2saPortSecLimitCtrlEntry 1 }

sm16tat2saPortSecLimitCtrlPortMode OBJECT-TYPE
   SYNTAX INTEGER { disable(0), enable(1) }
   MAX-ACCESS read-write
   STATUS current
   DESCRIPTION
       "default: 0
       0: disable
       1: enable"
   ::= { sm16tat2saPortSecLimitCtrlEntry 2 }

sm16tat2saPortSecLimitCtrlPortLimit OBJECT-TYPE
   SYNTAX Integer32(1..1024)
   MAX-ACCESS read-write
   STATUS current
   DESCRIPTION
       "default: 4, range: 1-1024"
   ::= { sm16tat2saPortSecLimitCtrlEntry 3 }

sm16tat2saPortSecLimitCtrlPortAction OBJECT-TYPE
   SYNTAX INTEGER { none(0), trap(1), shutdown(2), trapShutdown(3) }
   MAX-ACCESS read-write
   STATUS current
   DESCRIPTION
       "default: 0
       0: none
       1: trap
       2: shutdown
       3: trap&shutdown"
   ::= { sm16tat2saPortSecLimitCtrlEntry 4 }

sm16tat2saPortSecLimitCtrlPortState OBJECT-TYPE
   SYNTAX DisplayString
   MAX-ACCESS read-only
   STATUS current
   DESCRIPTION
       " "
   ::= { sm16tat2saPortSecLimitCtrlEntry 5 }

sm16tat2saPortSecLimitCtrlPortReOpen OBJECT-TYPE
   SYNTAX INTEGER { none(0), reopen(1) }
   MAX-ACCESS read-write
   STATUS current
   DESCRIPTION
       "default: 0
       0: none
       1: reopen"
   ::= { sm16tat2saPortSecLimitCtrlEntry 6 }

sm16tat2saPortSecSwitchStatusTable OBJECT-TYPE
   SYNTAX SEQUENCE OF SM16TAT2SAPortSecSwitchStatusEntry
   MAX-ACCESS not-accessible
   STATUS current
   DESCRIPTION
       " "
   ::= { sm16tat2saPortSecLimitCtrl 2 }

sm16tat2saPortSecSwitchStatusEntry OBJECT-TYPE
   SYNTAX SM16TAT2SAPortSecSwitchStatusEntry
   MAX-ACCESS not-accessible
   STATUS current
   DESCRIPTION
       " "
   INDEX { sm16tat2saPortSecSwitchStatusPort }
   ::= { sm16tat2saPortSecSwitchStatusTable 1 }

SM16TAT2SAPortSecSwitchStatusEntry ::= SEQUENCE {
   sm16tat2saPortSecSwitchStatusPort Integer32,
   sm16tat2saPortSecSwitchStatusState DisplayString,
   sm16tat2saPortSecSwitchStatusMACCountCurrent Integer32
}

sm16tat2saPortSecSwitchStatusPort OBJECT-TYPE
   SYNTAX Integer32 (1..4095)
   MAX-ACCESS not-accessible
   STATUS current
   DESCRIPTION
       " "
   ::= { sm16tat2saPortSecSwitchStatusEntry 1 }

sm16tat2saPortSecSwitchStatusState OBJECT-TYPE
   SYNTAX DisplayString
   MAX-ACCESS read-only
   STATUS current
   DESCRIPTION
       " Shows the current state of the port : Disabled, Ready, Limit Reached, Shutdown. "
   ::= { sm16tat2saPortSecSwitchStatusEntry 2 }

sm16tat2saPortSecSwitchStatusMACCountCurrent OBJECT-TYPE
   SYNTAX Integer32(1..4095)
   MAX-ACCESS read-only
   STATUS current
   DESCRIPTION
       " "
   ::= { sm16tat2saPortSecSwitchStatusEntry 3 }

-- *************************************************************
-- Start sm16tat2saTACACS group
-- *************************************************************
sm16tat2saTACACS OBJECT IDENTIFIER ::= { sm16tat2saSecurity 7 }

sm16tat2saTACACSGlobalConfigTimeout OBJECT-TYPE
   SYNTAX Integer32(1..1000)
   MAX-ACCESS read-write
   STATUS current
   DESCRIPTION
      "Timeout is the number of seconds,to wait for a reply from a TACACS+ server before it is considered to be dead.
        range: 1-1000 seconds, default: 5 seconds."
   ::= { sm16tat2saTACACS 1 }

sm16tat2saTACACSGlobalConfigDeadtime OBJECT-TYPE
   SYNTAX Integer32(0..1440)
   MAX-ACCESS read-write
   STATUS current
   DESCRIPTION
      "The period during which the switch will not send new requests to a server that has failed to respond to a previous request.
       This will stop the switch from continually trying to contact a server that it has already determined as dead.
        range: 0-1440 minutes, default: 0 minutes."
   ::= { sm16tat2saTACACS 2 }

sm16tat2saTACACSGlobalConfigKey OBJECT-TYPE
   SYNTAX DisplayString
   MAX-ACCESS read-write
   STATUS current
   DESCRIPTION
      "The secret key shared between the TACACS+ server and the switch."
   ::= { sm16tat2saTACACS 3 }

sm16tat2saTACACSServerConfigTable OBJECT-TYPE
   SYNTAX SEQUENCE OF SM16TAT2SATACACSServerConfigEntry
   MAX-ACCESS not-accessible
   STATUS current
   DESCRIPTION
      "The TACACS Server configuration Table."
   ::= { sm16tat2saTACACS 4 }

sm16tat2saTACACSServerConfigEntry OBJECT-TYPE
   SYNTAX SM16TAT2SATACACSServerConfigEntry
   MAX-ACCESS not-accessible
   STATUS current
   DESCRIPTION
      "The TACACS Server configuration Entry."
   INDEX { sm16tat2saTACACSServerConfigServerNo }
   ::= { sm16tat2saTACACSServerConfigTable 1 }

SM16TAT2SATACACSServerConfigEntry ::=
SEQUENCE {
   sm16tat2saTACACSServerConfigServerNo Integer32,
   sm16tat2saTACACSServerConfigHostname DisplayString,
   sm16tat2saTACACSServerConfigPort Integer32,
   sm16tat2saTACACSServerConfigTimeout Integer32,
   sm16tat2saTACACSServerConfigKey DisplayString,
   sm16tat2saTACACSServerConfigRowStatus RowStatus
}

sm16tat2saTACACSServerConfigServerNo OBJECT-TYPE
   SYNTAX Integer32(1..5)
   MAX-ACCESS not-accessible
   STATUS current
   DESCRIPTION
      "The TACACS server number.
        max: 5"
   ::= { sm16tat2saTACACSServerConfigEntry 1 }

sm16tat2saTACACSServerConfigHostname OBJECT-TYPE
   SYNTAX DisplayString
   MAX-ACCESS read-create
   STATUS current
   DESCRIPTION
      "The IP address or hostname of the TACACS+ server."
   ::= { sm16tat2saTACACSServerConfigEntry 2 }

sm16tat2saTACACSServerConfigPort OBJECT-TYPE
   SYNTAX Integer32(0..65535)
   MAX-ACCESS read-create
   STATUS current
   DESCRIPTION
      "The TCP port to use on the TACACS+ server for authentication."
   ::= { sm16tat2saTACACSServerConfigEntry 3 }

sm16tat2saTACACSServerConfigTimeout OBJECT-TYPE
   SYNTAX Integer32(1..1000)
   MAX-ACCESS read-create
   STATUS current
   DESCRIPTION
      "This optional setting overrides the global timeout value.
       Leaving it blank will use the global timeout value.
        range: 1-1000."
   ::= { sm16tat2saTACACSServerConfigEntry 4 }

sm16tat2saTACACSServerConfigKey OBJECT-TYPE
   SYNTAX DisplayString
   MAX-ACCESS read-create
   STATUS current
   DESCRIPTION
      "This optional setting overrides the global key.
       Leaving it blank will use the global key. "
   ::= { sm16tat2saTACACSServerConfigEntry 5 }

sm16tat2saTACACSServerConfigRowStatus OBJECT-TYPE
   SYNTAX RowStatus
   MAX-ACCESS read-create
   STATUS current
   DESCRIPTION
      "This object indicates the status of this entry, and is used to create/delete entries.
       Any object in an entry of this table may be modified while the value of the corresponding instance of this object is active(1).
       notReady(3) and createAndGo(4) are not supported."
   ::= { sm16tat2saTACACSServerConfigEntry 6 }

-- *************************************************************
-- Start sm16tat2saAuthMethod group
-- *************************************************************
sm16tat2saAuthMethod OBJECT IDENTIFIER ::= { sm16tat2saSecurity 9 }

sm16tat2saAuthMethodConfigTable OBJECT-TYPE
   SYNTAX SEQUENCE OF SM16TAT2SAAuthMethodConfigEntry
   MAX-ACCESS not-accessible
   STATUS current
   DESCRIPTION
      "The Auth Method Config Table."
   ::= { sm16tat2saAuthMethod 1 }

sm16tat2saAuthMethodConfigEntry OBJECT-TYPE
   SYNTAX SM16TAT2SAAuthMethodConfigEntry
   MAX-ACCESS not-accessible
   STATUS current
   DESCRIPTION
      "The Auth Method Config Entry."
   INDEX { sm16tat2saAuthMethodConfigClient }
   ::= { sm16tat2saAuthMethodConfigTable 1 }

SM16TAT2SAAuthMethodConfigEntry ::=
SEQUENCE {
   sm16tat2saAuthMethodConfigClient INTEGER,
   sm16tat2saAuthMethodConfigMethod1 INTEGER,
   sm16tat2saAuthMethodConfigMethod2 INTEGER,
   sm16tat2saAuthMethodConfigMethod3 INTEGER,
   sm16tat2saAuthMethodConfigServicePort Integer32
}

sm16tat2saAuthMethodConfigClient OBJECT-TYPE

   SYNTAX INTEGER {telnet(2), ssh(3), http(4), https(5)}

   MAX-ACCESS not-accessible
   STATUS current
   DESCRIPTION

      "The Client of the Auth Method Config.  2: telnet, 3: ssh, 4: http, 5: https"

   ::= { sm16tat2saAuthMethodConfigEntry 1 }

sm16tat2saAuthMethodConfigMethod1 OBJECT-TYPE
   SYNTAX INTEGER {no(0) ,local(1) ,radius(2) ,tacacs(3) ,redirect(4)}
   MAX-ACCESS read-write
   STATUS current
   DESCRIPTION
      "Methods that involves remote servers are timed out if the remote servers are offline.Each method is tried from left to
       right and continues until a method either approves or rejects a user.
         0: no, Authentication is disabled and login is not possible.
         1: local(default), Use the local user database on the switch for authentication.
         2: radius, Use remote RADIUS server(s) for authentication.
         3: tacacs+, Use remote TACACS+ server(s) for authentication.
         4: redirect, HTTP redirect HTTPS. "
   ::= { sm16tat2saAuthMethodConfigEntry 2 }

sm16tat2saAuthMethodConfigMethod2 OBJECT-TYPE
   SYNTAX INTEGER {no(0) ,local(1) ,radius(2) ,tacacs(3)}
   MAX-ACCESS read-write
   STATUS current
   DESCRIPTION
      "Methods that involves remote servers are timed out if the remote servers are offline.Each method is tried from left to
       right and continues until a method either approves or rejects a user.
         0: no(default), Authentication is disabled and login is not possible.
         1: local, Use the local user database on the switch for authentication.
         2: radius, Use remote RADIUS server(s) for authentication.
         3: tacacs+, Use remote TACACS+ server(s) for authentication. "
   ::= { sm16tat2saAuthMethodConfigEntry 3 }

sm16tat2saAuthMethodConfigMethod3 OBJECT-TYPE
   SYNTAX INTEGER {no(0), local(1), radius(2), tacacs(3)}
   MAX-ACCESS read-write
   STATUS current
   DESCRIPTION
      "Methods that involves remote servers are timed out if the remote servers are offline.Each method is tried from left to
       right and continues until a method either approves or rejects a user.
         0: no(default), Authentication is disabled and login is not possible.
         1: local, Use the local user database on the switch for authentication.
         2: radius, Use remote RADIUS server(s) for authentication.
         3: tacacs+, Use remote TACACS+ server(s) for authentication. "
   ::= { sm16tat2saAuthMethodConfigEntry 4 }

sm16tat2saAuthMethodConfigServicePort OBJECT-TYPE
   SYNTAX Integer32 (1..65535)
   MAX-ACCESS read-write
   STATUS current
   DESCRIPTION
      "The Service Port of the Auth Method Config Table.  range: 0~65535.  deault: 23(telnet), 22(ssh), 80(http), 443(https)."
   ::= { sm16tat2saAuthMethodConfigEntry 5 }

sm16tat2saCmdAuthMethodConfigTable OBJECT-TYPE
   SYNTAX SEQUENCE OF SM16TAT2SACmdAuthMethodConfigEntry
   MAX-ACCESS not-accessible
   STATUS current
   DESCRIPTION
      "The Command Auth Method Config Table."
   ::= { sm16tat2saAuthMethod 3 }

sm16tat2saCmdAuthMethodConfigEntry OBJECT-TYPE
   SYNTAX SM16TAT2SACmdAuthMethodConfigEntry
   MAX-ACCESS not-accessible
   STATUS current
   DESCRIPTION
      "The Command Auth Method Config Entry."
   INDEX { sm16tat2saCmdAuthMethodConfigClient }
   ::= { sm16tat2saCmdAuthMethodConfigTable 1 }

SM16TAT2SACmdAuthMethodConfigEntry ::=
SEQUENCE {
   sm16tat2saCmdAuthMethodConfigClient INTEGER,
   sm16tat2saCmdAuthMethodConfigMethods INTEGER,
   sm16tat2saCmdAuthMethodConfigCmdLvl Integer32,
   sm16tat2saCmdAuthMethodConfigCfgCmd INTEGER,
   sm16tat2saCmdAuthMethodConfigFallback INTEGER
}

sm16tat2saCmdAuthMethodConfigClient OBJECT-TYPE

   SYNTAX INTEGER {telnet(2), ssh(3)}

   MAX-ACCESS not-accessible
   STATUS current
   DESCRIPTION

      "The Client of the Command Auth Method Config.  2: telnet, 3: ssh"

   ::= { sm16tat2saCmdAuthMethodConfigEntry 1 }

sm16tat2saCmdAuthMethodConfigMethods OBJECT-TYPE
   SYNTAX INTEGER {no(0), tacacs(3)}
   MAX-ACCESS read-write
   STATUS current
   DESCRIPTION
      "Methods that involves remote servers are timed out if the remote servers are offline.Each method is tried from left to
       right and continues until a method either approves or rejects a user.
         0: no(default), Authentication is disabled and login is not possible.
         3: tacacs+, Use remote TACACS+ server(s) for authentication. "
   ::= { sm16tat2saCmdAuthMethodConfigEntry 2 }

sm16tat2saCmdAuthMethodConfigCmdLvl OBJECT-TYPE
   SYNTAX Integer32 (0..15)
   MAX-ACCESS read-write
   STATUS current
   DESCRIPTION
      "The Command Level of the Command Auth Method Config.  range: 0~15, deault: 0. "
   ::= { sm16tat2saCmdAuthMethodConfigEntry 3 }

sm16tat2saCmdAuthMethodConfigCfgCmd OBJECT-TYPE
   SYNTAX AdminMode
   MAX-ACCESS read-write
   STATUS current
   DESCRIPTION
      "Control whether The Config Command of the Command Auth Method Config is enabled or not.  0: disable(default), 1: enable. "
   ::= { sm16tat2saCmdAuthMethodConfigEntry 4 }

sm16tat2saCmdAuthMethodConfigFallback OBJECT-TYPE
   SYNTAX AdminMode
   MAX-ACCESS read-write
   STATUS current
   DESCRIPTION
      "Control whether The Fallback of the Command Auth Method Config is enabled or not.  0: disable(default), 1: enable. "
   ::= { sm16tat2saCmdAuthMethodConfigEntry 5 }

sm16tat2saAcctAuthMethodConfigTable OBJECT-TYPE
   SYNTAX SEQUENCE OF SM16TAT2SAAcctAuthMethodConfigEntry
   MAX-ACCESS not-accessible
   STATUS current
   DESCRIPTION
      "The Accounting Auth Method Config Table."
   ::= { sm16tat2saAuthMethod 4 }

sm16tat2saAcctAuthMethodConfigEntry OBJECT-TYPE
   SYNTAX SM16TAT2SAAcctAuthMethodConfigEntry
   MAX-ACCESS not-accessible
   STATUS current
   DESCRIPTION
      "The Accounting Auth Method Config Entry."
   INDEX { sm16tat2saAcctAuthMethodConfigClient }
   ::= { sm16tat2saAcctAuthMethodConfigTable 1 }

SM16TAT2SAAcctAuthMethodConfigEntry ::=
SEQUENCE {
   sm16tat2saAcctAuthMethodConfigClient INTEGER,
   sm16tat2saAcctAuthMethodConfigMethods INTEGER,
   sm16tat2saAcctAuthMethodConfigCmdLvl Integer32,
   sm16tat2saAcctAuthMethodConfigExec INTEGER
}

sm16tat2saAcctAuthMethodConfigClient OBJECT-TYPE

   SYNTAX INTEGER {telnet(2), ssh(3)}

   MAX-ACCESS not-accessible
   STATUS current
   DESCRIPTION

      "The Client of the Accounting Auth Method Config.  2: telnet, 3: ssh"

   ::= { sm16tat2saAcctAuthMethodConfigEntry 1 }

sm16tat2saAcctAuthMethodConfigMethods OBJECT-TYPE
   SYNTAX INTEGER {no(0), tacacs(3)}
   MAX-ACCESS read-write
   STATUS current
   DESCRIPTION
      "Methods that involves remote servers are timed out if the remote servers are offline.Each method is tried from left to
       right and continues until a method either approves or rejects a user.
         0: no(deault), Authentication is disabled and login is not possible.
         3: tacacs+, Use remote TACACS+ server(s) for authentication. "
   ::= { sm16tat2saAcctAuthMethodConfigEntry 2 }

sm16tat2saAcctAuthMethodConfigCmdLvl OBJECT-TYPE
   SYNTAX Integer32 (0..15)
   MAX-ACCESS read-write
   STATUS current
   DESCRIPTION
      "The Command Level of the Accounting Auth Method Config.  range: 0~15, deault: 0. "
   ::= { sm16tat2saAcctAuthMethodConfigEntry 3 }

sm16tat2saAcctAuthMethodConfigExec OBJECT-TYPE
   SYNTAX AdminMode
   MAX-ACCESS read-write
   STATUS current
   DESCRIPTION
      "Control whether The Exec of the Accounting Auth Method Config is enabled or not.  0: disable(default), 1: enable. "
   ::= { sm16tat2saAcctAuthMethodConfigEntry 4 }

-- *************************************************************
-- Start sm16tat2saAccessManagementConfig group
-- *************************************************************
sm16tat2saAccessManagementConfig OBJECT IDENTIFIER ::= { sm16tat2saSecurity 10 }

sm16tat2saAccessManagementConfigGlobals OBJECT IDENTIFIER ::= { sm16tat2saAccessManagementConfig 1 }

sm16tat2saAccessManagementConfigGlobalsAdminState OBJECT-TYPE
    SYNTAX INTEGER { disable(0), enable(1) }
    MAX-ACCESS read-write
    STATUS current
    DESCRIPTION
        "Enable/Disable the Access Management global functionality."
    ::= { sm16tat2saAccessManagementConfigGlobals 1 }

sm16tat2saAccessManagementConfigIpv4Table OBJECT-TYPE
    SYNTAX SEQUENCE OF SM16TAT2SAAccessManagementConfigIpv4Entry
    MAX-ACCESS not-accessible
    STATUS current
    DESCRIPTION
        "This is a table for managing Access Management per IPv4 basis"
    ::= { sm16tat2saAccessManagementConfig 2 }

sm16tat2saAccessManagementConfigIpv4Entry OBJECT-TYPE
    SYNTAX SM16TAT2SAAccessManagementConfigIpv4Entry
    MAX-ACCESS not-accessible
    STATUS current
    DESCRIPTION
        "Each entry has a set of parameters"
    INDEX { sm16tat2saAccessManagementConfigIpv4AccessIndex }
    ::= { sm16tat2saAccessManagementConfigIpv4Table 1 }

SM16TAT2SAAccessManagementConfigIpv4Entry ::= SEQUENCE {
    sm16tat2saAccessManagementConfigIpv4AccessIndex Integer32,
    sm16tat2saAccessManagementConfigIpv4VlanId Integer32,
    sm16tat2saAccessManagementConfigIpv4Address DisplayString,
    sm16tat2saAccessManagementConfigIpv4MaskLength Integer32,
    sm16tat2saAccessManagementConfigIpv4WebServices INTEGER,
    sm16tat2saAccessManagementConfigIpv4SnmpServices INTEGER,
    sm16tat2saAccessManagementConfigIpv4TelnetServices INTEGER,
    sm16tat2saAccessManagementConfigIpv4RowStatus RowStatus
}

sm16tat2saAccessManagementConfigIpv4AccessIndex OBJECT-TYPE
    SYNTAX Integer32 (0..2147483647)
    MAX-ACCESS not-accessible
    STATUS current
    DESCRIPTION
        "Index for Access Management IPv4/IPv6 table."
    ::= { sm16tat2saAccessManagementConfigIpv4Entry 1 }

sm16tat2saAccessManagementConfigIpv4VlanId OBJECT-TYPE
    SYNTAX Integer32 (1..4095)
    MAX-ACCESS read-create
    STATUS current
    DESCRIPTION
        "The ID of specific VLAN interface that Access Management should take
         effect for IPv4."
    ::= { sm16tat2saAccessManagementConfigIpv4Entry 2 }

sm16tat2saAccessManagementConfigIpv4Address OBJECT-TYPE
    SYNTAX DisplayString
    MAX-ACCESS read-create
    STATUS current
    DESCRIPTION
        "The starting IPv4 address of the range that Access Management performs
         checking."
    ::= { sm16tat2saAccessManagementConfigIpv4Entry 3 }

sm16tat2saAccessManagementConfigIpv4MaskLength OBJECT-TYPE
    SYNTAX Integer32
    MAX-ACCESS read-create
    STATUS current
    DESCRIPTION
        "The ending IPv4 address of the range that Access Management performs
         checking."
    ::= { sm16tat2saAccessManagementConfigIpv4Entry 4 }

sm16tat2saAccessManagementConfigIpv4WebServices OBJECT-TYPE
    SYNTAX INTEGER { disable(0), enable(1) }
    MAX-ACCESS read-create
    STATUS current
    DESCRIPTION
        "Enable/Disable HTTP and HTTPS functionality via Access Management. At
         least one of WebServices/SnmpServices/TelnetServices has to be enabled
         for a specific AccessIndex in Access Management IPv4 table."
    ::= { sm16tat2saAccessManagementConfigIpv4Entry 5 }

sm16tat2saAccessManagementConfigIpv4SnmpServices OBJECT-TYPE
    SYNTAX INTEGER { disable(0), enable(1) }
    MAX-ACCESS read-create
    STATUS current
    DESCRIPTION
        "Enable/Disable SNMP functionality via Access Management. At least one
         of WebServices/SnmpServices/TelnetServices has to be enabled for a
         specific AccessIndex in Access Management IPv4 table."
    ::= { sm16tat2saAccessManagementConfigIpv4Entry 6 }

sm16tat2saAccessManagementConfigIpv4TelnetServices OBJECT-TYPE
    SYNTAX INTEGER { disable(0), enable(1) }
    MAX-ACCESS read-create
    STATUS current
    DESCRIPTION
        "Enable/Disable TELNET/SSH functionality via Access Management. At least
         one of WebServices/SnmpServices/TelnetServices has to be enabled for a
         specific AccessIndex in Access Management IPv4 table."
    ::= { sm16tat2saAccessManagementConfigIpv4Entry 7 }

sm16tat2saAccessManagementConfigIpv4RowStatus OBJECT-TYPE
    SYNTAX RowStatus
    MAX-ACCESS read-create
    STATUS current
    DESCRIPTION
       "This object indicates the status of this entry, and is
        used to create/delete entries. Any object in an entry of
        this table may be modified while the value of the
        corresponding instance of this object is active(1).
        notReady(3) and createAndGo(4) not supported."
    ::= { sm16tat2saAccessManagementConfigIpv4Entry 8 }

-- *************************************************************
-- Start sm16tat2saSecurity group
-- *************************************************************
sm16tat2saSecurityConformance OBJECT IDENTIFIER ::= { sm16tat2saSecurity 200 }
sm16tat2saSecurityCompliances OBJECT IDENTIFIER ::= { sm16tat2saSecurityConformance 1 }
sm16tat2saSecurityGroups OBJECT IDENTIFIER ::= { sm16tat2saSecurityConformance 2 }

sm16tat2saIPSourceGuardGroup OBJECT-GROUP
    OBJECTS {
    --sm16tat2saIPSourceGuard
        sm16tat2saIPSourceGuardMode,

      --sm16tat2saIPSourceGuardPortConfigTable
        sm16tat2saIPSourceGuardPortConfigMode,
        sm16tat2saIPSourceGuardPortMaxDynamicClients,

      --sm16tat2saIPSourceGuardStaticTable
        sm16tat2saIPSourceGuardStaticPort,
        sm16tat2saIPSourceGuardStaticIPAddress,
        sm16tat2saIPSourceGuardStaticMACAddress,
        sm16tat2saIPSourceGuardStaticRowStatus,

      --sm16tat2saIPSourceGuardDynamicTable
        sm16tat2saIPSourceGuardDynamicPort,
        sm16tat2saIPSourceGuardDynamicIPAddress,
        sm16tat2saIPSourceGuardDynamicMACAddress
    }
    STATUS current
    DESCRIPTION
        "The collection of objects which are used to
        indicate ip source guard information."
    ::= { sm16tat2saSecurityGroups 1 }

sm16tat2saARPInspectionGroup OBJECT-GROUP
    OBJECTS {
    --sm16tat2saARPInspection
        sm16tat2saARPInspectionMode,

      --sm16tat2saARPPortConfigTable
        sm16tat2saARPPortConfigMode,
        sm16tat2saARPPortConfigCheckVLAN,
        sm16tat2saARPPortConfigLogType,

      --sm16tat2saARPVlanConfigTable
        sm16tat2saARPVlanConfigVlanID,
        sm16tat2saARPVlanConfigLogType,
        sm16tat2saARPVlanConfigRowStatus,

      --sm16tat2saARPStaticTable
        sm16tat2saARPStaticPort,
        sm16tat2saARPStaticVlanID,
        sm16tat2saARPStaticMACAddress,
        sm16tat2saARPStaticIPAddress,
        sm16tat2saARPStaticRowStatus,

      --sm16tat2saARPDynamicTable
        sm16tat2saARPDynamicPort,
        sm16tat2saARPDynamicVLANId,
        sm16tat2saARPDynamicMACAddress,
        sm16tat2saARPDynamicIPAddress
    }
    STATUS current
    DESCRIPTION
        "The collection of objects which are used to
        indicate ARP inspection information."
    ::= { sm16tat2saSecurityGroups 2 }

sm16tat2saDHCPSnoopingGroup OBJECT-GROUP
    OBJECTS {
    --sm16tat2saDHCPSnooping
      --sm16tat2saDHCPSnoopingConfiguration
        sm16tat2saDHCPSnoopingMode,

        --sm16tat2saDHCPSnoopingPortModeConfigurationTable
        sm16tat2saDHCPSnoopingPortModeConfigurationMode,

      --sm16tat2saDynamicDHCPSnoopingTable
        sm16tat2saDynamicDHCPSnoopingMACAddress,
        sm16tat2saDynamicDHCPSnoopingVLANID,
        sm16tat2saDynamicDHCPSnoopingPort,
        sm16tat2saDynamicDHCPSnoopingIPAddress,
        sm16tat2saDynamicDHCPSnoopingIPSubnetMask,
        sm16tat2saDynamicDHCPSnoopingDHCPServer,

      --sm16tat2saPortSecLimitCtrl
        --sm16tat2saPortSecLimitCtrlSystemConf
        sm16tat2saPortSecurityMode,

          --sm16tat2saPortSecLimitCtrlTable
        sm16tat2saPortSecLimitCtrlPortMode,
        sm16tat2saPortSecLimitCtrlPortLimit,
        sm16tat2saPortSecLimitCtrlPortAction,
        sm16tat2saPortSecLimitCtrlPortState,
        sm16tat2saPortSecLimitCtrlPortReOpen,

        --sm16tat2saPortSecSwitchStatusTable
        sm16tat2saPortSecSwitchStatusState,
        sm16tat2saPortSecSwitchStatusMACCountCurrent
    }
    STATUS current
    DESCRIPTION
        "The collection of objects which are used to
        indicate DHCP snooping information."
    ::= { sm16tat2saSecurityGroups 3 }

sm16tat2saTACACSGroup OBJECT-GROUP
    OBJECTS {
    --sm16tat2saTACACS
        sm16tat2saTACACSGlobalConfigTimeout,
        sm16tat2saTACACSGlobalConfigDeadtime,
        sm16tat2saTACACSGlobalConfigKey,

      --sm16tat2saTACACSServerConfigTable
        sm16tat2saTACACSServerConfigHostname,
        sm16tat2saTACACSServerConfigPort,
        sm16tat2saTACACSServerConfigTimeout,
        sm16tat2saTACACSServerConfigKey,
        sm16tat2saTACACSServerConfigRowStatus
    }
    STATUS current
    DESCRIPTION
        "The collection of objects which are used to
        indicate TACACS information."
    ::= { sm16tat2saSecurityGroups 7 }

sm16tat2saAuthMethodGroup OBJECT-GROUP
    OBJECTS {
    --sm16tat2saAuthMethod
      --sm16tat2saAuthMethodConfigTable
        sm16tat2saAuthMethodConfigMethod1,
        sm16tat2saAuthMethodConfigMethod2,
        sm16tat2saAuthMethodConfigMethod3,
        sm16tat2saAuthMethodConfigServicePort,

      --sm16tat2saCmdAuthMethodConfigTable
        sm16tat2saCmdAuthMethodConfigMethods,
        sm16tat2saCmdAuthMethodConfigCmdLvl,
        sm16tat2saCmdAuthMethodConfigCfgCmd,
        sm16tat2saCmdAuthMethodConfigFallback,

      --sm16tat2saAcctAuthMethodConfigTable
        sm16tat2saAcctAuthMethodConfigMethods,
        sm16tat2saAcctAuthMethodConfigCmdLvl,
        sm16tat2saAcctAuthMethodConfigExec
    }
    STATUS current
    DESCRIPTION
        "The collection of objects which are used to
        indicate auth method information."
    ::= { sm16tat2saSecurityGroups 9 }

sm16tat2saAccessManagementConfigGroup OBJECT-GROUP
    OBJECTS {
    --sm16tat2saAccessManagementConfig
      --sm16tat2saAccessManagementConfigGlobals
        sm16tat2saAccessManagementConfigGlobalsAdminState,

      --sm16tat2saAccessManagementConfigIpv4Table
        sm16tat2saAccessManagementConfigIpv4VlanId,
        sm16tat2saAccessManagementConfigIpv4Address,
        sm16tat2saAccessManagementConfigIpv4MaskLength,
        sm16tat2saAccessManagementConfigIpv4WebServices,
        sm16tat2saAccessManagementConfigIpv4SnmpServices,
        sm16tat2saAccessManagementConfigIpv4TelnetServices,
        sm16tat2saAccessManagementConfigIpv4RowStatus
    }
    STATUS current
    DESCRIPTION
        "The collection of objects which are used to
        indicate access management information."
    ::= { sm16tat2saSecurityGroups 10 }

sm16tat2saSecurityCompliance MODULE-COMPLIANCE
    STATUS current
    DESCRIPTION
        "The compliance statement for devices supporting security."
    MODULE
        MANDATORY-GROUPS {
            sm16tat2saIPSourceGuardGroup,
            sm16tat2saARPInspectionGroup,
            sm16tat2saDHCPSnoopingGroup,
            sm16tat2saTACACSGroup,
            sm16tat2saAuthMethodGroup,
            sm16tat2saAccessManagementConfigGroup
        }
    ::= { sm16tat2saSecurityCompliances 1 }

-- ======================================================================================================================
sm16tat2saMaintenance OBJECT IDENTIFIER ::= { sm16tat2saProductId 4 }

sm16tat2saSoftware OBJECT IDENTIFIER ::= { sm16tat2saMaintenance 3 }
sm16tat2saConfig OBJECT IDENTIFIER ::= { sm16tat2saMaintenance 4 }

-- *************************************************************
-- Objects in the sm16tat2saMaintenance Group
-- *************************************************************

sm16tat2saRestartDevice OBJECT-TYPE
   SYNTAX ActivateCmd
   MAX-ACCESS read-write
   STATUS current
   DESCRIPTION
       "Command to restart the device."
   ::= { sm16tat2saMaintenance 1 }

sm16tat2saFactoryDefaults OBJECT-TYPE
   SYNTAX ActivateCmd
   MAX-ACCESS read-write
   STATUS current
   DESCRIPTION
       "Reset the configuration to Factory Defaults keep-ip."
   ::= { sm16tat2saMaintenance 2 }

--sm16tat2saSoftware
sm16tat2saSoftwareIpAddress OBJECT-TYPE
   SYNTAX IpAddress
   MAX-ACCESS read-write
   STATUS current
   DESCRIPTION
        "Get/Set the firmware tftp server."
   ::= { sm16tat2saSoftware 1 }

sm16tat2saSoftwareFileName OBJECT-TYPE
   SYNTAX DisplayString
   MAX-ACCESS read-write
   STATUS current
   DESCRIPTION
        "Get/Set the path and filename for firmware upgrading."
   ::= { sm16tat2saSoftware 2 }

sm16tat2saSoftwareUpgradeCmd OBJECT-TYPE
   SYNTAX INTEGER { noAction ( 0 ), tftpUpgrade ( 1 )}
   MAX-ACCESS read-write
   STATUS current
   DESCRIPTION
        "Firmware upgrade command.
         noAction(0 )- do nothing (read only).
         tftpUpgrade (1) - activate 'tftp' firmware upgrade"
   ::= { sm16tat2saSoftware 3 }

sm16tat2saSoftwareImageSelectionCmd OBJECT-TYPE
   SYNTAX ActivateCmd
   MAX-ACCESS read-write
   STATUS current
   DESCRIPTION
        "Activate firmware image selection.
         noAction(0) - do nothing - returned upon get.
         activate(1) - activate firmware image selection."
   ::= { sm16tat2saSoftware 4 }

sm16tat2saSaveStart OBJECT-TYPE
   SYNTAX INTEGER { none(0), yes(1) }
   MAX-ACCESS read-write
   STATUS current
   DESCRIPTION
       "default: 0
        0:none
        1:yes"
   ::= { sm16tat2saConfig 1 }

sm16tat2saBackupIpAddress OBJECT-TYPE
   SYNTAX IpAddress
   MAX-ACCESS read-write
   STATUS current
   DESCRIPTION
        "Get/Set the backup tftp server."
   ::= { sm16tat2saConfig 2 }

sm16tat2saBackupFilename OBJECT-TYPE
   SYNTAX DisplayString
   MAX-ACCESS read-write
   STATUS current
   DESCRIPTION
        "Get/Set the backup file."
   ::= { sm16tat2saConfig 3 }

sm16tat2saDoBackupConfig OBJECT-TYPE
   SYNTAX INTEGER{ doNothing(0), do(1) }
   MAX-ACCESS read-write
   STATUS current
   DESCRIPTION
        "Do export-config.
         Get this OID always return zero.
         1 - export.
         If BackupFilename is running-config, you must wait for some seconds to get the file."
   ::= { sm16tat2saConfig 4 }

sm16tat2saRestoreIpAddress OBJECT-TYPE
   SYNTAX IpAddress
   MAX-ACCESS read-write
   STATUS current
   DESCRIPTION
        "Get/Set the import tftp server."
   ::= { sm16tat2saConfig 5 }

sm16tat2saRestoreConfigName OBJECT-TYPE
   SYNTAX DisplayString
   MAX-ACCESS read-write
   STATUS current
   DESCRIPTION
       "Get/Set the import file path and name."
   ::= { sm16tat2saConfig 6 }

sm16tat2saRestoreDestinationName OBJECT-TYPE
   SYNTAX DisplayString
   MAX-ACCESS read-write
   STATUS current
   DESCRIPTION
       "Get/Set the import destination file name.
        Note: The file name default-config is reserved."
   ::= { sm16tat2saConfig 7 }

sm16tat2saRestoreMode OBJECT-TYPE
   SYNTAX INTEGER{ replace(0), merge(1) }
   MAX-ACCESS read-write
   STATUS current
   DESCRIPTION
        "When destination file is running-config, it can be replaced or merged.
         Other destination file must be replaced. If merge, don't care."
   ::= { sm16tat2saConfig 8 }

sm16tat2saDoRestoreConfig OBJECT-TYPE
   SYNTAX INTEGER{ doNothing(0), do(1) }
   MAX-ACCESS read-write
   STATUS current
   DESCRIPTION
        "Do export-config.
         Get this OID always return zero.
         1 - import."
   ::= { sm16tat2saConfig 9 }

sm16tat2saConfigListActivateTable OBJECT-TYPE
   SYNTAX SEQUENCE OF SM16TAT2SAConfigListActivateEntry
   MAX-ACCESS not-accessible
   STATUS current
   DESCRIPTION
       " "
   ::= { sm16tat2saConfig 10 }

sm16tat2saConfigListActivateEntry OBJECT-TYPE
   SYNTAX SM16TAT2SAConfigListActivateEntry
   MAX-ACCESS not-accessible
   STATUS current
   DESCRIPTION
       " "
   INDEX { sm16tat2saConfigListActivateIndex }
   ::= { sm16tat2saConfigListActivateTable 1 }

SM16TAT2SAConfigListActivateEntry ::= SEQUENCE {
   sm16tat2saConfigListActivateIndex Integer32,
   sm16tat2saConfigListActivateFilename DisplayString,
   sm16tat2saConfigListActivate INTEGER
}

sm16tat2saConfigListActivateIndex OBJECT-TYPE
   SYNTAX Integer32(1..4095)
   MAX-ACCESS not-accessible
   STATUS current
   DESCRIPTION
       " "
   ::= { sm16tat2saConfigListActivateEntry 1 }

sm16tat2saConfigListActivateFilename OBJECT-TYPE
   SYNTAX DisplayString
   MAX-ACCESS read-only
   STATUS current
   DESCRIPTION
       " "
   ::= { sm16tat2saConfigListActivateEntry 2 }

sm16tat2saConfigListActivate OBJECT-TYPE
   SYNTAX INTEGER { doNothing(0), do(1) }
   MAX-ACCESS read-write
   STATUS current
   DESCRIPTION
        "Do activate-config.
         Get this OID always return zero.
         1 - import."
   ::= { sm16tat2saConfigListActivateEntry 3 }

sm16tat2saConfigListDeleteTable OBJECT-TYPE
   SYNTAX SEQUENCE OF SM16TAT2SAConfigListDeleteEntry
   MAX-ACCESS not-accessible
   STATUS current
   DESCRIPTION
       " "
   ::= { sm16tat2saConfig 11 }

sm16tat2saConfigListDeleteEntry OBJECT-TYPE
   SYNTAX SM16TAT2SAConfigListDeleteEntry
   MAX-ACCESS not-accessible
   STATUS current
   DESCRIPTION
       " "
   INDEX { sm16tat2saConfigListDeleteIndex }
   ::= { sm16tat2saConfigListDeleteTable 1 }

SM16TAT2SAConfigListDeleteEntry ::= SEQUENCE {
   sm16tat2saConfigListDeleteIndex Integer32,
   sm16tat2saConfigListDeleteFilename DisplayString,
   sm16tat2saConfigListDelete INTEGER
}

sm16tat2saConfigListDeleteIndex OBJECT-TYPE
   SYNTAX Integer32(1..4095)
   MAX-ACCESS not-accessible
   STATUS current
   DESCRIPTION
       " "
   ::= { sm16tat2saConfigListDeleteEntry 1 }

sm16tat2saConfigListDeleteFilename OBJECT-TYPE
   SYNTAX DisplayString
   MAX-ACCESS read-only
   STATUS current
   DESCRIPTION
       " "
   ::= { sm16tat2saConfigListDeleteEntry 2 }

sm16tat2saConfigListDelete OBJECT-TYPE
   SYNTAX INTEGER { doNothing(0), do(1) }
   MAX-ACCESS read-write
   STATUS current
   DESCRIPTION
        "Do delete-config.
         Get this OID always return zero.
         1 - import."
   ::= { sm16tat2saConfigListDeleteEntry 3 }

-- *************************************************************
-- Start sm16tat2saSystemAccount group
-- *************************************************************
sm16tat2saMaintenanceConformance OBJECT IDENTIFIER ::= { sm16tat2saMaintenance 200 }
sm16tat2saMaintenanceCompliances OBJECT IDENTIFIER ::= { sm16tat2saMaintenanceConformance 1 }
sm16tat2saMaintenanceGroups OBJECT IDENTIFIER ::= { sm16tat2saMaintenanceConformance 2 }

sm16tat2saMaintenanceGroup OBJECT-GROUP
    OBJECTS {
        sm16tat2saRestartDevice,
        sm16tat2saFactoryDefaults,
      --sm16tat2saSoftware
        sm16tat2saSoftwareIpAddress,
        sm16tat2saSoftwareFileName,
        sm16tat2saSoftwareUpgradeCmd,
        sm16tat2saSoftwareImageSelectionCmd,

      --sm16tat2saConfig
        sm16tat2saSaveStart,
        sm16tat2saBackupIpAddress,
        sm16tat2saBackupFilename,
        sm16tat2saDoBackupConfig,
        sm16tat2saRestoreIpAddress,
        sm16tat2saRestoreConfigName,
        sm16tat2saRestoreDestinationName,
        sm16tat2saRestoreMode,
        sm16tat2saDoRestoreConfig,

        --sm16tat2saConfigListActivateTable
        sm16tat2saConfigListActivateFilename,
        sm16tat2saConfigListActivate,

        --sm16tat2saConfigListDeleteTable
        sm16tat2saConfigListDeleteFilename,
        sm16tat2saConfigListDelete
    }
    STATUS current
    DESCRIPTION
        "The collection of objects which are used to
        indicate maintenance information."
    ::= { sm16tat2saMaintenanceGroups 1 }

sm16tat2saMaintenanceCompliance MODULE-COMPLIANCE
    STATUS current
    DESCRIPTION
        "The compliance statement for devices supporting maintenance."
    MODULE
        MANDATORY-GROUPS {
            sm16tat2saMaintenanceGroup
        }
    ::= { sm16tat2saMaintenanceCompliances 1 }

-- ================================================================================================================
sm16tat2saTrap OBJECT IDENTIFIER ::= { sm16tat2saProductId 5 }

-- *************************************************************
-- Start sm16tat2saTrapEvent group
-- *************************************************************
sm16tat2saTrapEvent OBJECT IDENTIFIER ::= { sm16tat2saTrap 0 }

sm16tat2saEmergency NOTIFICATION-TYPE
  OBJECTS { sm16tat2saInformation }
  STATUS current
    DESCRIPTION
        "The severity level is Emergency. Emergency conditions."
    ::= { sm16tat2saTrapEvent 1 }

sm16tat2saAlert NOTIFICATION-TYPE
  OBJECTS { sm16tat2saInformation }
  STATUS current
    DESCRIPTION
        "The severity level is Alert. Alert conditions."
    ::= { sm16tat2saTrapEvent 2 }

sm16tat2saCritical NOTIFICATION-TYPE
  OBJECTS { sm16tat2saInformation }
  STATUS current
    DESCRIPTION
        "The severity level is Critical. Critical conditions."
    ::= { sm16tat2saTrapEvent 3 }

sm16tat2saError NOTIFICATION-TYPE
  OBJECTS { sm16tat2saInformation }
  STATUS current
    DESCRIPTION
        "The severity level is Error. Error conditions."
    ::= { sm16tat2saTrapEvent 4 }

sm16tat2saWarning NOTIFICATION-TYPE
  OBJECTS { sm16tat2saInformation }
  STATUS current
    DESCRIPTION
        "The severity level is Warning. Warning conditions."
    ::= { sm16tat2saTrapEvent 5 }

sm16tat2saNotice NOTIFICATION-TYPE
  OBJECTS { sm16tat2saInformation }
  STATUS current
    DESCRIPTION
        "The severity level is Notice. Notice conditions."
    ::= { sm16tat2saTrapEvent 6 }

sm16tat2saInformational NOTIFICATION-TYPE
  OBJECTS { sm16tat2saInformation }
  STATUS current
    DESCRIPTION
        "The severity level is Informational. Informational conditions."
    ::= { sm16tat2saTrapEvent 7 }

sm16tat2saDebug NOTIFICATION-TYPE
  OBJECTS { sm16tat2saInformation }
  STATUS current
    DESCRIPTION
        "The severity level is Debug. Debug conditions."
    ::= { sm16tat2saTrapEvent 8 }

sm16tat2saTrapVariable OBJECT IDENTIFIER ::= { sm16tat2saTrap 2 }

sm16tat2saInformation OBJECT-TYPE
    SYNTAX DisplayString
    MAX-ACCESS read-only
    STATUS current
    DESCRIPTION
        "Trap information."
    ::= { sm16tat2saTrapVariable 1 }

sm16tat2saZTPTrap OBJECT IDENTIFIER ::= { sm16tat2saTrap 3 }
sm16tat2saZTPTrapEvent OBJECT IDENTIFIER ::= { sm16tat2saZTPTrap 0 }
sm16tat2saZTPOnboardTrap NOTIFICATION-TYPE
  OBJECTS { sm16tat2saInformation }
  STATUS current
    DESCRIPTION
        "The severity level is Emergency. Emergency conditions."
    ::= { sm16tat2saZTPTrapEvent 1 }

-- *************************************************************
-- Start sm16tat2saTrap group
-- *************************************************************
sm16tat2saTrapConformance OBJECT IDENTIFIER ::= { sm16tat2saTrap 200 }
sm16tat2saTrapCompliances OBJECT IDENTIFIER ::= { sm16tat2saTrapConformance 1 }
sm16tat2saTrapGroups OBJECT IDENTIFIER ::= { sm16tat2saTrapConformance 2 }

sm16tat2saTrapEventGroup NOTIFICATION-GROUP
    NOTIFICATIONS {
    --sm16tat2saTrapEvent
        sm16tat2saEmergency,
        sm16tat2saAlert,
        sm16tat2saCritical,
        sm16tat2saError,
        sm16tat2saWarning,
        sm16tat2saNotice,
        sm16tat2saInformational,
        sm16tat2saDebug
    }
    STATUS current
    DESCRIPTION
        "The collection of objects which are used to
        indicate trap event information."
    ::= { sm16tat2saTrapGroups 1 }

sm16tat2saTrapVariableGroup OBJECT-GROUP
    OBJECTS {
    --sm16tat2saTrapVariable
        sm16tat2saInformation
    }
    STATUS current
    DESCRIPTION
        "The collection of objects which are used to
        indicate trap variable information."
    ::= { sm16tat2saTrapGroups 2 }

sm16tat2saZTPTrapGroup NOTIFICATION-GROUP
    NOTIFICATIONS {
    --sm16tat2saZTPTrap
        sm16tat2saZTPOnboardTrap
    }
    STATUS current
    DESCRIPTION
        "The collection of objects which are used to
        indicate trap event information."
    ::= { sm16tat2saTrapGroups 3 }

sm16tat2saTrapCompliance MODULE-COMPLIANCE
    STATUS current
    DESCRIPTION
        "The compliance statement for devices supporting trap."
    MODULE
        MANDATORY-GROUPS {
            sm16tat2saTrapEventGroup,
            sm16tat2saTrapVariableGroup

            ,sm16tat2saZTPTrapGroup

        }
    ::= { sm16tat2saTrapCompliances 1 }

END
