TN-SM24DP4XA-FUNCTION-MIB DEFINITIONS ::= BEGIN

IMPORTS
    DisplayString,MacAddress,TEXTUAL-CONVENTION,RowStatus                                              FROM SNMPv2-TC
    MODULE-COMPLIANCE,OBJECT-GROUP, NOTIFICATION-GROUP                                                 FROM SNMPv2-CONF
    ifIndex                                                                                            FROM IF-MIB
    enterprises,MODULE-IDENTITY,OBJECT-TYPE,NOTIFICATION-TYPE,Unsigned32,Integer32,Counter32,Counter64,IpAddress  FROM SNMPv2-SMI
--  PortList                                                                                           FROM Q-BRIDGE-MIB
    InetAddress, InetAddressType                                                                       FROM INET-ADDRESS-MIB
    OwnerString                                                                                        FROM RMON-MIB
    sysObjectID                                                                                        FROM SNMPv2-MIB
    SnmpAdminString                                                                                    FROM SNMP-FRAMEWORK-MIB;
--  MacAddress FROM BRIDGE-MIB;

transition MODULE-IDENTITY
        LAST-UPDATED "201405300000Z"
        ORGANIZATION "Corp."
        CONTACT-INFO
            " "
        DESCRIPTION
            " "
		REVISION      "201405300000Z"
        DESCRIPTION
		"Rev 1.0 Initial version."
        ::= { enterprises 868 }


-- =======================================================================================================================

     OperState ::= TEXTUAL-CONVENTION
       STATUS         current
       DESCRIPTION
                      "Oper state."
       SYNTAX         INTEGER  { up ( 1 ) , down ( 2 ) }

     AdminMode ::= TEXTUAL-CONVENTION
       STATUS      current
       DESCRIPTION
            "The Admin state - default: disable(0)."
       SYNTAX  INTEGER { disable(0), enable(1) }

     AdminMode2 ::= TEXTUAL-CONVENTION
       STATUS      current
       DESCRIPTION
            "The Admin state - default: disable(0)."
       SYNTAX  INTEGER { disable(0), enable(1), notSupported(2) }

     ActivateCmd ::= TEXTUAL-CONVENTION
       STATUS      current
       DESCRIPTION
            "Used to activate commands. default: noAction(0). "
       SYNTAX         INTEGER  {  noAction ( 0 ),
                                  activate ( 1 )
                               }

     KeyType ::= TEXTUAL-CONVENTION
       STATUS      current
       DESCRIPTION
           "The key type specifying the key generated for frames received
            on the port.
            0 : Normal,
            1 : Double Tag,
            2 : IP Address,
            3 : MAC and IP Address."
        SYNTAX      INTEGER  { normal  ( 0 ),
                               doubleTag ( 1 ),
                               ipAddr ( 2 ),
                               macAndIpAddr ( 3 )
                             }

     FrameRate ::= TEXTUAL-CONVENTION
       STATUS      current
       DESCRIPTION
           "The values for frame rate"
       SYNTAX       INTEGER {
                            threeHundredFramesPerSec (0),
                            oneHundredFramesPerSec (1),
                            tenFramesPerSec (2),
                            oneFramePerSec (3),
                            sixFramesPerMin (4),
                            oneFramePerMin  (5),
                            sixFramesPerHour (6)
                            }

     DayOfWeek ::= TEXTUAL-CONVENTION
       STATUS      current
       DESCRIPTION
            "Used to set the days of the week."
       SYNTAX       INTEGER {mon(1),tue(2),wed(3),thur(4),
                             fri(5),sat(6),sun(7) }

     Month ::= TEXTUAL-CONVENTION
       STATUS      current
       DESCRIPTION
            "Used to set the month."
       SYNTAX       INTEGER {jan(1),feb(2),march(3),april(4),
                             may(5),june(6),july(7),aug(8),
                             sept(9),oct(10),nov(11),dec(12)}


switch                                                          OBJECT IDENTIFIER ::= { transition 2 }

tn-sm24dp4xaProductId                                          OBJECT IDENTIFIER ::= { switch 77 }

sm24dp4xaProductId                                             OBJECT IDENTIFIER ::= { tn-sm24dp4xaProductId 3 }

sm24dp4xaSystem                                                OBJECT IDENTIFIER ::= { sm24dp4xaProductId 1 }

sm24dp4xaSystemInformation                                     OBJECT IDENTIFIER ::= { sm24dp4xaSystem 1 }

sm24dp4xaSystemInfoTable OBJECT-TYPE
   SYNTAX      SEQUENCE OF SM24DP4XASystemInfoEntry
   MAX-ACCESS  not-accessible
   STATUS      current
   DESCRIPTION
       " Configure System Information Table. "
   ::= { sm24dp4xaSystemInformation 1 }

sm24dp4xaSystemInfoEntry OBJECT-TYPE
   SYNTAX      SM24DP4XASystemInfoEntry
   MAX-ACCESS  not-accessible
   STATUS      current
   DESCRIPTION
       " "
   INDEX    { sm24dp4xaSystemInfoSwitchIndex }
   ::= { sm24dp4xaSystemInfoTable 1 }

SM24DP4XASystemInfoEntry ::= SEQUENCE {
   sm24dp4xaSystemInfoSwitchIndex        Integer32,
   sm24dp4xaSystemInfoModelName          DisplayString,
   sm24dp4xaSystemInfoSystemDescript     DisplayString,
   sm24dp4xaSystemInfoLocation           DisplayString,
   sm24dp4xaSystemInfoContact            DisplayString,
   sm24dp4xaSystemInfoSystemName         DisplayString,
   sm24dp4xaSystemInfoSystemDate         DisplayString,
   sm24dp4xaSystemInfoSystemUptime       DisplayString,
   sm24dp4xaSystemInfoBootloaderVersion  DisplayString,
   sm24dp4xaSystemInfoFirmwareVersion    DisplayString,
   sm24dp4xaSystemInfoHardwareVersion    DisplayString,
   sm24dp4xaSystemInfoMechanicalVersion  DisplayString,
   sm24dp4xaSystemInfoSerialNumber       DisplayString,
   sm24dp4xaSystemInfoHostMACAddress     DisplayString,
   sm24dp4xaSystemInfoMemory             DisplayString,
   sm24dp4xaSystemInfoFlash              DisplayString,
   sm24dp4xaSystemInfoFanSpeed           DisplayString,
   sm24dp4xaSystemInfoPowers             DisplayString,   
--   sm24dp4xaSystemInfoTemperature1       DisplayString,
--   sm24dp4xaSystemInfoTemperature2       DisplayString,
   sm24dp4xaSystemInfoCPULoad            DisplayString
}

sm24dp4xaSystemInfoSwitchIndex OBJECT-TYPE
   SYNTAX      Integer32 (0..16)
   MAX-ACCESS  not-accessible
   STATUS      current
   DESCRIPTION
       "Switch Index."
   ::= { sm24dp4xaSystemInfoEntry 1 }

sm24dp4xaSystemInfoModelName OBJECT-TYPE
   SYNTAX       DisplayString
   MAX-ACCESS   read-only
   STATUS       current
   DESCRIPTION
       " "
   ::= { sm24dp4xaSystemInfoEntry 2 }

sm24dp4xaSystemInfoSystemDescript OBJECT-TYPE
   SYNTAX       DisplayString
   MAX-ACCESS   read-only
   STATUS       current
   DESCRIPTION
       " "
   ::= { sm24dp4xaSystemInfoEntry 3 }

sm24dp4xaSystemInfoLocation OBJECT-TYPE
   SYNTAX       DisplayString
   MAX-ACCESS   read-write
   STATUS       current
   DESCRIPTION
       " "
   ::= { sm24dp4xaSystemInfoEntry 4 }

sm24dp4xaSystemInfoContact OBJECT-TYPE
   SYNTAX       DisplayString
   MAX-ACCESS   read-write
   STATUS       current
   DESCRIPTION
       " "
   ::= { sm24dp4xaSystemInfoEntry 5 }

sm24dp4xaSystemInfoSystemName OBJECT-TYPE
   SYNTAX       DisplayString
   MAX-ACCESS   read-write
   STATUS       current
   DESCRIPTION
       " "
   ::= { sm24dp4xaSystemInfoEntry 6 }

sm24dp4xaSystemInfoSystemDate OBJECT-TYPE
   SYNTAX       DisplayString
   MAX-ACCESS   read-only
   STATUS       current
   DESCRIPTION
       " "
   ::= { sm24dp4xaSystemInfoEntry 7 }

sm24dp4xaSystemInfoSystemUptime OBJECT-TYPE
   SYNTAX       DisplayString
   MAX-ACCESS   read-only
   STATUS       current
   DESCRIPTION
       " "
   ::= { sm24dp4xaSystemInfoEntry 8 }

sm24dp4xaSystemInfoBootloaderVersion OBJECT-TYPE
   SYNTAX       DisplayString
   MAX-ACCESS   read-only
   STATUS       current
   DESCRIPTION
       " "
   ::= { sm24dp4xaSystemInfoEntry 9 }

sm24dp4xaSystemInfoFirmwareVersion OBJECT-TYPE
   SYNTAX       DisplayString
   MAX-ACCESS   read-only
   STATUS       current
   DESCRIPTION
       " "
   ::= { sm24dp4xaSystemInfoEntry 10 }

sm24dp4xaSystemInfoHardwareVersion OBJECT-TYPE
   SYNTAX       DisplayString
   MAX-ACCESS   read-only
   STATUS       current
   DESCRIPTION
       " "
   ::= { sm24dp4xaSystemInfoEntry 11 }

sm24dp4xaSystemInfoMechanicalVersion OBJECT-TYPE
   SYNTAX       DisplayString
   MAX-ACCESS   read-only
   STATUS       current
   DESCRIPTION
       " "
   ::= { sm24dp4xaSystemInfoEntry 12 }

sm24dp4xaSystemInfoSerialNumber OBJECT-TYPE
   SYNTAX       DisplayString
   MAX-ACCESS   read-only
   STATUS       current
   DESCRIPTION
       " "
   ::= { sm24dp4xaSystemInfoEntry 13 }

sm24dp4xaSystemInfoHostMACAddress OBJECT-TYPE
   SYNTAX       DisplayString
   MAX-ACCESS   read-only
   STATUS       current
   DESCRIPTION
       " "
   ::= { sm24dp4xaSystemInfoEntry 14 }

sm24dp4xaSystemInfoMemory OBJECT-TYPE
   SYNTAX       DisplayString
   MAX-ACCESS   read-only
   STATUS       current
   DESCRIPTION
       " "
   ::= { sm24dp4xaSystemInfoEntry 15 }

sm24dp4xaSystemInfoFlash OBJECT-TYPE
   SYNTAX       DisplayString
   MAX-ACCESS   read-only
   STATUS       current
   DESCRIPTION
       " "
   ::= { sm24dp4xaSystemInfoEntry 16 }

sm24dp4xaSystemInfoFanSpeed OBJECT-TYPE
   SYNTAX       DisplayString
   MAX-ACCESS   read-only
   STATUS       current
   DESCRIPTION
       " "
   ::= { sm24dp4xaSystemInfoEntry 17 }   
   
sm24dp4xaSystemInfoPowers OBJECT-TYPE
   SYNTAX       DisplayString
   MAX-ACCESS   read-only
   STATUS       current
   DESCRIPTION
       " "
   ::= { sm24dp4xaSystemInfoEntry 20 }   
   
--sm24dp4xaSystemInfoTemperature1 OBJECT-TYPE
--   SYNTAX       DisplayString
--   MAX-ACCESS   read-only
--   STATUS       current
--   DESCRIPTION
--       " "
--   ::= { sm24dp4xaSystemInfoEntry 22 }
--
--sm24dp4xaSystemInfoTemperature2 OBJECT-TYPE
--   SYNTAX       DisplayString
--   MAX-ACCESS   read-only
--   STATUS       current
--   DESCRIPTION
--       " "
--   ::= { sm24dp4xaSystemInfoEntry 23 }
   
sm24dp4xaSystemInfoCPULoad OBJECT-TYPE
   SYNTAX       DisplayString
   MAX-ACCESS   read-only
   STATUS       current
   DESCRIPTION
       "CPU Utilization."
   ::= { sm24dp4xaSystemInfoEntry 24 }     
   
sm24dp4xaSystemTimeConf                                    OBJECT IDENTIFIER ::= { sm24dp4xaSystem 2 }

sm24dp4xaSystemNTP                                      OBJECT IDENTIFIER ::= { sm24dp4xaSystemTimeConf  1 }

sm24dp4xaSystemTime                                      OBJECT IDENTIFIER ::= { sm24dp4xaSystemTimeConf  2 }
sm24dp4xaSystemTimeZone                              OBJECT IDENTIFIER ::= { sm24dp4xaSystemTime 1 }
sm24dp4xaSystemTimeDaylightSaving             OBJECT IDENTIFIER ::= { sm24dp4xaSystemTime 2 }
sm24dp4xaSystemTimeConfiguration              OBJECT IDENTIFIER ::= { sm24dp4xaSystemTime 3 }

    --
-- =======================================================================================================================
-- Objects in the sm24dp4xaSystemNTP Group
-- =======================================================================================================================
    sm24dp4xaSystemNTPMode OBJECT-TYPE
               SYNTAX       INTEGER {useLocal(0),useNTP(1)}
               MAX-ACCESS   read-write
               STATUS       current
               DESCRIPTION
                   "The system NTP Mode.
                    useLocal(0) : Use Local Settings,
                    useNTP(1)   : Use NTP Server."
               DEFVAL  { useLocal }
               ::= {     sm24dp4xaSystemNTP 1 }

    sm24dp4xaSystemNTPServer1    OBJECT-TYPE
               SYNTAX            DisplayString
               MAX-ACCESS        read-write
               STATUS            current
               DESCRIPTION
                   "Get/Set the NTP Time Server1.
                    You can use the IP address or domain name."
               ::= {     sm24dp4xaSystemNTP 2 }

    sm24dp4xaSystemNTPServer2    OBJECT-TYPE
               SYNTAX            DisplayString
               MAX-ACCESS        read-write
               STATUS            current
               DESCRIPTION
                   "Get/Set the NTP Time Server2.
                    You can use the IP address or domain name."
               ::= {     sm24dp4xaSystemNTP 3 }

    sm24dp4xaSystemNTPServer3    OBJECT-TYPE
               SYNTAX            DisplayString
               MAX-ACCESS        read-write
               STATUS            current
               DESCRIPTION
                   "Get/Set the NTP Time Server3.
                    You can use the IP address or domain name."
               ::= {     sm24dp4xaSystemNTP 4 }

    sm24dp4xaSystemNTPServer4    OBJECT-TYPE
               SYNTAX            DisplayString
               MAX-ACCESS        read-write
               STATUS            current
               DESCRIPTION
                   "Get/Set the NTP Time Server4.
                    You can use the IP address or domain name."
               ::= {     sm24dp4xaSystemNTP 5 }

    sm24dp4xaSystemNTPServer5    OBJECT-TYPE
               SYNTAX            DisplayString
               MAX-ACCESS        read-write
               STATUS            current
               DESCRIPTION
                   "Get/Set the NTP Time Server5.
                    You can use the IP address or domain name."
               ::= {     sm24dp4xaSystemNTP 6 }


--
-- =======================================================================================================================
-- Objects in the sm24dp4xaSystemTime Group
-- =======================================================================================================================
--sm24dp4xaSystemTimeZone

    sm24dp4xaSystemTimeZoneConf OBJECT-TYPE
               SYNTAX       Integer32(-7200..7201)
               MAX-ACCESS   read-write
               STATUS       current
               DESCRIPTION
                   "Get/Set the NTP Time Zone.
                    The value range is between -7200 and 7201 (minutes).
                    0 : None.
                    -7200 : (GMT-12:00).
                    -6600 : (GMT-11:00).
                    -6000 : (GMT-10:00).
                    -5400 : (GMT-09:00).
                    -4800 : (GMT-08:00)Pacific Time.
                    -4801 : (GMT-08:00)Tijuana, Baja California.
                    -4200 : (GMT-07:00)Arizona.
                    -4201 : (GMT-07:00)Chihuahua, La Paz, Mazatlan - New.
                    -4202 : (GMT-07:00)Chihuahua, La Paz, Mazatlan - Old.
                    -4203 : (GMT-07:00)Mountain Time.
                    -3600 : (GMT-06:00)Central America.
                    -3601 : (GMT-06:00)Central Time.
                    -3602 : (GMT-06:00)Guadalajara, Mexico City, Monterrey - New.
                    -3603 : (GMT-06:00)Guadalajara, Mexico City, Monterrey - Old.
                    -3604 : (GMT-06:00)Saskatchewan.
                    -3000 : (GMT-05:00)Bogota, Lima, Quito, Rio Branco.
                    -3001 : (GMT-05:00)Eastern Time.
                    -3002 : (GMT-05:00)Indiana.
                    -2700 : (GMT-04:30).
                    -2400 : (GMT-04:00)Atlantic Time.
                    -2401 : (GMT-04:00)La Paz.
                    -2402 : (GMT-04:00)Manaus.
                    -2403 : (GMT-04:00)Santiago.
                    -2100 : (GMT-03:30).
                    -1800 : (GMT-03:00)Brasilia.
                    -1801 : (GMT-03:00)Buenos Aires.
                    -1802 : (GMT-03:00)Georgetown.
                    -1803 : (GMT-03:00)Greenland.
                    -1804 : (GMT-03:00)Montevideo.
                    -1805 : (GMT-02:00).
                    -600 : (GMT-01:00)Azores.
                    -601 : (GMT-01:00)Cape Verde Is.
                    1 : (GMT) Casablanca.
                    2 : (GMT) Greenwich Mean Time.
                    3 : (GMT) Monrovia, Reykjavik.
                    600 : (GMT+01:00) Amsterdam, Berlin, Bern, Rome, Stockholm, Vienna.
                    601 : (GMT+01:00) Belgrade, Bratislava, Budapest, Ljubljana, Prague.
                    602 : (GMT+01:00) Brussels, Copenhagen, Madrid, Paris.
                    603 : (GMT+01:00) Sarajevo, Skopje, Warsaw, Zagreb.
                    604 : (GMT+01:00) West Central Africa.
                    1200 : (GMT+02:00) Amman.
                    1201 : (GMT+02:00) Athens, Bucharest, Istanbul.
                    1202 : (GMT+02:00) Beirut.
                    1203 : (GMT+02:00) Cairo.
                    1204 : (GMT+02:00) Harare, Pretoria.
                    1205 : (GMT+02:00) Helsinki, Kyiv, Riga, Sofia, Tallinn, Vilnius.
                    1206 : (GMT+02:00) Jerusalem.
                    1207 : (GMT+02:00) Minsk.
                    1208 : (GMT+02:00) Windhoek.
                    1800 : (GMT+03:00) Baghdad.
                    1801 : (GMT+03:00) Kuwait, Riyadh.
                    1802 : (GMT+03:00) Moscow, St. Petersburg, Volgograd.
                    1803 : (GMT+03:00) Nairobi.
                    1804 : (GMT+03:00) Tbilisi.
                    2100 : (GMT+03:30) Tehran.
                    2400 : (GMT+04:00) Abu Dhabi, Muscat.
                    2401 : (GMT+04:00) Baku.
                    2402 : (GMT+04:00) Caucasus Standard Time.
                    2403 : (GMT+04:00) Port Louis.
                    2404 : (GMT+04:00) Yerevan.
                    2700 : (GMT+04:30) Kabul.
                    3000 : (GMT+05:00) Ekaterinburg.
                    3001 : (GMT+05:00) Islamabad, Karachi.
                    3002 : (GMT+05:00) Tashkent.
                    3300 : (GMT+05:30) Chennai, Kolkata, Mumbai, New Delhi.
                    3301 : (GMT+05:30) Sri Jayawardenepura.
                    3455 : (GMT+05:45) Kathmandu.
                    3600 : (GMT+06:00) Almaty, Novosibirsk.
                    3601 : (GMT+06:00) Astana, Dhaka.
                    3600 : (GMT+06:30) Yangon (Rangoon).
                    4200 : (GMT+07:00) Bangkok, Hanoi, Jakarta.
                    4201 : (GMT+07:00) Krasnoyarsk.
                    4800 : (GMT+08:00) Beijing, Chongqing, Hong Kong, Urumqi.
                    4801 : (GMT+08:00) Irkutsk, Ulaan Bataar.
                    4802 : (GMT+08:00) Kuala Lumpur, Singapore.
                    4803 : (GMT+08:00) Perth.
                    4804 : (GMT+08:00) Taipei.
                    5400 : (GMT+09:00) Osaka, Sapporo, Tokyo.
                    5401 : (GMT+09:00) Seoul.
                    5402 : (GMT+09:00) Yakutsk.
                    5700 : (GMT+09:30) Adelaide.
                    5701 : (GMT+09:30) Darwin.
                    6000 : (GMT+10:00) Brisbane.
                    6001 : (GMT+10:00) Canberra, Melbourne, Sydney.
                    6002 : (GMT+10:00) Guam, Port Moresby.
                    6003 : (GMT+10:00) Hobart.
                    6004 : (GMT+10:00) Vladivostok.
                    6600 : (GMT+11:00) Magadan, Solomon Is., New Caledonia.
                    7200 : (GMT+12:00) Auckland, Wellington.
                    7201 : (GMT+12:00) Fiji, Kamchatka, Marshall Is."
               ::= {     sm24dp4xaSystemTimeZone 1 }

    sm24dp4xaSystemTimeZoneAcronym OBJECT-TYPE
               SYNTAX       DisplayString
               MAX-ACCESS   read-write
               STATUS       current
               DESCRIPTION
                   "Acronym - User can set the acronym of the time zone.
                    This is a User configurable acronym to identify the time zone.
                    Range : 0 - 16 characters."
               ::= {     sm24dp4xaSystemTimeZone 2 }

--sm24dp4xaSystemTimeDaylightSaving

    sm24dp4xaSystemTimeDaylightSavingMode OBJECT-TYPE
               SYNTAX       INTEGER { disable(0), recurring(1), nonRecurring(2) }
               MAX-ACCESS   read-write
               STATUS       current
               DESCRIPTION
                   "The system Daylight Savings Mode.
                    disable(0)   : Disable.
                    recurring(1) : Recurring
                        - configure the Daylight Saving Time duration
                        to repeat the configuration every year.
                    nonRecurring(2): Non-Recurring - configure the Daylight Saving Time
                        duration for single time configuration."
               DEFVAL  { disable }
               ::= {     sm24dp4xaSystemTimeDaylightSaving 1 }

    sm24dp4xaSystemTimeDaylightSavingStartWeek OBJECT-TYPE
               SYNTAX       Integer32 (1..5)
               MAX-ACCESS   read-write
               STATUS       current
               DESCRIPTION
                   "Start time Week. Use in Recurring Mode.
                    Range : 1 - 5.
                    Default : 1."
               ::= {     sm24dp4xaSystemTimeDaylightSaving 2 }

    sm24dp4xaSystemTimeDaylightSavingStartDay OBJECT-TYPE
               SYNTAX       DayOfWeek
               MAX-ACCESS   read-write
               STATUS       current
               DESCRIPTION
                   "Start time Day. Use in Recurring Mode."
               DEFVAL  { mon }
               ::= {     sm24dp4xaSystemTimeDaylightSaving 3 }

    sm24dp4xaSystemTimeDaylightSavingStartMonth OBJECT-TYPE
               SYNTAX       Month
               MAX-ACCESS   read-write
               STATUS       current
               DESCRIPTION
                   "Start time Month."
               DEFVAL  { jan }
               ::= {     sm24dp4xaSystemTimeDaylightSaving 4 }

    sm24dp4xaSystemTimeDaylightSavingStartDate OBJECT-TYPE
               SYNTAX       Integer32 (1..31)
               MAX-ACCESS   read-write
               STATUS       current
               DESCRIPTION
                   "Start time Date. Use in Non-Recurring Mode.
                    Range : 1 - 31.
                    Default : 1."
               ::= {     sm24dp4xaSystemTimeDaylightSaving 5 }

    sm24dp4xaSystemTimeDaylightSavingStartYear OBJECT-TYPE
               SYNTAX       Integer32 (2000..2097)
               MAX-ACCESS   read-write
               STATUS       current
               DESCRIPTION
                   "Start time Year. Use in Non-Recurring Mode.
                    Range : 2000 - 2097.
                    Default : 2000."
               ::= {     sm24dp4xaSystemTimeDaylightSaving 6 }

    sm24dp4xaSystemTimeDaylightSavingStartHours OBJECT-TYPE
               SYNTAX       Integer32 (0..23)
               MAX-ACCESS   read-write
               STATUS       current
               DESCRIPTION
                   "Start time Hours.
                     Range : 0 - 23.
                     Default : 0."
               ::= {     sm24dp4xaSystemTimeDaylightSaving 7 }

    sm24dp4xaSystemTimeDaylightSavingStartMinutes OBJECT-TYPE
               SYNTAX       Integer32 (0..59)
               MAX-ACCESS   read-write
               STATUS       current
               DESCRIPTION
                   "Start time Minutes.
                    Range : 0 - 59.
                    Default : 0."
               ::= {     sm24dp4xaSystemTimeDaylightSaving 8 }

    sm24dp4xaSystemTimeDaylightSavingEndWeek OBJECT-TYPE
               SYNTAX       Integer32 (1..5)
               MAX-ACCESS   read-write
               STATUS       current
               DESCRIPTION
                   "End time Week. Use in Recurring Mode.
                    Range : 1 - 5.
                    Default : 1."
               ::= {     sm24dp4xaSystemTimeDaylightSaving 9 }

    sm24dp4xaSystemTimeDaylightSavingEndDay OBJECT-TYPE
               SYNTAX       DayOfWeek
               MAX-ACCESS   read-write
               STATUS       current
               DESCRIPTION
                   "End time Day. Use in Recurring Mode."
               DEFVAL  { mon }
               ::= {     sm24dp4xaSystemTimeDaylightSaving 10 }

    sm24dp4xaSystemTimeDaylightSavingEndMonth OBJECT-TYPE
               SYNTAX       Month
               MAX-ACCESS   read-write
               STATUS       current
               DESCRIPTION
                   "End time Month."
              DEFVAL  { jan }
              ::= {     sm24dp4xaSystemTimeDaylightSaving 11 }

    sm24dp4xaSystemTimeDaylightSavingEndDate OBJECT-TYPE
               SYNTAX       Integer32 (1..31)
               MAX-ACCESS   read-write
               STATUS       current
               DESCRIPTION
                   "End time Date. Use in Non-Recurring Mode.
                    Range : 1 - 31.
                    Default : 1."
               ::= {     sm24dp4xaSystemTimeDaylightSaving 12 }

    sm24dp4xaSystemTimeDaylightSavingEndYear OBJECT-TYPE
               SYNTAX       Integer32 (2000..2097)
               MAX-ACCESS   read-write
               STATUS       current
               DESCRIPTION
                   "End time Year. Use in Non-Recurring Mode.
                    Range : 2000 - 2097.
                    Default : 2000."
               ::= {     sm24dp4xaSystemTimeDaylightSaving 13 }

    sm24dp4xaSystemTimeDaylightSavingEndHours OBJECT-TYPE
               SYNTAX       Integer32 (0..23)
               MAX-ACCESS   read-write
               STATUS       current
               DESCRIPTION
                   "End time Hours.
                    Range : 0 - 23.
                    Default : 0."
               ::= {     sm24dp4xaSystemTimeDaylightSaving 14 }

    sm24dp4xaSystemTimeDaylightSavingEndMinutes OBJECT-TYPE
               SYNTAX       Integer32 (0..59)
               MAX-ACCESS   read-write
               STATUS       current
               DESCRIPTION
                   "End time Minutes.
                    Range : 0 - 59.
                    Default : 0."
               ::= {     sm24dp4xaSystemTimeDaylightSaving 15 }

    sm24dp4xaSystemTimeDaylightSavingOffset OBJECT-TYPE
               SYNTAX       Integer32 (1..1440)
               MAX-ACCESS   read-write
               STATUS       current
               DESCRIPTION
                   "Offset - the number of minutes to add during Daylight Saving Time.
                    Range : 1 - 1440(Minutes).
                    Default : 1."
               ::= {     sm24dp4xaSystemTimeDaylightSaving 16 }

    sm24dp4xaSystemTimeConfigurationClockSource OBJECT-TYPE
               SYNTAX       Integer32
               MAX-ACCESS   read-write
               STATUS       current
               DESCRIPTION
                   "0:Use Local Settings.
                    1:Use NTP Server."
	           ::= {     sm24dp4xaSystemTimeConfiguration 1}

    sm24dp4xaSystemTimeConfigurationDateFormat OBJECT-TYPE
               SYNTAX       Integer32 (0|1|2)
               MAX-ACCESS   read-write
               STATUS       current
               DESCRIPTION
                   "The date format of the system.
				   0:yyyy-mm-dd
				   1:mm-dd-yyyy
				   2:dd-mm-yyyy"
	           ::= {     sm24dp4xaSystemTimeConfiguration 2}
			   
    sm24dp4xaSystemTimeConfigurationTimeFormat OBJECT-TYPE
               SYNTAX       Integer32 (0|1)
               MAX-ACCESS   read-write
               STATUS       current
               DESCRIPTION
                   "The time format of the system.
				   0:24-hr, format:hh:mm:ss
				   1:12-hr, format:hh:mm:ss am/pm"
	           ::= {     sm24dp4xaSystemTimeConfiguration 3}
			   
    sm24dp4xaSystemTimeConfigurationSystemDate OBJECT-TYPE
               SYNTAX       DisplayString
               MAX-ACCESS   read-write
               STATUS       current
               DESCRIPTION
                   "System date. Default format:yyyy-mm-dd.
                    When ClockSource is Use Local Settings, you can set this field."
	           ::= {     sm24dp4xaSystemTimeConfiguration 4}
			   
    sm24dp4xaSystemTimeConfigurationSystemTime OBJECT-TYPE
               SYNTAX       DisplayString
               MAX-ACCESS   read-write
               STATUS       current
               DESCRIPTION
                   "System date.
				    24-hr, format:hh:mm:ss
				    12-hr, format:hh:mm:ss am/pm
                    When ClockSource is Use Local Settings, you can set this field."
	           ::= {     sm24dp4xaSystemTimeConfiguration 5}			   

-- =======================================================================================================================
sm24dp4xaSystemAccount                                         OBJECT IDENTIFIER ::= { sm24dp4xaSystem 3 }

sm24dp4xaSystemAccountUsers                                     OBJECT IDENTIFIER  ::= { sm24dp4xaSystemAccount 1 }

--
-- =======================================================================================================================
-- Start sm24dp4xaUserConfig group
-- =======================================================================================================================
--sm24dp4xaUserConfigTable

    sm24dp4xaUserConfigTable OBJECT-TYPE
               SYNTAX      SEQUENCE OF     SM24DP4XAUserConfigEntry
               MAX-ACCESS  not-accessible
               STATUS      current
               DESCRIPTION
                   "The User Config Table. "
               ::= {     sm24dp4xaSystemAccountUsers 1 }

    sm24dp4xaUserConfigEntry OBJECT-TYPE
               SYNTAX          SM24DP4XAUserConfigEntry
               MAX-ACCESS  not-accessible
               STATUS      current
               DESCRIPTION
                   "The User Config Entry."
               INDEX    {    sm24dp4xaUserConfigIndex  }
               ::= {     sm24dp4xaUserConfigTable 1 }

    SM24DP4XAUserConfigEntry             ::= SEQUENCE {
                 sm24dp4xaUserConfigIndex            Integer32,
                 sm24dp4xaUserConfigUserName         DisplayString,
                 sm24dp4xaUserConfigPassword         DisplayString,
                 sm24dp4xaUserConfigPrivilegeLevel   Integer32,
                 sm24dp4xaUserConfigRowStatus        RowStatus
                }

    sm24dp4xaUserConfigIndex OBJECT-TYPE
               SYNTAX      Integer32 (1..4095)
               MAX-ACCESS  not-accessible
               STATUS      current
               DESCRIPTION
                   "The user Config Index. "
               ::= {     sm24dp4xaUserConfigEntry 1 }

    sm24dp4xaUserConfigUserName OBJECT-TYPE
               SYNTAX      DisplayString(SIZE (1..31))
               MAX-ACCESS  read-create
               STATUS      current
               DESCRIPTION
                   "A string identifying the user name for the entry.
                    string length: 1-31. "
               ::= {     sm24dp4xaUserConfigEntry 2 }

    sm24dp4xaUserConfigPassword OBJECT-TYPE
               SYNTAX      DisplayString(SIZE (0..31))
               MAX-ACCESS  read-create
               STATUS      current
               DESCRIPTION
                   "The password of the user.
                    string length: 0-31. "
               ::= {     sm24dp4xaUserConfigEntry 3 }

    sm24dp4xaUserConfigPrivilegeLevel OBJECT-TYPE
               SYNTAX      Integer32(1..15)
               MAX-ACCESS  read-create
               STATUS      current
               DESCRIPTION
                   "The privilege level of the user.If the privilege level
                    value is 15, it can access all groups.range: 1-15. "
               ::= {     sm24dp4xaUserConfigEntry 4 }

    sm24dp4xaUserConfigRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sm24dp4xaUserConfigEntry 5 }


--
-- =======================================================================================================================
-- Start sm24dp4xaPrivilegeLevelConfig group
-- =======================================================================================================================
--sm24dp4xaPrivilegeLevelConfigTable

    sm24dp4xaPrivilegeLevelConfigTable OBJECT-TYPE
               SYNTAX      SEQUENCE OF     SM24DP4XAPrivilegeLevelConfigEntry
               MAX-ACCESS  not-accessible
               STATUS      current
               DESCRIPTION
                   "The Privilege Level Config Table. "
               ::= {     sm24dp4xaSystemAccountUsers 2 }

    sm24dp4xaPrivilegeLevelConfigEntry OBJECT-TYPE
               SYNTAX          SM24DP4XAPrivilegeLevelConfigEntry
               MAX-ACCESS  not-accessible
               STATUS      current
               DESCRIPTION
                   "The Privilege Level Config Entry."
               INDEX    {    sm24dp4xaPrivilegeLevelIndex  }
               ::= {     sm24dp4xaPrivilegeLevelConfigTable 1 }

    SM24DP4XAPrivilegeLevelConfigEntry             ::= SEQUENCE {
                 sm24dp4xaPrivilegeLevelIndex                Integer32,
                 sm24dp4xaPrivilegeLevelGroupName            DisplayString,
                 sm24dp4xaPrivilegeLevelConfigReadOnly       Integer32,
                 sm24dp4xaPrivilegeLevelConfigReadWrite      Integer32,
                 sm24dp4xaPrivilegeLevelStatusReadOnly       Integer32,
                 sm24dp4xaPrivilegeLevelStatusReadWrite      Integer32
                 }

    sm24dp4xaPrivilegeLevelIndex OBJECT-TYPE
               SYNTAX      Integer32 (1..4095)
               MAX-ACCESS  not-accessible
               STATUS      current
               DESCRIPTION
                   "The Privilege Level Index. "
               ::= {     sm24dp4xaPrivilegeLevelConfigEntry 1 }

    sm24dp4xaPrivilegeLevelGroupName OBJECT-TYPE
               SYNTAX      DisplayString
               MAX-ACCESS  read-only
               STATUS      current
               DESCRIPTION
                   "The name identifying the privilege group."
               ::= {     sm24dp4xaPrivilegeLevelConfigEntry 2 }

    sm24dp4xaPrivilegeLevelConfigReadOnly OBJECT-TYPE
               SYNTAX      Integer32(1..15)
               MAX-ACCESS  read-write
               STATUS      current
               DESCRIPTION
                   "The privilege level of configuration read-only.If the
                    privilege level value is 15,it can access all groups.
                    range: 1-15.  "
               ::= {     sm24dp4xaPrivilegeLevelConfigEntry 3 }

    sm24dp4xaPrivilegeLevelConfigReadWrite OBJECT-TYPE
               SYNTAX      Integer32(1..15)
               MAX-ACCESS  read-write
               STATUS      current
               DESCRIPTION
                   "The privilege level of configuration/execute read/write.
                    If the privilege level value is 15,it can access all groups.
                    range: 1-15. "
               ::= {     sm24dp4xaPrivilegeLevelConfigEntry 4 }

    sm24dp4xaPrivilegeLevelStatusReadOnly OBJECT-TYPE
               SYNTAX      Integer32(1..15)
               MAX-ACCESS  read-write
               STATUS      current
               DESCRIPTION
                   "The privilege level of status/statistics read-only.
                    If the privilege level value is 15,it can access all groups.
                    range: 1-15. "
               ::= {     sm24dp4xaPrivilegeLevelConfigEntry 5 }

    sm24dp4xaPrivilegeLevelStatusReadWrite OBJECT-TYPE
               SYNTAX      Integer32(1..15)
               MAX-ACCESS  read-write
               STATUS      current
               DESCRIPTION
                   "The privilege level of status/statistics read-write.
                    If the privilege level value is 15,it can access all groups.
                    range: 1-15. "
               ::= {     sm24dp4xaPrivilegeLevelConfigEntry 6 }
-- =======================================================================================================================
sm24dp4xaIP                                                    OBJECT IDENTIFIER ::= { sm24dp4xaSystem 4 }

sm24dp4xaIPConfiguration OBJECT IDENTIFIER ::= { sm24dp4xaIP 1 }

sm24dp4xaMode OBJECT-TYPE
   SYNTAX      Integer32 (0|1)
   MAX-ACCESS  read-write
   STATUS      current
   DESCRIPTION
       "IP Configuration Mode.
        default:0
        0: Host
        1: Router"
   ::= {sm24dp4xaIPConfiguration 2 }

sm24dp4xaDNSServerSource1 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sm24dp4xaIPConfiguration 3 }
   
sm24dp4xaDNSServerSource2 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
		4. DNS configuration is derived from DHCPv6.
		5. DNS configuration is derived from DHCPv6 on specific VLAN.
		"
   ::= {sm24dp4xaIPConfiguration 4 }   
   
sm24dp4xaDNSServerSource3 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sm24dp4xaIPConfiguration 5 }  
   
sm24dp4xaDNSServerSource4 OBJECT-TYPE
   SYNTAX      Integer32 (0..5)
   MAX-ACCESS  read-write
   STATUS      current
   DESCRIPTION
       "DNS Server Source.
        0: No DNS configuration is applied
        1: DNS configuration is manually set
        2: DNS configuration is derived from DHCPv4
        3: DNS configuration is derived from DHCPv4 on specific VLAN.
	4. DNS configuration is derived from DHCPv6.
	5. DNS configuration is derived from DHCPv6 on specific VLAN.
	"
   ::= {sm24dp4xaIPConfiguration 6 }    

sm24dp4xaDNSServerValue1 OBJECT-TYPE
   SYNTAX      DisplayString
   MAX-ACCESS  read-write
   STATUS      current
   DESCRIPTION
       "DNS IPv4/IPv6 Address or VLAN value."
   ::= {sm24dp4xaIPConfiguration 7 }
   
sm24dp4xaDNSServerValue2 OBJECT-TYPE
   SYNTAX      DisplayString
   MAX-ACCESS  read-write
   STATUS      current
   DESCRIPTION
      "DNS IPv4/IPv6 Address or VLAN value."
   ::= {sm24dp4xaIPConfiguration 8 }   
   
sm24dp4xaDNSServerValue3 OBJECT-TYPE
   SYNTAX      DisplayString
   MAX-ACCESS  read-write
   STATUS      current
   DESCRIPTION
       "DNS IPv4/IPv6 Address or VLAN value."
   ::= {sm24dp4xaIPConfiguration 9 }    
   
sm24dp4xaDNSServerValue4 OBJECT-TYPE
   SYNTAX      DisplayString
   MAX-ACCESS  read-write
   STATUS      current
   DESCRIPTION
       "DNS IPv4/IPv6 Address or VLAN value."
   ::= {sm24dp4xaIPConfiguration 10 }   
   
sm24dp4xaDNSProxy OBJECT-TYPE
   SYNTAX      Integer32 (0|1)
   MAX-ACCESS  read-write
   STATUS      current
   DESCRIPTION
       "DNS Proxy enable/disable.
        default:0
        0: disable
        1: enable"
   ::= {sm24dp4xaIPConfiguration 11 }


sm24dp4xaIPInterfaces OBJECT IDENTIFIER ::= { sm24dp4xaIP 2 }

sm24dp4xaIPInterfacesDHCPPerPortMode OBJECT-TYPE
   SYNTAX      INTEGER { disable(0), enable(1) }
   MAX-ACCESS  read-write
   STATUS      current
   DESCRIPTION
       "The dhcp per-port mode for the interface.
        0: Disable,
        1: Enable,
        default: Disable. "
   ::= { sm24dp4xaIPInterfaces 1 }

sm24dp4xaIPInterfacesDHCPPerPortIPRangeLow OBJECT-TYPE
   SYNTAX      IpAddress
   MAX-ACCESS  read-write
   STATUS      current
   DESCRIPTION
       "The dhcp per-port ip low for the interface."
   ::= { sm24dp4xaIPInterfaces 2 }

sm24dp4xaIPInterfacesDHCPPerPortIPRangeHigh OBJECT-TYPE
   SYNTAX      IpAddress
   MAX-ACCESS  read-write
   STATUS      current
   DESCRIPTION
       "The dhcp per-port ip high for the interface."
   ::= { sm24dp4xaIPInterfaces 3 }

sm24dp4xaIPInterfacesDHCPPerPortApply OBJECT-TYPE
   SYNTAX      Integer32 (1)
   MAX-ACCESS  read-write
   STATUS      current
   DESCRIPTION
       "1: Apply DHCP Per Port settings."
   ::= { sm24dp4xaIPInterfaces 4 }
   
sm24dp4xaIPInterfacesDHCPPerPortVLAN OBJECT-TYPE
   SYNTAX      Integer32 (1..4095)
   MAX-ACCESS  read-write
   STATUS      current
   DESCRIPTION
       "dhcp per-port VLAN."
   ::= { sm24dp4xaIPInterfaces 6 }   
   
sm24dp4xaIPInterfacesTable OBJECT-TYPE
   SYNTAX      SEQUENCE OF SM24DP4XAIPInterfacesEntry
   MAX-ACCESS  not-accessible
   STATUS      current
   DESCRIPTION
       "A table of IP interface for switch."
    ::= { sm24dp4xaIPInterfaces 5 }

sm24dp4xaIPInterfacesEntry OBJECT-TYPE
    SYNTAX        SM24DP4XAIPInterfacesEntry
    MAX-ACCESS    not-accessible
    STATUS        current
    DESCRIPTION
        "An entry in the sm24dp4xaIPInterfacesTable."
    INDEX        { sm24dp4xaIPInterfacesIndex }
    ::= { sm24dp4xaIPInterfacesTable 1 }

SM24DP4XAIPInterfacesEntry ::=
    SEQUENCE {
        sm24dp4xaIPInterfacesIndex                       Integer32,
        sm24dp4xaIPInterfacesVLAN                        Integer32,
        sm24dp4xaIPInterfacesIPv4DHCP                    Integer32,
        sm24dp4xaIPInterfacesIPv4DHCPFallback            DisplayString,
        sm24dp4xaIPInterfacesIPv4DHCPCurrentLease        IpAddress,
        sm24dp4xaIPInterfacesIPv4Address                 IpAddress,
        sm24dp4xaIPInterfacesIPv4Mask                    Integer32,
	sm24dp4xaIPInterfacesIPv6DHCP                    Integer32,
	sm24dp4xaIPInterfacesIPv6RapidCommit             Integer32,
	sm24dp4xaIPInterfacesIPv6CurrentLease            DisplayString,
        sm24dp4xaIPInterfacesIPv6Address                 DisplayString,
        sm24dp4xaIPInterfacesIPv6Mask                    Integer32,
	sm24dp4xaIPInterfacesRowStatus                   RowStatus
    }

sm24dp4xaIPInterfacesIndex OBJECT-TYPE
   SYNTAX      Integer32 (1..128)
   MAX-ACCESS  not-accessible
   STATUS      current
   DESCRIPTION
       "interface table index"
   ::= {sm24dp4xaIPInterfacesEntry 1 }

sm24dp4xaIPInterfacesVLAN OBJECT-TYPE
   SYNTAX      Integer32 (1..4095)
   MAX-ACCESS  read-write
   STATUS      current
   DESCRIPTION
       "VLAN ID for interface, range: 1-4095."
   ::= {sm24dp4xaIPInterfacesEntry 2 }

sm24dp4xaIPInterfacesIPv4DHCP OBJECT-TYPE
   SYNTAX      Integer32 (0|1)
   MAX-ACCESS  read-write
   STATUS      current
   DESCRIPTION
       "IPv4 DHCP Setting for interface.
        default:0
        0: disable
        1: enable"
   ::= {sm24dp4xaIPInterfacesEntry 3 }

sm24dp4xaIPInterfacesIPv4DHCPFallback OBJECT-TYPE
   SYNTAX      DisplayString
   MAX-ACCESS  read-write
   STATUS      current
   DESCRIPTION
       "IPv4 DHCP fallbcak. range: 1-4294967295 seconds."
   ::= {sm24dp4xaIPInterfacesEntry 4 }


sm24dp4xaIPInterfacesIPv4DHCPCurrentLease OBJECT-TYPE
   SYNTAX      IpAddress
   MAX-ACCESS  read-only
   STATUS      current
   DESCRIPTION
       "IPv4 DHCP Current Lease Address for interface."
   ::= {sm24dp4xaIPInterfacesEntry 5 }


sm24dp4xaIPInterfacesIPv4Address OBJECT-TYPE
   SYNTAX      IpAddress
   MAX-ACCESS  read-write
   STATUS      current
   DESCRIPTION
       "IPv4 address for interface."
   ::= {sm24dp4xaIPInterfacesEntry 6 }

sm24dp4xaIPInterfacesIPv4Mask OBJECT-TYPE
   SYNTAX      Integer32 (1..32)
   MAX-ACCESS  read-write
   STATUS      current
   DESCRIPTION
       "IPv4 mask for interface."
   ::= { sm24dp4xaIPInterfacesEntry 7 }

sm24dp4xaIPInterfacesIPv6DHCP OBJECT-TYPE
   SYNTAX      Integer32 (0|1)
   MAX-ACCESS  read-write
   STATUS      current
   DESCRIPTION
       "IPv6 DHCP Setting for interface.
        default:0
        0: disable
        1: enable"
   ::= {sm24dp4xaIPInterfacesEntry 8 } 
   
sm24dp4xaIPInterfacesIPv6RapidCommit OBJECT-TYPE
   SYNTAX      Integer32 (0|1)
   MAX-ACCESS  read-write
   STATUS      current
   DESCRIPTION
       "Enable the DHCPv6 Rapid-Commit option.
        default:0
        0: disable
        1: enable"
   ::= {sm24dp4xaIPInterfacesEntry 9 }    
   
sm24dp4xaIPInterfacesIPv6CurrentLease OBJECT-TYPE
   SYNTAX      DisplayString
   MAX-ACCESS  read-only
   STATUS      current
   DESCRIPTION
       "IPv6 DHCP Current Lease Address for interface."
   ::= {sm24dp4xaIPInterfacesEntry 10 }

   
sm24dp4xaIPInterfacesIPv6Address OBJECT-TYPE
   SYNTAX      DisplayString (SIZE (0..30))
   MAX-ACCESS  read-write
   STATUS      current
   DESCRIPTION
       "IPv6 address for interface."
   ::= { sm24dp4xaIPInterfacesEntry 11 }

sm24dp4xaIPInterfacesIPv6Mask OBJECT-TYPE
   SYNTAX      Integer32 (1..128)
   MAX-ACCESS  read-write
   STATUS      current
   DESCRIPTION
       "IPv6 mask for interface."
   ::= { sm24dp4xaIPInterfacesEntry 12 }

sm24dp4xaIPInterfacesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sm24dp4xaIPInterfacesEntry 13 }
   

sm24dp4xaIPRoutes OBJECT IDENTIFIER ::= { sm24dp4xaIP 3 }

sm24dp4xaIPRoutesTable OBJECT-TYPE
   SYNTAX      SEQUENCE OF SM24DP4XAIPRoutesEntry
   MAX-ACCESS  not-accessible
   STATUS      current
   DESCRIPTION
       "IP routes table for switch."
    ::= { sm24dp4xaIPRoutes 1 }

sm24dp4xaIPRoutesEntry OBJECT-TYPE
    SYNTAX        SM24DP4XAIPRoutesEntry
    MAX-ACCESS    not-accessible
    STATUS        current
    DESCRIPTION
        "Entry in the sm24dp4xaIPRoutesTable."
    INDEX        { sm24dp4xaIPRoutesIndex }
    ::= { sm24dp4xaIPRoutesTable 1 }

SM24DP4XAIPRoutesEntry ::=
    SEQUENCE {
        sm24dp4xaIPRoutesIndex                       Integer32,
        sm24dp4xaIPRoutesNetwork                     DisplayString,
        sm24dp4xaIPRoutesMaskLength                  Integer32,
        sm24dp4xaIPRoutesGateway                     DisplayString,
        sm24dp4xaIPRoutesNextHopVLAN                 Integer32,
	sm24dp4xaIPRoutesRowStatus                   RowStatus
    }

sm24dp4xaIPRoutesIndex OBJECT-TYPE
   SYNTAX      Integer32 (1..32)
   MAX-ACCESS  not-accessible
   STATUS      current
   DESCRIPTION
       "routes table index"
   ::= {sm24dp4xaIPRoutesEntry 2 }

sm24dp4xaIPRoutesNetwork OBJECT-TYPE
   SYNTAX      DisplayString (SIZE (0..30))
   MAX-ACCESS  read-write
   STATUS      current
   DESCRIPTION
       "IPv4/IPv6 Network address.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry.
        If Set IPRoutesNetwork, please also set IPRoutesMaskLength, IPRoutesGateway, IPRoutesNextHopVLAN."
   ::= {sm24dp4xaIPRoutesEntry 3 }

sm24dp4xaIPRoutesMaskLength OBJECT-TYPE
   SYNTAX      Integer32 (1..32)
   MAX-ACCESS  read-write
   STATUS      current
   DESCRIPTION
       "IPv4/IPv6 mask length.
        Please set IPRoutesNetwork first.
        Note: All entries in routes table will be sort by 1.network address 2.mask length 3. gateway 4. next hop VLAN, if you add/modify an entry, all entries will be reordered. Please check all entries in table to find your modified entry after set/add an entry."
   ::= { sm24dp4xaIPRoutesEntry 4 }

sm24dp4xaIPRoutesGateway OBJECT-TYPE
   SYNTAX      DisplayString (SIZE (0..30))
   MAX-ACCESS  read-write
   STATUS      current
   DESCRIPTION
       "IPv4/IPv6 Gateway.
        Please set IPRoutesNetwork first.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry."
   ::= {sm24dp4xaIPRoutesEntry 5 }

sm24dp4xaIPRoutesNextHopVLAN OBJECT-TYPE
   SYNTAX      Integer32 (1..4095)
   MAX-ACCESS  read-write
   STATUS      current
   DESCRIPTION
       "Next Hop VLAN ID, range: 1-4095.
        Please set IPRoutesNetwork first.
        This entry only work when 1.network address is IPv6, 2.Gateway is link-local, 3.Interface of specific VLAN ID is IPv6.
        Note: All entries in routes table will be sort by 1.network address 2.mask length 3. gateway 4. next hop VLAN, if you add/modify an entry, all entries will be reordered. Please check all entries in table to find your modified entry after set/add an entry."
   ::= {sm24dp4xaIPRoutesEntry 6 }

sm24dp4xaIPRoutesRowStatus OBJECT-TYPE
   SYNTAX      RowStatus
   MAX-ACCESS  read-create
   STATUS      current
   DESCRIPTION
	   "This object indicates the status of this entry, and is used
		to create/delete entries.  Any object in an entry of this
		table may be modified while the value of the corresponding
		instance of this object is active(1).
		createAndGo, notReady not supported."
   ::= { sm24dp4xaIPRoutesEntry 7 }

sm24dp4xaIPConfigurationConfigured OBJECT IDENTIFIER ::= { sm24dp4xaIP 4 }

sm24dp4xaModeConfigured OBJECT-TYPE
   SYNTAX      Integer32 (0|1)
   MAX-ACCESS  read-only
   STATUS      current
   DESCRIPTION
       "IP Configuration Mode
	default:0
        0: Host
        1: Router"
   ::= {sm24dp4xaIPConfigurationConfigured 2 }

sm24dp4xaDNSServerSource1Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sm24dp4xaIPConfigurationConfigured 3 }
   
sm24dp4xaDNSServerSource2Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sm24dp4xaIPConfigurationConfigured 4 }
   
sm24dp4xaDNSServerSource3Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sm24dp4xaIPConfigurationConfigured 5 }   

sm24dp4xaDNSServerSource4Configured OBJECT-TYPE
   SYNTAX      Integer32 (0..4)
   MAX-ACCESS  read-only
   STATUS      current
   DESCRIPTION
       "DNS Server Source.
        0: From any DHCP interfaces
        1: No DNS Server
        2: Configured
        4: From this DHCP interface"
   ::= {sm24dp4xaIPConfigurationConfigured 6 }   

sm24dp4xaDNSServerValue1Configured OBJECT-TYPE
   SYNTAX      DisplayString
   MAX-ACCESS  read-only
   STATUS      current
   DESCRIPTION
       "DNS IPv4/IPv6 Address or VLAN value."
   ::= {sm24dp4xaIPConfigurationConfigured 7 }  

sm24dp4xaDNSServerValue2Configured OBJECT-TYPE
   SYNTAX      DisplayString
   MAX-ACCESS  read-only
   STATUS      current
   DESCRIPTION
       "DNS IPv4/IPv6 Address or VLAN value."
   ::= {sm24dp4xaIPConfigurationConfigured 8 } 
   
sm24dp4xaDNSServerValue3Configured OBJECT-TYPE
   SYNTAX      DisplayString
   MAX-ACCESS  read-only
   STATUS      current
   DESCRIPTION
       "DNS IPv4/IPv6 Address or VLAN value."
   ::= {sm24dp4xaIPConfigurationConfigured 9 } 

sm24dp4xaDNSServerValue4Configured OBJECT-TYPE
   SYNTAX      DisplayString
   MAX-ACCESS  read-only
   STATUS      current
   DESCRIPTION
       "DNS IPv4/IPv6 Address or VLAN value."
   ::= {sm24dp4xaIPConfigurationConfigured 10 }    
      
sm24dp4xaDNSProxyConfigured OBJECT-TYPE
   SYNTAX      Integer32 (0|1)
   MAX-ACCESS  read-only
   STATUS      current
   DESCRIPTION
       "DNS Proxy enable/disable.
        default:0
        0: disable
        1: enable"
   ::= {sm24dp4xaIPConfigurationConfigured 11 }


sm24dp4xaIPInterfacesConfigured OBJECT IDENTIFIER ::= { sm24dp4xaIP 5 }

sm24dp4xaIPInterfacesConfiguredTable OBJECT-TYPE
   SYNTAX      SEQUENCE OF SM24DP4XAIPInterfacesConfiguredEntry
   MAX-ACCESS  not-accessible
   STATUS      current
   DESCRIPTION
        "A table of ip interface for switch."
    ::= { sm24dp4xaIPInterfacesConfigured 1 }

sm24dp4xaIPInterfacesConfiguredEntry OBJECT-TYPE
    SYNTAX        SM24DP4XAIPInterfacesConfiguredEntry
    MAX-ACCESS    not-accessible
    STATUS        current
    DESCRIPTION
        "An entry in the sm24dp4xaIPInterfacesConfiguredTable."
    INDEX        { sm24dp4xaIPInterfacesIndexConfigured }
    ::= { sm24dp4xaIPInterfacesConfiguredTable 1 }

SM24DP4XAIPInterfacesConfiguredEntry ::=
    SEQUENCE {
        sm24dp4xaIPInterfacesIndexConfigured                       Integer32,
        sm24dp4xaIPInterfacesVLANConfigured                        Integer32,
        sm24dp4xaIPInterfacesIPv4DHCPConfigured                    Integer32,
        sm24dp4xaIPInterfacesIPv4DHCPFallbackConfigured            DisplayString,
        sm24dp4xaIPInterfacesIPv4AddressConfigured                 IpAddress,
        sm24dp4xaIPInterfacesIPv4MaskConfigured                    Integer32,
	sm24dp4xaIPInterfacesIPv6DHCPConfigured                    Integer32, 
	sm24dp4xaIPInterfacesIPv6RapidCommitConfigured             Integer32,
        sm24dp4xaIPInterfacesIPv6AddressConfigured                 DisplayString,
        sm24dp4xaIPInterfacesIPv6MaskConfigured                    Integer32
    }

sm24dp4xaIPInterfacesIndexConfigured OBJECT-TYPE
   SYNTAX      Integer32 (1..128)
   MAX-ACCESS  not-accessible
   STATUS      current
   DESCRIPTION
       "interface table index"
   ::= {sm24dp4xaIPInterfacesConfiguredEntry 2 }

sm24dp4xaIPInterfacesVLANConfigured OBJECT-TYPE
   SYNTAX      Integer32 (1..4095)
   MAX-ACCESS  read-only
   STATUS      current
   DESCRIPTION
       "VLAN ID for interface, range: 1-4095."
   ::= {sm24dp4xaIPInterfacesConfiguredEntry 3 }

sm24dp4xaIPInterfacesIPv4DHCPConfigured OBJECT-TYPE
   SYNTAX      Integer32 (0|1)
   MAX-ACCESS  read-only
   STATUS      current
   DESCRIPTION
       "IPv4 DHCP Setting for interface.
	default:0
        0: disable
        1: enable"
   ::= {sm24dp4xaIPInterfacesConfiguredEntry 4 }

sm24dp4xaIPInterfacesIPv4DHCPFallbackConfigured OBJECT-TYPE
   SYNTAX      DisplayString
   MAX-ACCESS  read-only
   STATUS      current
   DESCRIPTION
       "IPv4 DHCP fallbcak. range: 1-4294967295 seconds."
   ::= {sm24dp4xaIPInterfacesConfiguredEntry 5 }

sm24dp4xaIPInterfacesIPv4AddressConfigured OBJECT-TYPE
   SYNTAX      IpAddress
   MAX-ACCESS  read-only
   STATUS      current
   DESCRIPTION
       "IPv4 address for interface."
   ::= {sm24dp4xaIPInterfacesConfiguredEntry 6 }

sm24dp4xaIPInterfacesIPv4MaskConfigured OBJECT-TYPE
   SYNTAX      Integer32 (1..32)
   MAX-ACCESS  read-only
   STATUS      current
   DESCRIPTION
       "IPv4 mask for interface."
   ::= { sm24dp4xaIPInterfacesConfiguredEntry 7 }

sm24dp4xaIPInterfacesIPv6DHCPConfigured OBJECT-TYPE
   SYNTAX      Integer32 (0|1)
   MAX-ACCESS  read-only
   STATUS      current
   DESCRIPTION
       "IPv6 DHCP Setting for interface.
        default:0
        0: disable
        1: enable"
   ::= {sm24dp4xaIPInterfacesConfiguredEntry 8 } 
   
sm24dp4xaIPInterfacesIPv6RapidCommitConfigured OBJECT-TYPE
   SYNTAX      Integer32 (0|1)
   MAX-ACCESS  read-only
   STATUS      current
   DESCRIPTION
       "Enable the DHCPv6 Rapid-Commit option.
        default:0
        0: disable
        1: enable"
   ::= {sm24dp4xaIPInterfacesConfiguredEntry 9 } 

sm24dp4xaIPInterfacesIPv6AddressConfigured OBJECT-TYPE
   SYNTAX      DisplayString (SIZE (0..30))
   MAX-ACCESS  read-only
   STATUS      current
   DESCRIPTION
       "IPv6 address for interface."
   ::= { sm24dp4xaIPInterfacesConfiguredEntry 10 }

sm24dp4xaIPInterfacesIPv6MaskConfigured OBJECT-TYPE
   SYNTAX      Integer32 (1..128)
   MAX-ACCESS  read-only
   STATUS      current
   DESCRIPTION
       "IPv6 mask for interface."
   ::= { sm24dp4xaIPInterfacesConfiguredEntry 11 }

sm24dp4xaIPRoutesConfigured OBJECT IDENTIFIER ::= { sm24dp4xaIP 6 }

sm24dp4xaIPRoutesConfiguredTable OBJECT-TYPE
   SYNTAX      SEQUENCE OF SM24DP4XAIPRoutesConfiguredEntry
   MAX-ACCESS  not-accessible
   STATUS      current
   DESCRIPTION
        "IP routes table for switch."
    ::= { sm24dp4xaIPRoutesConfigured 1 }

sm24dp4xaIPRoutesConfiguredEntry OBJECT-TYPE
    SYNTAX        SM24DP4XAIPRoutesConfiguredEntry
    MAX-ACCESS    not-accessible
    STATUS        current
    DESCRIPTION
        "Entry in the sm24dp4xaIPRoutesConfiguredTable."
    INDEX        { sm24dp4xaIPRoutesIndexConfigured }
    ::= { sm24dp4xaIPRoutesConfiguredTable 1 }

SM24DP4XAIPRoutesConfiguredEntry ::=
    SEQUENCE {
        sm24dp4xaIPRoutesIndexConfigured                       Integer32,
        sm24dp4xaIPRoutesNetworkConfigured                     DisplayString,
        sm24dp4xaIPRoutesMaskLengthConfigured                  Integer32,
        sm24dp4xaIPRoutesGatewayConfigured                     DisplayString,
        sm24dp4xaIPRoutesNextHopVLANConfigured                 Integer32
    }

sm24dp4xaIPRoutesIndexConfigured OBJECT-TYPE
   SYNTAX      Integer32 (1..32)
   MAX-ACCESS  not-accessible
   STATUS      current
   DESCRIPTION
       "routes table index"
   ::= {sm24dp4xaIPRoutesConfiguredEntry 2 }

sm24dp4xaIPRoutesNetworkConfigured OBJECT-TYPE
   SYNTAX      DisplayString (SIZE (0..30))
   MAX-ACCESS  read-only
   STATUS      current
   DESCRIPTION
       "IPv4/IPv6 Network address.
        Note: All entries in routes table will be sort by 1.network address 2.mask length 3. gateway 4. next hop VLAN, if you add/modify an entry, all entries will be reordered. Please check all entries in table to find your modified entry after set/add an entry."
   ::= {sm24dp4xaIPRoutesConfiguredEntry 3 }

sm24dp4xaIPRoutesMaskLengthConfigured OBJECT-TYPE
   SYNTAX      Integer32 (1..32)
   MAX-ACCESS  read-only
   STATUS      current
   DESCRIPTION
       "IPv4/IPv6 mask length.
        Note: All entries in routes table will be sort by 1.network address 2.mask length 3. gateway 4. next hop VLAN, if you add/modify an entry, all entries will be reordered. Please check all entries in table to find your modified entry after set/add an entry."
   ::= { sm24dp4xaIPRoutesConfiguredEntry 4 }

sm24dp4xaIPRoutesGatewayConfigured OBJECT-TYPE
   SYNTAX      DisplayString (SIZE (0..30))
   MAX-ACCESS  read-only
   STATUS      current
   DESCRIPTION
       "IPv4/IPv6 Gateway.
        Note: All entries in routes table will be sort by 1.network address 2.mask length 3. gateway 4. next hop VLAN, if you add/modify an entry, all entries will be reordered. Please check all entries in table to find your modified entry after set/add an entry."
   ::= {sm24dp4xaIPRoutesConfiguredEntry 5 }

sm24dp4xaIPRoutesNextHopVLANConfigured OBJECT-TYPE
   SYNTAX      Integer32 (1..4095)
   MAX-ACCESS  read-only
   STATUS      current
   DESCRIPTION
       "Next Hop VLAN ID, range: 1-4095.
        Note: All entries in routes table will be sort by 1.network address 2.mask length 3. gateway 4. next hop VLAN, if you add/modify an entry, all entries will be reordered. Please check all entries in table to find your modified entry after set/add an entry."
   ::= {sm24dp4xaIPRoutesConfiguredEntry 6 }

sm24dp4xaIPStatusInterface OBJECT IDENTIFIER ::= { sm24dp4xaIP 7 }

sm24dp4xaIPStatusInterfaceTable OBJECT-TYPE
              SYNTAX      SEQUENCE OF     SM24DP4XAIPStatusInterfaceEntry
              MAX-ACCESS  not-accessible
              STATUS      current
              DESCRIPTION
                       "The system IP Status table to show all IP interfaces."
                   ::= {     sm24dp4xaIPStatusInterface 1 }

    sm24dp4xaIPStatusInterfaceEntry OBJECT-TYPE
               SYNTAX          SM24DP4XAIPStatusInterfaceEntry
               MAX-ACCESS  not-accessible
               STATUS      current
               DESCRIPTION
                       "An entry in the IP Status Table."
               INDEX    {    sm24dp4xaIPStatusInterfaceIndex  }
               ::= {     sm24dp4xaIPStatusInterfaceTable 1 }

    SM24DP4XAIPStatusInterfaceEntry             ::= SEQUENCE {
            sm24dp4xaIPStatusInterfaceIndex         Integer32,
            sm24dp4xaIPStatusInterfaceName          DisplayString,
            sm24dp4xaIPStatusInterfaceType          DisplayString,
            sm24dp4xaIPStatusInterfaceAddress       DisplayString,
            sm24dp4xaIPStatusInterfaceStatus        DisplayString
            }

    sm24dp4xaIPStatusInterfaceIndex OBJECT-TYPE
               SYNTAX      Integer32(1..1024)
               MAX-ACCESS  not-accessible
               STATUS      current
               DESCRIPTION
                   "The entry of table to show all IP interfaces."
               ::= {     sm24dp4xaIPStatusInterfaceEntry 1 }

    sm24dp4xaIPStatusInterfaceName OBJECT-TYPE
               SYNTAX      DisplayString
               MAX-ACCESS  read-only
               STATUS      current
               DESCRIPTION
                   "The name of the interface."
               ::= {     sm24dp4xaIPStatusInterfaceEntry 2 }

    sm24dp4xaIPStatusInterfaceType OBJECT-TYPE
               SYNTAX      DisplayString
               MAX-ACCESS  read-only
               STATUS      current
               DESCRIPTION
                   "The address type of the entry. This may be LINK or IPv4."
               ::= {     sm24dp4xaIPStatusInterfaceEntry 3 }

    sm24dp4xaIPStatusInterfaceAddress OBJECT-TYPE
               SYNTAX      DisplayString
               MAX-ACCESS  read-only
               STATUS      current
               DESCRIPTION
                   "The current address of the interface (of the given type)."
               ::= {     sm24dp4xaIPStatusInterfaceEntry 4 }

    sm24dp4xaIPStatusInterfaceStatus OBJECT-TYPE
               SYNTAX      DisplayString
               MAX-ACCESS  read-only
               STATUS      current
               DESCRIPTION
                   "The status flags of the interface (and/or address)."
               ::= {     sm24dp4xaIPStatusInterfaceEntry 5 }

sm24dp4xaIPStatusRoute OBJECT IDENTIFIER ::= { sm24dp4xaIP 8 }

    sm24dp4xaIPStatusRouteTable OBJECT-TYPE
              SYNTAX      SEQUENCE OF     SM24DP4XAIPStatusRouteEntry
              MAX-ACCESS  not-accessible
              STATUS      current
              DESCRIPTION
                       "The IP Status Route table show all routing entries."
                   ::= {     sm24dp4xaIPStatusRoute 1 }

    sm24dp4xaIPStatusRouteEntry OBJECT-TYPE
               SYNTAX          SM24DP4XAIPStatusRouteEntry
               MAX-ACCESS  not-accessible
               STATUS      current
               DESCRIPTION
                       "an entry in the IP Status route table."
               INDEX    {     sm24dp4xaIPStatusRouteIndex  }
               ::= {     sm24dp4xaIPStatusRouteTable 1 }

    SM24DP4XAIPStatusRouteEntry             ::= SEQUENCE {
            sm24dp4xaIPStatusRouteIndex          Integer32,
            sm24dp4xaIPStatusRouteNetwork        DisplayString,
            sm24dp4xaIPStatusRouteGateway        DisplayString,
            sm24dp4xaIPStatusRouteAddress        DisplayString
     }

    sm24dp4xaIPStatusRouteIndex OBJECT-TYPE
               SYNTAX      Integer32(1..2048)
               MAX-ACCESS  not-accessible
               STATUS      current
               DESCRIPTION
                   "The entry of table to show all routing entries."
               ::= {     sm24dp4xaIPStatusRouteEntry 1 }

    sm24dp4xaIPStatusRouteNetwork OBJECT-TYPE
               SYNTAX      DisplayString
               MAX-ACCESS  read-only
               STATUS      current
               DESCRIPTION
                   "The destination IP network or host address of this route."
               ::= {     sm24dp4xaIPStatusRouteEntry 2 }

    sm24dp4xaIPStatusRouteGateway OBJECT-TYPE
               SYNTAX      DisplayString
               MAX-ACCESS  read-only
               STATUS      current
               DESCRIPTION
                   "The gateway address of this route."
               ::= {     sm24dp4xaIPStatusRouteEntry 3 }

    sm24dp4xaIPStatusRouteAddress OBJECT-TYPE
               SYNTAX      DisplayString
               MAX-ACCESS  read-only
               STATUS      current
               DESCRIPTION
                   "The route address."
               ::= {     sm24dp4xaIPStatusRouteEntry 4 }

sm24dp4xaIPStatusNeighborCache OBJECT IDENTIFIER ::= { sm24dp4xaIP 9 }

    sm24dp4xaIPStatusNeighborCacheTable OBJECT-TYPE
               SYNTAX      SEQUENCE OF     SM24DP4XAIPStatusNeighborCacheEntry
               MAX-ACCESS  not-accessible
               STATUS      current
               DESCRIPTION
                       "The Ip Status Neighbor Cache Table."
                   ::= {     sm24dp4xaIPStatusNeighborCache 1 }

    sm24dp4xaIPStatusNeighborCacheEntry OBJECT-TYPE
               SYNTAX          SM24DP4XAIPStatusNeighborCacheEntry
               MAX-ACCESS  not-accessible
               STATUS      current
               DESCRIPTION
                       "An entry in the Ip Status Neighbor Cache Table."
               INDEX    {     sm24dp4xaIPStatusNeighborCacheIndex  }
               ::= {     sm24dp4xaIPStatusNeighborCacheTable 1 }

    SM24DP4XAIPStatusNeighborCacheEntry             ::= SEQUENCE {
            sm24dp4xaIPStatusNeighborCacheIndex            Integer32,
            sm24dp4xaIPStatusNeighborCacheIPAddress        DisplayString,
            sm24dp4xaIPStatusNeighborCacheLinkAddress      DisplayString
            }

    sm24dp4xaIPStatusNeighborCacheIndex OBJECT-TYPE
               SYNTAX      Integer32(1..1024)
               MAX-ACCESS  not-accessible
               STATUS      current
               DESCRIPTION
                   "The index for the Ip Status Neighbor Cache Table."
               ::= {     sm24dp4xaIPStatusNeighborCacheEntry 1 }

    sm24dp4xaIPStatusNeighborCacheIPAddress OBJECT-TYPE
               SYNTAX      DisplayString
               MAX-ACCESS  read-only
               STATUS      current
               DESCRIPTION
                   "The IP address of the entry."
               ::= {     sm24dp4xaIPStatusNeighborCacheEntry 2 }

    sm24dp4xaIPStatusNeighborCacheLinkAddress OBJECT-TYPE
               SYNTAX      DisplayString
               MAX-ACCESS  read-only
               STATUS      current
               DESCRIPTION
                   "The Link (MAC) address for which a binding to the
                    IP address given exist."
               ::= {     sm24dp4xaIPStatusNeighborCacheEntry 3 }

sm24dp4xaIPStatusDNSServer OBJECT IDENTIFIER ::= { sm24dp4xaIP 10 }

    sm24dp4xaIPStatusDNSServerType OBJECT-TYPE
               SYNTAX      DisplayString
               MAX-ACCESS  read-only
               STATUS      current
               DESCRIPTION
                   "The configuration type of DNS server."
               ::= {     sm24dp4xaIPStatusDNSServer 1 }

    sm24dp4xaIPStatusDNSServerIPAddress OBJECT-TYPE
               SYNTAX      DisplayString
               MAX-ACCESS  read-only
               STATUS      current
               DESCRIPTION
                   "The IP address of the DNS server."
               ::= {     sm24dp4xaIPStatusDNSServer 2 }

    sm24dp4xaIPStatusDNSServerInterface OBJECT-TYPE
               SYNTAX      DisplayString
               MAX-ACCESS  read-only
               STATUS      current
               DESCRIPTION
                   "The name of the interface."
               ::= {     sm24dp4xaIPStatusDNSServer 3 }			   
			   
-- =======================================================================================================================
sm24dp4xaSyslog                                                OBJECT IDENTIFIER ::= { sm24dp4xaSystem 5 }

sm24dp4xaSyslogConf                                            OBJECT IDENTIFIER ::= { sm24dp4xaSyslog 1 }

sm24dp4xaSysLogInfo                                            OBJECT IDENTIFIER   ::= {  sm24dp4xaSyslog 2 }
--
-- =======================================================================================================================
-- Objects in the sm24dp4xaSystemLog Group
-- =======================================================================================================================
--sm24dp4xaSystemLogConf

    sm24dp4xaSystemLogServerMode OBJECT-TYPE
               SYNTAX      AdminMode
               MAX-ACCESS  read-write
               STATUS      current
               DESCRIPTION
                   "The System log server mode admin state."
               DEFVAL  { disable }
               ::= {     sm24dp4xaSyslogConf 1 }

    sm24dp4xaSystemLogServerAddress OBJECT-TYPE
               SYNTAX      DisplayString
               MAX-ACCESS  read-write
               STATUS      current
               DESCRIPTION
                   "The Host address of syslog server."
               ::= {     sm24dp4xaSyslogConf 2 }

--    sm24dp4xaSystemLogSyslogLevel OBJECT-TYPE
--               SYNTAX      INTEGER {
--                    info(0),
--                    warning(1),
--                    error(2)
--               }
--               MAX-ACCESS  read-write
--               STATUS      current
--               DESCRIPTION
--                   "The syslog level.
--                       info(0)   : Info.
--                       warning(1): Warning.
--                       error(2)  : Error."
--               DEFVAL  { info }
--               ::= {     sm24dp4xaSyslogConf 3 }

    sm24dp4xaSystemLogServerPort OBJECT-TYPE
                 SYNTAX      Integer32(1..65535)
                 MAX-ACCESS  read-write
                 STATUS      current
                 DESCRIPTION
                      "syslog service port number.
                 range : 1-65535, default : 514."
               ::= {     sm24dp4xaSyslogConf 4 }

--sm24dp4xaSystemLogInfo
    sm24dp4xaSystemLogInfoLevel OBJECT-TYPE
               SYNTAX      INTEGER { emergency(0), alert(1), critical(2), error(3), warning(4), notice(5), information(6), debug(7), all(8) }
               MAX-ACCESS  read-write
               STATUS      current
               DESCRIPTION
                  "The Level input field is used to filter the display system log entries.
                   0: Emergency.
                   1: Alert.
                   2: Critical.
                   3: Error.
                   4: Warning.
                   5: Notice.
                   6: Information.
                   7: Debug.
                   8: All."
               DEFVAL  { all }
               ::= {     sm24dp4xaSysLogInfo 1 }

    sm24dp4xaSystemLogInfoClearLevel OBJECT-TYPE
               SYNTAX      INTEGER { emergency(0), alert(1), critical(2), error(3), warning(4), notice(5), information(6), debug(7), all(8) }
               MAX-ACCESS  read-write
               STATUS      current
               DESCRIPTION
                  "The Clear Level input field is used to specify which
                  system log entries will be cleared.
                  default: 8 (All).
                   0: Emergency.
                   1: Alert.
                   2: Critical.
                   3: Error.
                   4: Warning.
                   5: Notice.
                   6: Information.
                   7: Debug.
                   8: All."
               DEFVAL  { all }
               ::= {     sm24dp4xaSysLogInfo 2 }

    sm24dp4xaSystemLogInfoClearCmd OBJECT-TYPE
               SYNTAX      ActivateCmd
               MAX-ACCESS  read-write
               STATUS      current
               DESCRIPTION
                  "Command to clear the syslog.
                   noAction(0) : do nothing  (read only).
                   activate(1) : Clear Syslog."
               DEFVAL  { noAction }
               ::= {     sm24dp4xaSysLogInfo 3 }

    sm24dp4xaSystemLogDetailedInfoTable OBJECT-TYPE
              SYNTAX      SEQUENCE OF     SM24DP4XASystemLogDetailedInfoEntry
              MAX-ACCESS  not-accessible
              STATUS      current
              DESCRIPTION
                       "The system detailed Log Info table."
                   ::= {     sm24dp4xaSysLogInfo 4 }

    sm24dp4xaSystemLogDetailedInfoEntry OBJECT-TYPE
               SYNTAX          SM24DP4XASystemLogDetailedInfoEntry
               MAX-ACCESS  not-accessible
               STATUS      current
               DESCRIPTION
                       "An entry in the system detailed Log Info table."
               INDEX    {     sm24dp4xaSystemLogDetailedInfoID  }
               ::= {     sm24dp4xaSystemLogDetailedInfoTable 1 }

    SM24DP4XASystemLogDetailedInfoEntry             ::= SEQUENCE {
                sm24dp4xaSystemLogDetailedSwitchIndex       Integer32,
                sm24dp4xaSystemLogDetailedInfoID            Integer32,
                sm24dp4xaSystemLogDetailedInfoLevel         DisplayString,
                sm24dp4xaSystemLogDetailedInfoTime          DisplayString,
                sm24dp4xaSystemLogDetailedInfoMessage       DisplayString
                }

    sm24dp4xaSystemLogDetailedSwitchIndex OBJECT-TYPE
               SYNTAX      Integer32(1..16)
               MAX-ACCESS  not-accessible
               STATUS      current
               DESCRIPTION
                   "The switch index for the system detailed Log Info table."
               ::= {     sm24dp4xaSystemLogDetailedInfoEntry 1 }

    sm24dp4xaSystemLogDetailedInfoID OBJECT-TYPE
               SYNTAX      Integer32(1..999)
               MAX-ACCESS  not-accessible
               STATUS      current
               DESCRIPTION
                   "The index for the system detailed Log Info table."
               ::= {     sm24dp4xaSystemLogDetailedInfoEntry 2 }

    sm24dp4xaSystemLogDetailedInfoLevel OBJECT-TYPE
               SYNTAX      DisplayString
               MAX-ACCESS  read-only
               STATUS      current
               DESCRIPTION
                   "The Info Level."
               ::= {     sm24dp4xaSystemLogDetailedInfoEntry 3 }

    sm24dp4xaSystemLogDetailedInfoTime OBJECT-TYPE
               SYNTAX      DisplayString(SIZE (0..20))
               MAX-ACCESS  read-only
               STATUS      current
               DESCRIPTION
                   "The time"
               ::= {     sm24dp4xaSystemLogDetailedInfoEntry 4 }

    sm24dp4xaSystemLogDetailedInfoMessage OBJECT-TYPE
               SYNTAX      DisplayString
               MAX-ACCESS  read-only
               STATUS      current
               DESCRIPTION
                   "The message of this entry."
               ::= {     sm24dp4xaSystemLogDetailedInfoEntry 5 }
               
    sm24dp4xaSystemDORelayOpenClose OBJECT-TYPE
               SYNTAX      Integer32
               MAX-ACCESS  read-write
               STATUS      current
               DESCRIPTION
                  "DO Relay Open/Close.
                   1:open
                   0:close"
               ::= {     sm24dp4xaSysLogInfo 5 }
-- =======================================================================================================================
sm24dp4xaSnmp                                                OBJECT IDENTIFIER ::= { sm24dp4xaSystem 6 }

sm24dp4xaSnmpSystem                                            OBJECT IDENTIFIER ::= { sm24dp4xaSnmp 1 }

sm24dp4xaSnmpSystemMode OBJECT-TYPE
   SYNTAX       Integer32
   MAX-ACCESS   read-write
   STATUS       current
   DESCRIPTION
       "SNMP mode operation.
        default : 1, 0: disable, 1: enable. "
   ::= { sm24dp4xaSnmpSystem 1 }

sm24dp4xaSnmpSystemVersion OBJECT-TYPE
   SYNTAX       Integer32
   MAX-ACCESS   read-write
   STATUS       current
   DESCRIPTION
       "SNMP supported version.
       default : snmpv2c.
       0: snmpv1
       1: snmpv2c
       2: snmpv3."
   ::= { sm24dp4xaSnmpSystem 2 }

sm24dp4xaSnmpSystemReadCommunity OBJECT-TYPE
   SYNTAX       DisplayString
   MAX-ACCESS   read-write
   STATUS       current
   DESCRIPTION
       "Indicates the community read access string to permit access to SNMP agent.
       The allowed string length is 0 to 255.
       The field is applicable only when SNMP version is SNMPv1 or SNMPv2c."
   ::= { sm24dp4xaSnmpSystem 3 }

sm24dp4xaSnmpSystemWriteCommunity OBJECT-TYPE
   SYNTAX       DisplayString
   MAX-ACCESS   read-write
   STATUS       current
   DESCRIPTION
       "Indicates the community write access string to permit access to SNMP agent.
       The allowed string length is 0 to 255.
       The field is applicable only when SNMP version is SNMPv1 or SNMPv2c."
   ::= { sm24dp4xaSnmpSystem 4 }

sm24dp4xaSnmpSystemEngineID OBJECT-TYPE
   SYNTAX       DisplayString
   MAX-ACCESS   read-only
   STATUS       current
   DESCRIPTION
       "Indicates the SNMPv3 engine ID.
        The string must contain an even number(in hexadecimal format) with number of digits between 10 and 64,
	but all-zeros and all-'F's are not allowed.
	Allow string length is 10 to 32.
	Change of the Engine ID will clear all original local users."
   ::= { sm24dp4xaSnmpSystem 5 }

sm24dp4xaSnmpSystemWriteCommunityMode OBJECT-TYPE
   SYNTAX       Integer32
   MAX-ACCESS   read-write
   STATUS       current
   DESCRIPTION
       "SNMP write community mode operation.
        default : 1, 0: disable, 1: enable. "
   ::= { sm24dp4xaSnmpSystem 6 }

sm24dp4xaSnmpTrapGlobalMode OBJECT-TYPE
   SYNTAX       Integer32
   MAX-ACCESS   read-write
   STATUS       current
   DESCRIPTION
       "Indicates the trap mode operation.
        0:Disable.
	1:Enable."
   ::= { sm24dp4xaSnmp 2 }

sm24dp4xaTrapDestinationConfTable OBJECT-TYPE
   SYNTAX      SEQUENCE OF SM24DP4XATrapDestinationConfEntry
   MAX-ACCESS  not-accessible
   STATUS      current
   DESCRIPTION
       "A list of trap host entry. The numbers of entries are given by the value of TrapHostConfNumber."
   ::= { sm24dp4xaSnmp 3 }

sm24dp4xaTrapDestinationConfEntry OBJECT-TYPE
   SYNTAX      SM24DP4XATrapDestinationConfEntry
   MAX-ACCESS  not-accessible
   STATUS      current
   DESCRIPTION
       "This is the entry information for trap host."
   INDEX    { sm24dp4xaTrapDestinationConfIndex  }
   ::= { sm24dp4xaTrapDestinationConfTable 1 }

SM24DP4XATrapDestinationConfEntry ::= SEQUENCE {
    sm24dp4xaTrapDestinationConfIndex                      Integer32,
    sm24dp4xaTrapDestinationConfTrapConfigName             DisplayString,
    sm24dp4xaTrapDestinationConfTrapMode                   Integer32,
    sm24dp4xaTrapDestinationConfTrapVersion                Integer32,
    sm24dp4xaTrapDestinationConfTrapCommunity              DisplayString,
    sm24dp4xaTrapDestinationConfTrapDestinationAddres      DisplayString,
    sm24dp4xaTrapDestinationConfTrapDestinationPort        Integer32,
    sm24dp4xaTrapDestinationConfTrapInformMode             Integer32,
    sm24dp4xaTrapDestinationConfTrapInformTimeout          Integer32,
    sm24dp4xaTrapDestinationConfTrapInformRetryTimes       Integer32,
    sm24dp4xaTrapDestinationConfTrapProbeSecurityEngineID  Integer32,
    sm24dp4xaTrapDestinationConfTrapSecurityEngineID       DisplayString,
    sm24dp4xaTrapDestinationConfTrapSecurityName           DisplayString,
    sm24dp4xaTrapDestinationConfTrapRowStatus              Integer32
}

sm24dp4xaTrapDestinationConfIndex OBJECT-TYPE
   SYNTAX       Integer32(1..65535)
   MAX-ACCESS   not-accessible
   STATUS       current
   DESCRIPTION
       "Index of tarp destination configurations."
   ::= { sm24dp4xaTrapDestinationConfEntry 1 }

sm24dp4xaTrapDestinationConfTrapConfigName OBJECT-TYPE
   SYNTAX       DisplayString
   MAX-ACCESS   read-write
   STATUS       current
   DESCRIPTION
       "Indicates which trap Configuration's name for configuring.
       The allowed string length is 0 to 255, and the allowed content is
       ASCII characters from 33 to 126."
   ::= { sm24dp4xaTrapDestinationConfEntry 2 }

sm24dp4xaTrapDestinationConfTrapMode OBJECT-TYPE
   SYNTAX       Integer32
   MAX-ACCESS   read-write
   STATUS       current
   DESCRIPTION
       "Indicates the SNMP mode operation. Possible modes are:
        2: Enable TCP SNMP mode operation.
        1: Enable UDP SNMP mode operation.
        0: Disable SNMP mode operation. "
   ::= { sm24dp4xaTrapDestinationConfEntry 3 }

sm24dp4xaTrapDestinationConfTrapVersion OBJECT-TYPE
   SYNTAX       Integer32
   MAX-ACCESS   read-write
   STATUS       current
   DESCRIPTION
       "0: snmpv1
        1: snmpv2c
        3: snmpv3.
        "
   ::= { sm24dp4xaTrapDestinationConfEntry 4 }

sm24dp4xaTrapDestinationConfTrapCommunity OBJECT-TYPE
   SYNTAX       DisplayString
   MAX-ACCESS   read-write
   STATUS       current
   DESCRIPTION
       "Indicates the community access string when sending SNMP trap packet.
       The allowed string length is 0 to 255, and the allowed content is
       ASCII characters from 33 to 126."
   ::= { sm24dp4xaTrapDestinationConfEntry 5 }

sm24dp4xaTrapDestinationConfTrapDestinationAddres OBJECT-TYPE
   SYNTAX       DisplayString
   MAX-ACCESS   read-write
   STATUS       current
   DESCRIPTION
       "Indicates the SNMP trap destination address.
       It allow a valid IP address in dotted decimal notation ('x.y.z.w').
    And it also allow a valid hostname.
    A valid hostname is a string drawn from the alphabet (A-Za-z), digits (0-9),
    dot (.), dash (-). Spaces are not allowed, the first character must be an alpha character,
    and the first and last characters must not be a dot or a dash.
    Indicates the SNMP trap destination IPv6 address.
    IPv6 address is in 128-bit records represented as eight fields of up to four hexadecimal digits
    with a colon separating each field (:).
    For example, 'fe80::215:c5ff:fe03:4dc7'. The symbol '::' is a special syntax
    that can be used as a shorthand way of representing multiple 16-bit groups of contiguous zeros;
    but it can appear only once.
    It can also represent a legally valid IPv4 address.
    For example, '::192.1.2.34'."
   ::= { sm24dp4xaTrapDestinationConfEntry 6 }

sm24dp4xaTrapDestinationConfTrapDestinationPort OBJECT-TYPE
   SYNTAX       Integer32
   MAX-ACCESS   read-write
   STATUS       current
   DESCRIPTION
       "Indicates the SNMP trap destination port.
       SNMP Agent will send SNMP message via this port,
       the port range is 1~65535."
   ::= { sm24dp4xaTrapDestinationConfEntry 7 }

sm24dp4xaTrapDestinationConfTrapInformMode OBJECT-TYPE
   SYNTAX       Integer32
   MAX-ACCESS   read-write
   STATUS       current
   DESCRIPTION
       "Indicates the SNMP trap inform mode operation. Possible modes are:
        1: Enable SNMP trap inform mode operation.
        0: Disable SNMP trap inform mode operation. "
   ::= { sm24dp4xaTrapDestinationConfEntry 8 }

sm24dp4xaTrapDestinationConfTrapInformTimeout OBJECT-TYPE
   SYNTAX       Integer32
   MAX-ACCESS   read-write
   STATUS       current
   DESCRIPTION
       "Indicates the SNMP trap inform timeout. The allowed range is 0 to 2147."
   ::= { sm24dp4xaTrapDestinationConfEntry 9 }

sm24dp4xaTrapDestinationConfTrapInformRetryTimes OBJECT-TYPE
   SYNTAX       Integer32
   MAX-ACCESS   read-write
   STATUS       current
   DESCRIPTION
       "Indicates the SNMP trap inform retry times. The allowed range is 0 to 255."
   ::= { sm24dp4xaTrapDestinationConfEntry 10 }

sm24dp4xaTrapDestinationConfTrapProbeSecurityEngineID OBJECT-TYPE
   SYNTAX       Integer32
   MAX-ACCESS   read-write
   STATUS       current
   DESCRIPTION
       "Indicates the SNMP trap probe security engine ID mode of operation.
       Possible values are:
       1: Enable SNMP trap probe security engine ID mode of operation.
       0: Disable SNMP trap probe security engine ID mode of operation."
   ::= { sm24dp4xaTrapDestinationConfEntry 11 }

sm24dp4xaTrapDestinationConfTrapSecurityEngineID OBJECT-TYPE
   SYNTAX       DisplayString
   MAX-ACCESS   read-write
   STATUS       current
   DESCRIPTION
       "Indicates the SNMP trap security engine ID.
       SNMPv3 sends traps and informs using USM for authentication and privacy.
       A unique engine ID for these traps and informs is needed.
       When Trap Probe Security Engine ID is enabled, the ID will be probed automatically.
       Otherwise, the ID specified in this field is used.
       The string must contain an even number(in hexadecimal format) with
       number of digits between 10 and 64, but all-zeros and all-'F's are not allowed."
   ::= { sm24dp4xaTrapDestinationConfEntry 12 }

sm24dp4xaTrapDestinationConfTrapSecurityName OBJECT-TYPE
   SYNTAX       DisplayString
   MAX-ACCESS   read-write
   STATUS       current
   DESCRIPTION
       "Indicates the SNMP trap security name.
       SNMPv3 traps and informs using USM for authentication and privacy.
       A unique security name is needed when traps and informs are enabled.
       This name from user name of user configuration."
   ::= { sm24dp4xaTrapDestinationConfEntry 13 }

sm24dp4xaTrapDestinationConfTrapRowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sm24dp4xaTrapDestinationConfEntry 14 }


sm24dp4xaSNMPCommunityConfTable OBJECT-TYPE
   SYNTAX      SEQUENCE OF SM24DP4XASNMPCommunityConfEntry
   MAX-ACCESS  not-accessible
   STATUS      current
   DESCRIPTION
       "A list of snmp community configuration entry."
   ::= { sm24dp4xaSnmp 5 }

sm24dp4xaSNMPCommunityConfEntry OBJECT-TYPE
   SYNTAX      SM24DP4XASNMPCommunityConfEntry
   MAX-ACCESS  not-accessible
   STATUS      current
   DESCRIPTION
       "This is the entry information for snmp community configuration."
   INDEX    { sm24dp4xaSNMPCommunityConfIndex  }
   ::= { sm24dp4xaSNMPCommunityConfTable 1 }

SM24DP4XASNMPCommunityConfEntry ::= SEQUENCE {
    sm24dp4xaSNMPCommunityConfIndex                       Integer32,
    sm24dp4xaSNMPCommunityConfSNMPv3Community             DisplayString,
    sm24dp4xaSNMPCommunityConfSNMPv3SourceIP              IpAddress,
    sm24dp4xaSNMPCommunityConfSNMPv3SourceMask            IpAddress,
    sm24dp4xaSNMPCommunityConfSNMPv3RowStatus             Integer32
}

sm24dp4xaSNMPCommunityConfIndex OBJECT-TYPE
   SYNTAX       Integer32(1..65535)
   MAX-ACCESS   read-write
   STATUS       current
   DESCRIPTION
       "Community configuration index."
   ::= { sm24dp4xaSNMPCommunityConfEntry 1 }

sm24dp4xaSNMPCommunityConfSNMPv3Community OBJECT-TYPE
   SYNTAX       DisplayString
   MAX-ACCESS   read-write
   STATUS       current
   DESCRIPTION
       "Indicates the community access string to permit access to SNMPv3 agent.
       The allowed string length is 1 to 32, and the allowed content is
       ASCII characters from 33 to 126.
       The community string will be treated as security name and map a SNMPv1
       or SNMPv2c community string."
   ::= { sm24dp4xaSNMPCommunityConfEntry 2 }


sm24dp4xaSNMPCommunityConfSNMPv3SourceIP OBJECT-TYPE
   SYNTAX      IpAddress
   MAX-ACCESS  read-write
   STATUS      current
   DESCRIPTION
       "Indicates the SNMP access source address.
       A particular range of source addresses can be used to restrict source subnet
       when combined with source mask."
   ::= {sm24dp4xaSNMPCommunityConfEntry 3 }

sm24dp4xaSNMPCommunityConfSNMPv3SourceMask OBJECT-TYPE
   SYNTAX      IpAddress
   MAX-ACCESS  read-write
   STATUS      current
   DESCRIPTION
       "Indicates the SNMP access source address mask."
   ::= {sm24dp4xaSNMPCommunityConfEntry 4 }

sm24dp4xaSNMPCommunityConfSNMPv3RowStatus OBJECT-TYPE
   SYNTAX       Integer32
   MAX-ACCESS   read-write
   STATUS       current
   DESCRIPTION
       "This object indicates the status of this entry, and is
       used to create(5)/delete(6) entries.  Any object in an entry of
       this table may be modified while the value of the
       corresponding instance of this object is active(1).
       createAndGo, notReady not supported."
   ::= { sm24dp4xaSNMPCommunityConfEntry 5 }

sm24dp4xaSNMPv3UserConfTable OBJECT-TYPE
   SYNTAX      SEQUENCE OF SM24DP4XASNMPv3UserConfEntry
   MAX-ACCESS  not-accessible
   STATUS      current
   DESCRIPTION
       "A list of snmpv3 user configuration entry."
   ::= { sm24dp4xaSnmp 6 }

sm24dp4xaSNMPv3UserConfEntry OBJECT-TYPE
   SYNTAX      SM24DP4XASNMPv3UserConfEntry
   MAX-ACCESS  not-accessible
   STATUS      current
   DESCRIPTION
       "This is the entry information for snmpv3 user configuration."
   INDEX    { sm24dp4xaSNMPv3UserConfIndex  }
   ::= { sm24dp4xaSNMPv3UserConfTable 1 }

SM24DP4XASNMPv3UserConfEntry ::= SEQUENCE {
    sm24dp4xaSNMPv3UserConfIndex                     Integer32,
    sm24dp4xaSNMPv3UserConfEngineID                  DisplayString,
    sm24dp4xaSNMPv3UserConfUserName                  DisplayString,
    sm24dp4xaSNMPv3UserConfSecurityLevel             Integer32,
    sm24dp4xaSNMPv3UserConfAuthenticationProtocol    Integer32,
    sm24dp4xaSNMPv3UserConfAuthenticationPassword    DisplayString,
    sm24dp4xaSNMPv3UserConfPrivacyProtocol           Integer32,
    sm24dp4xaSNMPv3UserConfPrivacyPassword           DisplayString,
    sm24dp4xaSNMPv3UserConfRowStatus                 RowStatus
}

sm24dp4xaSNMPv3UserConfIndex OBJECT-TYPE
   SYNTAX       Integer32(1..65535)
   MAX-ACCESS   read-write
   STATUS       current
   DESCRIPTION
       "User configuration index."
   ::= { sm24dp4xaSNMPv3UserConfEntry 1 }

sm24dp4xaSNMPv3UserConfEngineID OBJECT-TYPE
   SYNTAX       DisplayString
   MAX-ACCESS   read-write
   STATUS       current
   DESCRIPTION
       "An octet string identifying the engine ID that this entry should belong to.
       The string must contain an even number(in hexadecimal format) with
       number of digits between 10 and 64, but all-zeros and all-'F's are not allowed.
       The SNMPv3 architecture uses the User-based Security Model (USM)
       for message security and the View-based Access Control Model (VACM) for access control.
       For the USM entry, the usmUserEngineID and usmUserName are the entry's keys.
       In a simple agent, usmUserEngineID is always that agent's own snmpEngineID value.
       The value can also take the value of the snmpEngineID of a remote SNMP engine with
       which this user can communicate. In other words, if user engine ID equal system engine ID
       then it is local user; otherwise it's remote user. "
   ::= { sm24dp4xaSNMPv3UserConfEntry 2 }

sm24dp4xaSNMPv3UserConfUserName OBJECT-TYPE
   SYNTAX       DisplayString
   MAX-ACCESS   read-write
   STATUS       current
   DESCRIPTION
       "A string identifying the user name that this entry should belong to.
       The allowed string length is 1 to 32, and the allowed content is
       ASCII characters from 33 to 126."
   ::= { sm24dp4xaSNMPv3UserConfEntry 3 }

sm24dp4xaSNMPv3UserConfSecurityLevel OBJECT-TYPE
   SYNTAX       Integer32
   MAX-ACCESS   read-write
   STATUS       current
   DESCRIPTION
       "1:NoAuth, NoPriv
        2:Auth, NoPriv
	3:Auth, Priv"
   ::= { sm24dp4xaSNMPv3UserConfEntry 4 }

sm24dp4xaSNMPv3UserConfAuthenticationProtocol OBJECT-TYPE
   SYNTAX       Integer32
   MAX-ACCESS   read-write
   STATUS       current
   DESCRIPTION
       "0:None
        1:MD5
	2:SHA"
   ::= { sm24dp4xaSNMPv3UserConfEntry 5 }

sm24dp4xaSNMPv3UserConfAuthenticationPassword OBJECT-TYPE
   SYNTAX       DisplayString
   MAX-ACCESS   read-write
   STATUS       current
   DESCRIPTION
       "A string identifying the authentication password phrase.
       For MD5 authentication protocol, the allowed string length is 8 to 32.
       For SHA authentication protocol, the allowed string length is 8 to 40.
       The allowed content is ASCII characters from 33 to 126."
   ::= { sm24dp4xaSNMPv3UserConfEntry 6 }

sm24dp4xaSNMPv3UserConfPrivacyProtocol OBJECT-TYPE
   SYNTAX       Integer32
   MAX-ACCESS   read-write
   STATUS       current
   DESCRIPTION
       "0:None
        1:DES
        2:AES"
   ::= { sm24dp4xaSNMPv3UserConfEntry 7 }

sm24dp4xaSNMPv3UserConfPrivacyPassword OBJECT-TYPE
   SYNTAX       DisplayString
   MAX-ACCESS   read-write
   STATUS       current
   DESCRIPTION
       "A string identifying the privacy password phrase.
       The allowed string length is 8 to 32, and the allowed content is
       ASCII characters from 33 to 126."
   ::= { sm24dp4xaSNMPv3UserConfEntry 8 }

sm24dp4xaSNMPv3UserConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sm24dp4xaSNMPv3UserConfEntry 9 }

sm24dp4xaSNMPv3GroupConfTable OBJECT-TYPE
   SYNTAX      SEQUENCE OF SM24DP4XASNMPv3GroupConfEntry
   MAX-ACCESS  not-accessible
   STATUS      current
   DESCRIPTION
       "A list of snmpv3 group configuration entry."
   ::= { sm24dp4xaSnmp 7 }

sm24dp4xaSNMPv3GroupConfEntry OBJECT-TYPE
   SYNTAX      SM24DP4XASNMPv3GroupConfEntry
   MAX-ACCESS  not-accessible
   STATUS      current
   DESCRIPTION
       "This is the entry information for snmpv3 group configuration."
   INDEX    { sm24dp4xaSNMPv3GroupConfIndex  }
   ::= { sm24dp4xaSNMPv3GroupConfTable 1 }

SM24DP4XASNMPv3GroupConfEntry ::= SEQUENCE {
    sm24dp4xaSNMPv3GroupConfIndex                     Integer32,
    sm24dp4xaSNMPv3GroupConfSecurityModel             Integer32,
    sm24dp4xaSNMPv3GroupConfSecurityName          DisplayString,
    sm24dp4xaSNMPv3GroupConfGroupName             DisplayString,
    sm24dp4xaSNMPv3GroupConfRowStatus                 RowStatus
}

sm24dp4xaSNMPv3GroupConfIndex OBJECT-TYPE
   SYNTAX       Integer32(1..65535)
   MAX-ACCESS   read-write
   STATUS       current
   DESCRIPTION
       "Group configuration index."
   ::= { sm24dp4xaSNMPv3GroupConfEntry 1 }

sm24dp4xaSNMPv3GroupConfSecurityModel OBJECT-TYPE
   SYNTAX       Integer32
   MAX-ACCESS   read-write
   STATUS       current
   DESCRIPTION
       "1:v1
        2:v2c
	3:usm"
   ::= { sm24dp4xaSNMPv3GroupConfEntry 2 }

sm24dp4xaSNMPv3GroupConfSecurityName OBJECT-TYPE
   SYNTAX       DisplayString
   MAX-ACCESS   read-write
   STATUS       current
   DESCRIPTION
       "A string identifying the security name that this entry should belong to.
       The allowed string length is 1 to 32, and the allowed content is
       ASCII characters from 33 to 126.
       This name is from the Community of Community configuration."
   ::= { sm24dp4xaSNMPv3GroupConfEntry 3 }

sm24dp4xaSNMPv3GroupConfGroupName OBJECT-TYPE
   SYNTAX       DisplayString
   MAX-ACCESS   read-write
   STATUS       current
   DESCRIPTION
       "A string identifying the group name that this entry should belong to.
       The allowed string length is 1 to 32, and the allowed content is
       ASCII characters from 33 to 126. "
   ::= { sm24dp4xaSNMPv3GroupConfEntry 4 }


sm24dp4xaSNMPv3GroupConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sm24dp4xaSNMPv3GroupConfEntry 5 }

sm24dp4xaSNMPv3ViewsConfTable OBJECT-TYPE
   SYNTAX      SEQUENCE OF SM24DP4XASNMPv3ViewsConfEntry
   MAX-ACCESS  not-accessible
   STATUS      current
   DESCRIPTION
       "A list of snmpv3 view configuration entry."
   ::= { sm24dp4xaSnmp 8 }

sm24dp4xaSNMPv3ViewsConfEntry OBJECT-TYPE
   SYNTAX      SM24DP4XASNMPv3ViewsConfEntry
   MAX-ACCESS  not-accessible
   STATUS      current
   DESCRIPTION
       "This is the entry information for snmpv3 view configuration."
   INDEX    { sm24dp4xaSNMPv3ViewsConfIndex  }
   ::= { sm24dp4xaSNMPv3ViewsConfTable 1 }

SM24DP4XASNMPv3ViewsConfEntry ::= SEQUENCE {
    sm24dp4xaSNMPv3ViewsConfIndex                   Integer32,
    sm24dp4xaSNMPv3ViewsConfViewName            DisplayString,
    sm24dp4xaSNMPv3ViewsConfViewType                Integer32,
    sm24dp4xaSNMPv3ViewsConfOIDSubtree          DisplayString,
    sm24dp4xaSNMPv3ViewsConfRowStatus               RowStatus
}

sm24dp4xaSNMPv3ViewsConfIndex OBJECT-TYPE
   SYNTAX       Integer32(1..65535)
   MAX-ACCESS   read-write
   STATUS       current
   DESCRIPTION
       "view configuration index."
   ::= { sm24dp4xaSNMPv3ViewsConfEntry 1 }

sm24dp4xaSNMPv3ViewsConfViewName OBJECT-TYPE
   SYNTAX       DisplayString
   MAX-ACCESS   read-write
   STATUS       current
   DESCRIPTION
       "A string identifying the view name that this entry should belong to.
       The allowed string length is 1 to 32, and the allowed content is
       ASCII characters from 33 to 126. "
   ::= { sm24dp4xaSNMPv3ViewsConfEntry 2 }

sm24dp4xaSNMPv3ViewsConfViewType OBJECT-TYPE
   SYNTAX       Integer32
   MAX-ACCESS   read-write
   STATUS       current
   DESCRIPTION
       "1:included
       2:excluded"
   ::= { sm24dp4xaSNMPv3ViewsConfEntry 3 }

sm24dp4xaSNMPv3ViewsConfOIDSubtree OBJECT-TYPE
   SYNTAX       DisplayString
   MAX-ACCESS   read-write
   STATUS       current
   DESCRIPTION
       "The OID defining the root of the subtree to add to the named view.
       The allowed OID length is 1 to 128. The allowed string content is
       digital number or asterisk(*)"
   ::= { sm24dp4xaSNMPv3ViewsConfEntry 4 }

sm24dp4xaSNMPv3ViewsConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sm24dp4xaSNMPv3ViewsConfEntry 5 }


sm24dp4xaSNMPv3AccessConfTable OBJECT-TYPE
   SYNTAX      SEQUENCE OF SM24DP4XASNMPv3AccessConfEntry
   MAX-ACCESS  not-accessible
   STATUS      current
   DESCRIPTION
       "A list of snmpv3 access configuration entry."
   ::= { sm24dp4xaSnmp 9 }

sm24dp4xaSNMPv3AccessConfEntry OBJECT-TYPE
   SYNTAX      SM24DP4XASNMPv3AccessConfEntry
   MAX-ACCESS  not-accessible
   STATUS      current
   DESCRIPTION
       "This is the entry information for snmpv3 access configuration."
   INDEX    { sm24dp4xaSNMPv3AccessConfIndex  }
   ::= { sm24dp4xaSNMPv3AccessConfTable 1 }

SM24DP4XASNMPv3AccessConfEntry ::= SEQUENCE {
    sm24dp4xaSNMPv3AccessConfIndex                    Integer32,
    sm24dp4xaSNMPv3AccessConfGroupName            DisplayString,
    sm24dp4xaSNMPv3AccessConfSecurityModel            Integer32,
    sm24dp4xaSNMPv3AccessConfSecurityLevel            Integer32,
    sm24dp4xaSNMPv3AccessConfReadViewName         DisplayString,
    sm24dp4xaSNMPv3AccessConfWriteViewName        DisplayString,
    sm24dp4xaSNMPv3AccessConfRowStatus                RowStatus
}

sm24dp4xaSNMPv3AccessConfIndex OBJECT-TYPE
   SYNTAX       Integer32(1..65535)
   MAX-ACCESS   read-write
   STATUS       current
   DESCRIPTION
       "Access configuration index"
   ::= { sm24dp4xaSNMPv3AccessConfEntry 1 }

sm24dp4xaSNMPv3AccessConfGroupName OBJECT-TYPE
   SYNTAX       DisplayString
   MAX-ACCESS   read-write
   STATUS       current
   DESCRIPTION
       "Group name from Group configuration."
   ::= { sm24dp4xaSNMPv3AccessConfEntry 2 }

sm24dp4xaSNMPv3AccessConfSecurityModel OBJECT-TYPE
   SYNTAX       Integer32
   MAX-ACCESS   read-write
   STATUS       current
   DESCRIPTION
       "0:any
        1:v1
	2:v2c
	3:usm"
   ::= { sm24dp4xaSNMPv3AccessConfEntry 3 }

sm24dp4xaSNMPv3AccessConfSecurityLevel OBJECT-TYPE
   SYNTAX       Integer32
   MAX-ACCESS   read-write
   STATUS       current
   DESCRIPTION
       "1:NoAuth, NoPriv
       2:Auth, NoPriv
       3:Auth, Priv"
   ::= { sm24dp4xaSNMPv3AccessConfEntry 4 }

sm24dp4xaSNMPv3AccessConfReadViewName OBJECT-TYPE
   SYNTAX       DisplayString
   MAX-ACCESS   read-write
   STATUS       current
   DESCRIPTION
       "Read View Name from View configuration."
   ::= { sm24dp4xaSNMPv3AccessConfEntry 5 }

sm24dp4xaSNMPv3AccessConfWriteViewName OBJECT-TYPE
   SYNTAX       DisplayString
   MAX-ACCESS   read-write
   STATUS       current
   DESCRIPTION
       "Write View Name from View configuration."
   ::= { sm24dp4xaSNMPv3AccessConfEntry 6 }

sm24dp4xaSNMPv3AccessConfRowStatus OBJECT-TYPE
   SYNTAX       RowStatus
   MAX-ACCESS   read-create
   STATUS       current
   DESCRIPTION
       "This object indicates the status of this entry, and is
       used to create(5)/delete(6) entries.  Any object in an entry of
       this table may be modified while the value of the
       corresponding instance of this object is active(1).
       createAndGo, notReady not supported."
   ::= { sm24dp4xaSNMPv3AccessConfEntry 7 }

-- =======================================================================================================================
sm24dp4xaDHCPServer                                     OBJECT IDENTIFIER ::= { sm24dp4xaSystem 9 }

sm24dp4xaDHCPServerConf                                 OBJECT IDENTIFIER ::= { sm24dp4xaDHCPServer 1 }

sm24dp4xaDHCPServerMode OBJECT-TYPE
   SYNTAX      Integer32 (0|1)
   MAX-ACCESS  read-write
   STATUS      current
   DESCRIPTION
       "default: 0,
        Global Mode :
        0: Disable,
        1: Enable.
       "
   ::= { sm24dp4xaDHCPServerConf 1 }

sm24dp4xaVLANModeTable OBJECT-TYPE
   SYNTAX      SEQUENCE OF SM24DP4XAVLANModeEntry
   MAX-ACCESS  not-accessible
   STATUS      current
   DESCRIPTION
       "A table of VLAN Mode for DHCP Server."
    ::= { sm24dp4xaDHCPServerConf 2 }

sm24dp4xaVLANModeEntry OBJECT-TYPE
    SYNTAX        SM24DP4XAVLANModeEntry
    MAX-ACCESS    not-accessible
    STATUS        current
    DESCRIPTION
        "An entry in the sm24dp4xaVLANModeTable."
    INDEX        { sm24dp4xaVLANModeIndex }
    ::= { sm24dp4xaVLANModeTable 1 }

SM24DP4XAVLANModeEntry ::=
    SEQUENCE {
        sm24dp4xaVLANModeIndex                            Integer32,
        sm24dp4xaVLANModeRangeLow                         Integer32,
        sm24dp4xaVLANModeRangeHigh                        Integer32,
        sm24dp4xaVLANModeEnable                           Integer32,
		sm24dp4xaVLANModeRowStatus                        RowStatus
    }

sm24dp4xaVLANModeIndex OBJECT-TYPE
   SYNTAX      Integer32 (1..2048)
   MAX-ACCESS  not-accessible
   STATUS      current
   DESCRIPTION
       "VLAN Mode table index, range: 1-2048."
   ::= {sm24dp4xaVLANModeEntry 1 }

sm24dp4xaVLANModeRangeLow OBJECT-TYPE
   SYNTAX      Integer32 (1..4095)
   MAX-ACCESS  read-create
   STATUS      current
   DESCRIPTION
       "VLAN Mode low range: 1-4095."
   ::= {sm24dp4xaVLANModeEntry 2 }

sm24dp4xaVLANModeRangeHigh OBJECT-TYPE
   SYNTAX      Integer32 (1..4095)
   MAX-ACCESS  read-create
   STATUS      current
   DESCRIPTION
       "VLAN Mode high range: 1-4095."
   ::= {sm24dp4xaVLANModeEntry 3 }

sm24dp4xaVLANModeEnable OBJECT-TYPE
   SYNTAX      Integer32 (0..1)
   MAX-ACCESS  read-create
   STATUS      current
   DESCRIPTION
       "VLAN Mode Enable, Enable:1, Disable:0."
   ::= {sm24dp4xaVLANModeEntry 4 }

sm24dp4xaVLANModeRowStatus OBJECT-TYPE
   SYNTAX      RowStatus
   MAX-ACCESS  read-create
   STATUS      current
   DESCRIPTION
      "This object indicates the status of this entry, and is
       used to create/delete entries.  Any object in an entry of
       this table may be modified while the value of the
       corresponding instance of this object is active(1).
       createAndGo, notReady not supported."
   ::= {     sm24dp4xaVLANModeEntry 5 }



-- sm24dp4xaDHCPServerBindingType OBJECT-TYPE
--   SYNTAX      Integer32 (0|1|2|3)
--   MAX-ACCESS  read-only
--   STATUS      current
--   DESCRIPTION
--       "default: None,
--        Global Mode :
--        0: None,
--        1: Automatic,
--        2: Manual,
--        3: Expired.
--       "
--   ::= { sm24dp4xaDHCPServerConf 2 }

-- sm24dp4xaDHCPServerBindingState OBJECT-TYPE
--   SYNTAX      Integer32 (0|1|2|3)
--   MAX-ACCESS  read-only
--   STATUS      current
--   DESCRIPTION
--       "default: None,
--        Global Mode :
--        0: None,
--        1: Allocated,
--        2: Committed,
--        3: Expired.
--       "
--   ::= { sm24dp4xaDHCPServerConf 3 }

-- sm24dp4xaDHCPServerBindingIP OBJECT-TYPE
--   SYNTAX      DisplayString
--   MAX-ACCESS  read-only
--   STATUS      current
--   DESCRIPTION
--       "The DHCP Server Binding IP"
--   ::= { sm24dp4xaDHCPServerConf 4 }


sm24dp4xaDHCPServerExcludedIP                                 OBJECT IDENTIFIER ::= { sm24dp4xaDHCPServer 2 }

sm24dp4xaExcludedIPTable OBJECT-TYPE
   SYNTAX      SEQUENCE OF SM24DP4XAExcludedIPEntry
   MAX-ACCESS  not-accessible
   STATUS      current
   DESCRIPTION
       "A table of Excluded IP for DHCP Server."
    ::= { sm24dp4xaDHCPServerExcludedIP 1 }

sm24dp4xaExcludedIPEntry OBJECT-TYPE
    SYNTAX        SM24DP4XAExcludedIPEntry
    MAX-ACCESS    not-accessible
    STATUS        current
    DESCRIPTION
        "An entry in the sm24dp4xaExcludedIPTable."
    INDEX        { sm24dp4xaExcludedIPIndex }
    ::= { sm24dp4xaExcludedIPTable 1 }

SM24DP4XAExcludedIPEntry ::=
    SEQUENCE {
        sm24dp4xaExcludedIPIndex                            Integer32,
        sm24dp4xaExcludedIPRangeLow                         IpAddress,
        sm24dp4xaExcludedIPRangeHigh                        IpAddress,
		sm24dp4xaExcludedIPRowStatus                        RowStatus
    }

sm24dp4xaExcludedIPIndex OBJECT-TYPE
   SYNTAX      Integer32 (1..16)
   MAX-ACCESS  not-accessible
   STATUS      current
   DESCRIPTION
       "Excluded IP table index, range: 1-16."
   ::= {sm24dp4xaExcludedIPEntry 1 }

sm24dp4xaExcludedIPRangeLow OBJECT-TYPE
   SYNTAX      IpAddress
   MAX-ACCESS  read-create
   STATUS      current
   DESCRIPTION
       "ExcludedIP low range: 1-4095."
   ::= {sm24dp4xaExcludedIPEntry 2 }

sm24dp4xaExcludedIPRangeHigh OBJECT-TYPE
   SYNTAX      IpAddress
   MAX-ACCESS  read-create
   STATUS      current
   DESCRIPTION
       "ExcludedIP high range: 1-4095."
   ::= {sm24dp4xaExcludedIPEntry 3 }

sm24dp4xaExcludedIPRowStatus OBJECT-TYPE
   SYNTAX      RowStatus
   MAX-ACCESS  read-create
   STATUS      current
   DESCRIPTION
      "This object indicates the status of this entry, and is
       used to create/delete entries.  Any object in an entry of
       this table may be modified while the value of the
       corresponding instance of this object is active(1).
       createAndGo, notReady not supported."
   ::= {sm24dp4xaExcludedIPEntry 4 }



sm24dp4xaDHCPServerPoolConf                                 OBJECT IDENTIFIER ::= { sm24dp4xaDHCPServer 3 }

sm24dp4xaDHCPServerPoolTable OBJECT-TYPE
   SYNTAX      SEQUENCE OF SM24DP4XADHCPServerPoolEntry
   MAX-ACCESS  not-accessible
   STATUS      current
   DESCRIPTION
       "This is the entry information for DHCP Pool."
   ::= { sm24dp4xaDHCPServerPoolConf 1 }

sm24dp4xaDHCPServerPoolEntry OBJECT-TYPE
   SYNTAX      SM24DP4XADHCPServerPoolEntry
   MAX-ACCESS  not-accessible
   STATUS      current
   DESCRIPTION
       " "
   INDEX    { sm24dp4xaDHCPServerConfIndex  }
   ::= { sm24dp4xaDHCPServerPoolTable 1 }

SM24DP4XADHCPServerPoolEntry ::= SEQUENCE {
    sm24dp4xaDHCPServerConfIndex               Integer32,
    sm24dp4xaDHCPServerPoolName                DisplayString,
    sm24dp4xaDHCPServerPoolType                Integer32,
    sm24dp4xaDHCPServerIP                      IpAddress,
    sm24dp4xaDHCPServerSubnetMask              IpAddress,
    sm24dp4xaDHCPServerLeaseTimeDays           Integer32,
    sm24dp4xaDHCPServerLeaseTimeHours          Integer32,
    sm24dp4xaDHCPServerLeaseTimeMinutes        Integer32,
    sm24dp4xaDHCPServerDomainName              DisplayString,
    sm24dp4xaDHCPServerBroadcastAddress        IpAddress,
    sm24dp4xaDHCPServerDefRouter1              IpAddress,
    sm24dp4xaDHCPServerDefRouter2              IpAddress,
    sm24dp4xaDHCPServerDefRouter3              IpAddress,
    sm24dp4xaDHCPServerDefRouter4              IpAddress,
    sm24dp4xaDHCPServerDNSServer1              IpAddress,
    sm24dp4xaDHCPServerDNSServer2              IpAddress,
    sm24dp4xaDHCPServerDNSServer3              IpAddress,
    sm24dp4xaDHCPServerDNSServer4              IpAddress,
    sm24dp4xaDHCPServerNTPServer1              IpAddress,
    sm24dp4xaDHCPServerNTPServer2              IpAddress,
    sm24dp4xaDHCPServerNTPServer3              IpAddress,
    sm24dp4xaDHCPServerNTPServer4              IpAddress,
    sm24dp4xaDHCPServerNetbiosType             Integer32,
    sm24dp4xaDHCPServerNetbiosScope            DisplayString,
    sm24dp4xaDHCPServerNetbiosNameServer1      IpAddress,
    sm24dp4xaDHCPServerNetbiosNameServer2      IpAddress,
    sm24dp4xaDHCPServerNetbiosNameServer3      IpAddress,
    sm24dp4xaDHCPServerNetbiosNameServer4      IpAddress,
    sm24dp4xaDHCPServerNisDomainName           DisplayString,
    sm24dp4xaDHCPServerNisServer1              IpAddress,
    sm24dp4xaDHCPServerNisServer2              IpAddress,
    sm24dp4xaDHCPServerNisServer3              IpAddress,
    sm24dp4xaDHCPServerNisServer4              IpAddress,
    sm24dp4xaDHCPServerClientIDType            Integer32,
    sm24dp4xaDHCPServerClientID                DisplayString,
    sm24dp4xaDHCPServerHWAddr                  DisplayString,
    sm24dp4xaDHCPServerClientName              DisplayString,
    sm24dp4xaDHCPServerVendorClassID1          DisplayString,
    sm24dp4xaDHCPServerVendorSpecificInfo1     DisplayString,
    sm24dp4xaDHCPServerVendorClassID2          DisplayString,
    sm24dp4xaDHCPServerVendorSpecificInfo2     DisplayString,
    sm24dp4xaDHCPServerVendorClassID3          DisplayString,
    sm24dp4xaDHCPServerVendorSpecificInfo3     DisplayString,
    sm24dp4xaDHCPServerVendorClassID4          DisplayString,
    sm24dp4xaDHCPServerVendorSpecificInfo4     DisplayString,
--    sm24dp4xaDHCPServerVendorClassID5          DisplayString,
--    sm24dp4xaDHCPServerVendorSpecificInfo5     DisplayString,
--    sm24dp4xaDHCPServerVendorClassID6          DisplayString,
--    sm24dp4xaDHCPServerVendorSpecificInfo6     DisplayString,
--    sm24dp4xaDHCPServerVendorClassID7          DisplayString,
--    sm24dp4xaDHCPServerVendorSpecificInfo7     DisplayString,
--    sm24dp4xaDHCPServerVendorClassID8          DisplayString,
--    sm24dp4xaDHCPServerVendorSpecificInfo8     DisplayString,
    sm24dp4xaDHCPServerLightingServer          DisplayString,
    sm24dp4xaDHCPServerRowStatus               RowStatus
}

sm24dp4xaDHCPServerConfIndex OBJECT-TYPE
   SYNTAX      Integer32 (1..64)
   MAX-ACCESS  not-accessible
   STATUS      current
   DESCRIPTION
       " pool, range : 1 - 64. "
   ::= { sm24dp4xaDHCPServerPoolEntry 1 }

sm24dp4xaDHCPServerPoolName OBJECT-TYPE
   SYNTAX      DisplayString(SIZE (1..32))
   MAX-ACCESS  read-create
   STATUS      current
   DESCRIPTION
       " DHCP pool name. "
   ::= { sm24dp4xaDHCPServerPoolEntry 2 }

sm24dp4xaDHCPServerPoolType OBJECT-TYPE
   SYNTAX      Integer32(0|1|2)
   MAX-ACCESS  read-create
   STATUS      current
   DESCRIPTION
       " DHCP Server Pool Type.
	   0:None
	   1:Network
	   2:Host, please set DHCP Server IP first."
   ::= { sm24dp4xaDHCPServerPoolEntry 3 }

sm24dp4xaDHCPServerIP OBJECT-TYPE
   SYNTAX      IpAddress
   MAX-ACCESS  read-create
   STATUS      current
   DESCRIPTION
       " DHCP Server IP. "
   ::= { sm24dp4xaDHCPServerPoolEntry 4 }

sm24dp4xaDHCPServerSubnetMask OBJECT-TYPE
   SYNTAX      IpAddress
   MAX-ACCESS  read-create
   STATUS      current
   DESCRIPTION
       " DHCP Server IPv4 Subnet Mask. "
   ::= { sm24dp4xaDHCPServerPoolEntry 5}

sm24dp4xaDHCPServerLeaseTimeDays OBJECT-TYPE
   SYNTAX      Integer32(0..365)
   MAX-ACCESS  read-create
   STATUS      current
   DESCRIPTION
       " DHCP Server IPv4 Lease Time:Days. "
   ::= { sm24dp4xaDHCPServerPoolEntry 6 }

sm24dp4xaDHCPServerLeaseTimeHours OBJECT-TYPE
   SYNTAX      Integer32(0..23)
   MAX-ACCESS  read-create
   STATUS      current
   DESCRIPTION
       " DHCP Server IPv4 Lease Time:Hours. "
   ::= { sm24dp4xaDHCPServerPoolEntry 7 }

sm24dp4xaDHCPServerLeaseTimeMinutes OBJECT-TYPE
   SYNTAX      Integer32(0..59)
   MAX-ACCESS  read-create
   STATUS      current
   DESCRIPTION
       " DHCP Server IPv4 Lease Time:Minutes. "
   ::= { sm24dp4xaDHCPServerPoolEntry 8 }

sm24dp4xaDHCPServerDomainName OBJECT-TYPE
   SYNTAX      DisplayString(SIZE (0..128))
   MAX-ACCESS  read-create
   STATUS      current
   DESCRIPTION
       " DHCP Server Domain Name. "
   ::= { sm24dp4xaDHCPServerPoolEntry 9 }

sm24dp4xaDHCPServerBroadcastAddress OBJECT-TYPE
   SYNTAX      IpAddress
   MAX-ACCESS  read-create
   STATUS      current
   DESCRIPTION
       " DHCP Server IPv4 Broadcast Address. "
   ::= { sm24dp4xaDHCPServerPoolEntry 10 }

sm24dp4xaDHCPServerDefRouter1 OBJECT-TYPE
   SYNTAX      IpAddress
   MAX-ACCESS  read-create
   STATUS      current
   DESCRIPTION
       " DHCP Server IPv4 Default Router 1. "
   ::= { sm24dp4xaDHCPServerPoolEntry 11 }

sm24dp4xaDHCPServerDefRouter2 OBJECT-TYPE
   SYNTAX      IpAddress
   MAX-ACCESS  read-create
   STATUS      current
   DESCRIPTION
       " DHCP Server IPv4 Default Router 2. "
   ::= { sm24dp4xaDHCPServerPoolEntry 12 }

sm24dp4xaDHCPServerDefRouter3 OBJECT-TYPE
   SYNTAX      IpAddress
   MAX-ACCESS  read-create
   STATUS      current
   DESCRIPTION
       " DHCP Server IPv4 Default Router 3. "
   ::= { sm24dp4xaDHCPServerPoolEntry 13 }

sm24dp4xaDHCPServerDefRouter4 OBJECT-TYPE
   SYNTAX      IpAddress
   MAX-ACCESS  read-create
   STATUS      current
   DESCRIPTION
       " DHCP Server IPv4 Default Router 4. "
   ::= { sm24dp4xaDHCPServerPoolEntry 14 }

sm24dp4xaDHCPServerDNSServer1 OBJECT-TYPE
   SYNTAX      IpAddress
   MAX-ACCESS  read-create
   STATUS      current
   DESCRIPTION
       " DHCP Server DNS Server 1. "
   ::= { sm24dp4xaDHCPServerPoolEntry 15 }

sm24dp4xaDHCPServerDNSServer2 OBJECT-TYPE
   SYNTAX      IpAddress
   MAX-ACCESS  read-create
   STATUS      current
   DESCRIPTION
       " DHCP Server DNS Server 2. "
   ::= { sm24dp4xaDHCPServerPoolEntry 16 }

sm24dp4xaDHCPServerDNSServer3 OBJECT-TYPE
   SYNTAX      IpAddress
   MAX-ACCESS  read-create
   STATUS      current
   DESCRIPTION
       " DHCP Server DNS Server 3. "
   ::= { sm24dp4xaDHCPServerPoolEntry 17 }

sm24dp4xaDHCPServerDNSServer4 OBJECT-TYPE
   SYNTAX      IpAddress
   MAX-ACCESS  read-create
   STATUS      current
   DESCRIPTION
       " DHCP Server DNS Server 4. "
   ::= { sm24dp4xaDHCPServerPoolEntry 18 }

sm24dp4xaDHCPServerNTPServer1 OBJECT-TYPE
   SYNTAX      IpAddress
   MAX-ACCESS  read-create
   STATUS      current
   DESCRIPTION
       " DHCP Server NTP Server 1. "
   ::= { sm24dp4xaDHCPServerPoolEntry 19 }

sm24dp4xaDHCPServerNTPServer2 OBJECT-TYPE
   SYNTAX      IpAddress
   MAX-ACCESS  read-create
   STATUS      current
   DESCRIPTION
       " DHCP Server NTP Server 2. "
   ::= { sm24dp4xaDHCPServerPoolEntry 20 }

sm24dp4xaDHCPServerNTPServer3 OBJECT-TYPE
   SYNTAX      IpAddress
   MAX-ACCESS  read-create
   STATUS      current
   DESCRIPTION
       " DHCP Server NTP Server 3. "
   ::= { sm24dp4xaDHCPServerPoolEntry 21 }

sm24dp4xaDHCPServerNTPServer4 OBJECT-TYPE
   SYNTAX      IpAddress
   MAX-ACCESS  read-create
   STATUS      current
   DESCRIPTION
       " DHCP Server NTP Server 4. "
   ::= { sm24dp4xaDHCPServerPoolEntry 22 }

sm24dp4xaDHCPServerNetbiosType OBJECT-TYPE
   SYNTAX      Integer32(1..4)
   MAX-ACCESS  read-create
   STATUS      current
   DESCRIPTION
       " DHCP Server Netbios Node Type.
	   0:None
	   1:B-node
	   2:P-node
	   3:M-node
	   4:H-node"
   ::= { sm24dp4xaDHCPServerPoolEntry 23 }

sm24dp4xaDHCPServerNetbiosScope OBJECT-TYPE
   SYNTAX      DisplayString(SIZE (0..128))
   MAX-ACCESS  read-create
   STATUS      current
   DESCRIPTION
       " DHCP Server Netbios Scope. "
   ::= { sm24dp4xaDHCPServerPoolEntry 24 }

sm24dp4xaDHCPServerNetbiosNameServer1 OBJECT-TYPE
   SYNTAX      IpAddress
   MAX-ACCESS  read-create
   STATUS      current
   DESCRIPTION
       " DHCP Server Netbios Name Server 1. "
   ::= { sm24dp4xaDHCPServerPoolEntry 25 }

sm24dp4xaDHCPServerNetbiosNameServer2 OBJECT-TYPE
   SYNTAX      IpAddress
   MAX-ACCESS  read-create
   STATUS      current
   DESCRIPTION
       " DHCP Server Netbios Name Server 2. "
   ::= { sm24dp4xaDHCPServerPoolEntry 26 }

sm24dp4xaDHCPServerNetbiosNameServer3 OBJECT-TYPE
   SYNTAX      IpAddress
   MAX-ACCESS  read-create
   STATUS      current
   DESCRIPTION
       " DHCP Server Netbios Name Server 3. "
   ::= { sm24dp4xaDHCPServerPoolEntry 27 }

sm24dp4xaDHCPServerNetbiosNameServer4 OBJECT-TYPE
   SYNTAX      IpAddress
   MAX-ACCESS  read-create
   STATUS      current
   DESCRIPTION
       " DHCP Server Netbios Name Server 4. "
   ::= { sm24dp4xaDHCPServerPoolEntry 28 }

sm24dp4xaDHCPServerNisDomainName OBJECT-TYPE
   SYNTAX      DisplayString(SIZE (0..128))
   MAX-ACCESS  read-create
   STATUS      current
   DESCRIPTION
       " DHCP Server Nis Domain Name. "
   ::= { sm24dp4xaDHCPServerPoolEntry 29 }

sm24dp4xaDHCPServerNisServer1 OBJECT-TYPE
   SYNTAX      IpAddress
   MAX-ACCESS  read-create
   STATUS      current
   DESCRIPTION
       " DHCP Server Nis Server 1. "
   ::= { sm24dp4xaDHCPServerPoolEntry 30 }

sm24dp4xaDHCPServerNisServer2 OBJECT-TYPE
   SYNTAX      IpAddress
   MAX-ACCESS  read-create
   STATUS      current
   DESCRIPTION
       " DHCP Server Nis Server 2. "
   ::= { sm24dp4xaDHCPServerPoolEntry 31 }

sm24dp4xaDHCPServerNisServer3 OBJECT-TYPE
   SYNTAX      IpAddress
   MAX-ACCESS  read-create
   STATUS      current
   DESCRIPTION
       " DHCP Server Nis Server 3. "
   ::= { sm24dp4xaDHCPServerPoolEntry 32 }

sm24dp4xaDHCPServerNisServer4 OBJECT-TYPE
   SYNTAX      IpAddress
   MAX-ACCESS  read-create
   STATUS      current
   DESCRIPTION
       " DHCP Server Nis Server 4. "
   ::= { sm24dp4xaDHCPServerPoolEntry 33 }

sm24dp4xaDHCPServerClientIDType OBJECT-TYPE
   SYNTAX      Integer32(0..2)
   MAX-ACCESS  read-create
   STATUS      current
   DESCRIPTION
       " DHCP Server Client ID Type.
	   0:None
	   1:FQDN
	   2:MAC"
   ::= { sm24dp4xaDHCPServerPoolEntry 34 }

sm24dp4xaDHCPServerClientID OBJECT-TYPE
   SYNTAX      DisplayString(SIZE (0..128))
   MAX-ACCESS  read-create
   STATUS      current
   DESCRIPTION
       " DHCP Server Pool Client ID. "
   ::= { sm24dp4xaDHCPServerPoolEntry 35 }

sm24dp4xaDHCPServerHWAddr OBJECT-TYPE
   SYNTAX      DisplayString(SIZE (0..17))
   MAX-ACCESS  read-create
   STATUS      current
   DESCRIPTION
       " DHCP Server Pool Hardware Address. "
   ::= { sm24dp4xaDHCPServerPoolEntry 36 }

sm24dp4xaDHCPServerClientName OBJECT-TYPE
   SYNTAX      DisplayString(SIZE (0..32))
   MAX-ACCESS  read-create
   STATUS      current
   DESCRIPTION
       " DHCP Server Pool Client Name. "
   ::= { sm24dp4xaDHCPServerPoolEntry 37 }

sm24dp4xaDHCPServerVendorClassID1 OBJECT-TYPE
   SYNTAX      DisplayString(SIZE (0..64))
   MAX-ACCESS  read-create
   STATUS      current
   DESCRIPTION
       " DHCP Server Vendor Class ID 1. Please also set VendorSpecificInfo1."
   ::= { sm24dp4xaDHCPServerPoolEntry 38 }

sm24dp4xaDHCPServerVendorSpecificInfo1 OBJECT-TYPE
   SYNTAX      DisplayString(SIZE (0..32))
   MAX-ACCESS  read-create
   STATUS      current
   DESCRIPTION
       " DHCP Server Vendor Specific Info 1. Please also set VendorClassID1."
   ::= { sm24dp4xaDHCPServerPoolEntry 39 }

sm24dp4xaDHCPServerVendorClassID2 OBJECT-TYPE
   SYNTAX      DisplayString(SIZE (0..64))
   MAX-ACCESS  read-create
   STATUS      current
   DESCRIPTION
       " DHCP Server Vendor Class ID 2. Please also set VendorSpecificInfo2."
   ::= { sm24dp4xaDHCPServerPoolEntry 40 }

sm24dp4xaDHCPServerVendorSpecificInfo2 OBJECT-TYPE
   SYNTAX      DisplayString(SIZE (0..32))
   MAX-ACCESS  read-create
   STATUS      current
   DESCRIPTION
       " DHCP Server Vendor Specific Info 2. Please also set VendorClassID2."
   ::= { sm24dp4xaDHCPServerPoolEntry 41 }

sm24dp4xaDHCPServerVendorClassID3 OBJECT-TYPE
   SYNTAX      DisplayString(SIZE (0..64))
   MAX-ACCESS  read-create
   STATUS      current
   DESCRIPTION
       " DHCP Server Vendor Class ID 3. Please also set VendorSpecificInfo3."
   ::= { sm24dp4xaDHCPServerPoolEntry 42 }

sm24dp4xaDHCPServerVendorSpecificInfo3 OBJECT-TYPE
   SYNTAX      DisplayString(SIZE (0..32))
   MAX-ACCESS  read-create
   STATUS      current
   DESCRIPTION
       " DHCP Server Vendor Specific Info 3. Please also set VendorClassID3."
   ::= { sm24dp4xaDHCPServerPoolEntry 43 }

sm24dp4xaDHCPServerVendorClassID4 OBJECT-TYPE
   SYNTAX      DisplayString(SIZE (0..64))
   MAX-ACCESS  read-create
   STATUS      current
   DESCRIPTION
       " DHCP Server Vendor Class ID 4. Please also set VendorSpecificInfo4."
   ::= { sm24dp4xaDHCPServerPoolEntry 44 }

sm24dp4xaDHCPServerVendorSpecificInfo4 OBJECT-TYPE
   SYNTAX      DisplayString(SIZE (0..32))
   MAX-ACCESS  read-create
   STATUS      current
   DESCRIPTION
       " DHCP Server Vendor Specific Info 4. Please also set VendorClassID4."
   ::= { sm24dp4xaDHCPServerPoolEntry 45 }

--sm24dp4xaDHCPServerVendorClassID5 OBJECT-TYPE
--   SYNTAX      DisplayString(SIZE (0..64))
--   MAX-ACCESS  read-create
--   STATUS      current
--   DESCRIPTION
--       " DHCP Server Vendor Class ID 5. Please also set VendorSpecificInfo5."
--   ::= { sm24dp4xaDHCPServerPoolEntry 46 }
--
--sm24dp4xaDHCPServerVendorSpecificInfo5 OBJECT-TYPE
--   SYNTAX      DisplayString(SIZE (0..32))
--   MAX-ACCESS  read-create
--   STATUS      current
--   DESCRIPTION
--       " DHCP Server Vendor Specific Info 5. Please also set VendorClassID5."
--   ::= { sm24dp4xaDHCPServerPoolEntry 47 }
--
--sm24dp4xaDHCPServerVendorClassID6 OBJECT-TYPE
--   SYNTAX      DisplayString(SIZE (0..64))
--   MAX-ACCESS  read-create
--   STATUS      current
--   DESCRIPTION
--       " DHCP Server Vendor Class ID 6. Please also set VendorSpecificInfo6."
--   ::= { sm24dp4xaDHCPServerPoolEntry 48 }
--
--sm24dp4xaDHCPServerVendorSpecificInfo6 OBJECT-TYPE
--   SYNTAX      DisplayString(SIZE (0..32))
--   MAX-ACCESS  read-create
--   STATUS      current
--   DESCRIPTION
--       " DHCP Server Vendor Specific Info 6. Please also set VendorClassID6."
--   ::= { sm24dp4xaDHCPServerPoolEntry 49 }
--
--sm24dp4xaDHCPServerVendorClassID7 OBJECT-TYPE
--   SYNTAX      DisplayString(SIZE (0..64))
--   MAX-ACCESS  read-create
--   STATUS      current
--   DESCRIPTION
--       " DHCP Server Vendor Class ID 7. Please also set VendorSpecificInfo7."
--   ::= { sm24dp4xaDHCPServerPoolEntry 50 }
--
--sm24dp4xaDHCPServerVendorSpecificInfo7 OBJECT-TYPE
--   SYNTAX      DisplayString(SIZE (0..32))
--   MAX-ACCESS  read-create
--   STATUS      current
--   DESCRIPTION
--       " DHCP Server Vendor Specific Info 7. Please also set VendorClassID7."
--   ::= { sm24dp4xaDHCPServerPoolEntry 51 }
--
--sm24dp4xaDHCPServerVendorClassID8 OBJECT-TYPE
--   SYNTAX      DisplayString(SIZE (0..64))
--   MAX-ACCESS  read-create
--   STATUS      current
--   DESCRIPTION
--       " DHCP Server Vendor Class ID 8. Please also set VendorSpecificInfo8."
--   ::= { sm24dp4xaDHCPServerPoolEntry 52 }
--
--sm24dp4xaDHCPServerVendorSpecificInfo8 OBJECT-TYPE
--   SYNTAX      DisplayString(SIZE (0..32))
--   MAX-ACCESS  read-create
--   STATUS      current
--   DESCRIPTION
--       " DHCP Server Vendor Specific Info 8. Please also set VendorClassID8."
--   ::= { sm24dp4xaDHCPServerPoolEntry 53 }

sm24dp4xaDHCPServerLightingServer OBJECT-TYPE
   SYNTAX      DisplayString(SIZE (7..15))
   MAX-ACCESS  read-create
   STATUS      current
   DESCRIPTION
       "DHCP option 229.
        Specify a lighting server available to the client."
   ::= { sm24dp4xaDHCPServerPoolEntry 54 }

sm24dp4xaDHCPServerRowStatus OBJECT-TYPE
   SYNTAX      RowStatus
   MAX-ACCESS  read-create
   STATUS      current
   DESCRIPTION
      "This object indicates the status of this entry, and is
       used to create/delete entries.  Any object in an entry of
       this table may be modified while the value of the
       corresponding instance of this object is active(1).
       createAndGo, notReady not supported."
   ::= {sm24dp4xaDHCPServerPoolEntry 55 }

-- =======================================================================================================================
sm24dp4xaVLANConf                                     OBJECT IDENTIFIER ::= { sm24dp4xaSystem 10 }

sm24dp4xaVLAN                                     OBJECT IDENTIFIER ::= { sm24dp4xaVLANConf 2}

sm24dp4xaVlanStatus              OBJECT IDENTIFIER   ::= { sm24dp4xaVLAN 6 }

--
-- =======================================================================================================================
-- Start sm24dp4xaVlan group
-- =======================================================================================================================
    sm24dp4xaVlanExistingVLANs  OBJECT-TYPE
               SYNTAX      DisplayString
               MAX-ACCESS  read-write
               STATUS      current
               DESCRIPTION
                   "This field shows the VLANs that are created on the switch.
                    More VLANs may be created by using a
                    list syntax where the individual elements are separated by commas.
                    Ranges are specified with a
                    dash separating the lower and upper bound.
                    The following example will create VLANs 1, 10, 11, 12
                    , 13, 200, and 300: 1,10-13,200,300.
                    default: 1."
               ::= {     sm24dp4xaVLAN 1 }

    sm24dp4xaVlanEthertypeforCustomSPorts  OBJECT-TYPE
               SYNTAX      DisplayString
               MAX-ACCESS  read-write
               STATUS      current
               DESCRIPTION
                   "This field specifies the ethertype/TPID (specified in hexadecimal)
                    used for Custom S-ports. The
                    setting is in force for all ports whose Port Type
                    is set to S-Custom-Port.
                    range: 0600-ffff,
                    default: 88a8."
               ::= {     sm24dp4xaVLAN 2 }

    sm24dp4xaVlanTable OBJECT-TYPE
               SYNTAX      SEQUENCE OF     SM24DP4XAVlanEntry
               MAX-ACCESS  not-accessible
               STATUS      current
               DESCRIPTION
                   "Configure Vlan ports Configuration mode.
                    INDEX for this table is ifIndex which is
                    equivalent to the panel port number."
               ::= {     sm24dp4xaVLAN 3 }

    sm24dp4xaVlanEntry OBJECT-TYPE
               SYNTAX          SM24DP4XAVlanEntry
               MAX-ACCESS  not-accessible
               STATUS      current
               DESCRIPTION
                   "The Vlan entry."
               INDEX    {     ifIndex  }
               ::= {     sm24dp4xaVlanTable 1 }

    SM24DP4XAVlanEntry             ::= SEQUENCE {
                sm24dp4xaVlanMode              INTEGER,
                sm24dp4xaVlanPortVLAN          Integer32,
                sm24dp4xaVlanPortType          INTEGER,
                sm24dp4xaVlanIngressFiltering  AdminMode,
                sm24dp4xaVlanVLANTrunking      AdminMode,
                sm24dp4xaVlanIngressAcceptance INTEGER,
                sm24dp4xaVlanEgressTagging     INTEGER,
                sm24dp4xaVlanAllowedVLANs      DisplayString,
                sm24dp4xaVlanForbiddenVLANs    DisplayString
                }

    sm24dp4xaVlanMode OBJECT-TYPE
               SYNTAX      INTEGER{access(0), trunk(1), hybrid(2)}
               MAX-ACCESS  read-write
               STATUS      current
               DESCRIPTION
                   "The port mode determines the fundamental
                    behavior of the port in question.
                    A port can be in one of three modes as described below.
                    0: access,
                    1: trunk,
                    2: hybrid."
               DEFVAL  { access }
               ::= {     sm24dp4xaVlanEntry 2 }

    sm24dp4xaVlanPortVLAN OBJECT-TYPE
               SYNTAX      Integer32(1..4094)
               MAX-ACCESS  read-write
               STATUS      current
               DESCRIPTION
                   "Determines the port's VLAN ID (a.k.a. PVID).
                    range: 1-4095,
                    default: 1."
               ::= {     sm24dp4xaVlanEntry 3 }

    sm24dp4xaVlanPortType OBJECT-TYPE
               SYNTAX      INTEGER { unaware(0), cPort(1), sPort(2), sCustomPort(3) }
               MAX-ACCESS  read-write
               STATUS      current
               DESCRIPTION
                   "Ports in hybrid mode allow for changing the port type,
                    that is, whether a frame's VLAN tag is
                    used to classify the frame on ingress to a particular VLAN,
                    and if so, which TPID it reacts on.
                    Likewise, on egress, the Port Type determines the
                    TPID of the tag, if a tag is required.
                    0: unaware,
                    1: c-Port,
                    2: s-Port,
                    3: s-Custom-Port."
                DEFVAL  { cPort }
               ::= {     sm24dp4xaVlanEntry 4 }

    sm24dp4xaVlanIngressFiltering OBJECT-TYPE
               SYNTAX      AdminMode
               MAX-ACCESS  read-write
               STATUS      current
               DESCRIPTION
                   "Hybrid ports allow for changing ingress filtering.
                    Access and Trunk ports always have ingress
                    filtering enabled.If ingress filtering is enabled,
                    frames classified to
                    a VLAN that the port is not a member of get discarded."
               ::= {     sm24dp4xaVlanEntry 5 }

    sm24dp4xaVlanVLANTrunking OBJECT-TYPE
               SYNTAX      AdminMode
               MAX-ACCESS  read-write
               STATUS      current
               DESCRIPTION
                   "Trunk and Hybrid ports allow for enabling VLAN trunking.
                    When VLAN trunking is enabled, frames
                    classified to unknown VLANs are accepted on the port
                    whether ingress filtering is enabled or not."
               DEFVAL  { disable }
               ::= {     sm24dp4xaVlanEntry 6 }

    sm24dp4xaVlanIngressAcceptance OBJECT-TYPE
               SYNTAX      INTEGER  { taggedAndUntagged  ( 0 ),
                                      taggedOnly ( 1 ),
                                      untaggedOnly ( 2 )
                                    }
               MAX-ACCESS  read-write
               STATUS      current
               DESCRIPTION
                   "Hybrid ports allow for changing the type of frames that are
                    accepted on ingress.
                    0: Tagged and Untagged,
                    1: Tagged Only,
                    2: Untagged Only."
               ::= {     sm24dp4xaVlanEntry 7 }

    sm24dp4xaVlanEgressTagging OBJECT-TYPE
               SYNTAX      INTEGER  { untagPortVlan  ( 0 ),
                                      tagAll ( 1 ),
                                      untagAll ( 2 )
                                    }
               MAX-ACCESS  read-write
               STATUS      current
               DESCRIPTION
                   "Ports in Trunk and Hybrid mode may control the
                    tagging of frames on egress.
                    0: Untag Port VLAN,
                    1: Tag All,
                    2: Untag All."
               ::= {     sm24dp4xaVlanEntry 8 }

    sm24dp4xaVlanAllowedVLANs OBJECT-TYPE
               SYNTAX      DisplayString
               MAX-ACCESS  read-write
               STATUS      current
               DESCRIPTION
                   "Ports in Trunk and Hybrid mode may control which
                    VLANs they are allowed to become members of.
                    Access ports can only be member of one VLAN, the Access VLAN.
                    range: 1~4095.
                    '-': Allowed VLANs is empty."
               ::= {     sm24dp4xaVlanEntry 9 }

    sm24dp4xaVlanForbiddenVLANs OBJECT-TYPE
               SYNTAX      DisplayString
               MAX-ACCESS  read-write
               STATUS      current
               DESCRIPTION
                   "A port may be configured to never be member of one or
                    more VLANs. This is particularly useful
                    when dynamic VLAN protocols like MVRP and GVRP
                    must be prevented from dynamically adding ports
                    to VLANs.
                    range: 1~4095.
                    '-': Forbidden VLANs is empty."
               ::= {     sm24dp4xaVlanEntry 10 }

--sm24dp4xaVLANMembershipStatusTable

    sm24dp4xaVLANMembershipStatusTable OBJECT-TYPE
               SYNTAX      SEQUENCE OF     SM24DP4XAVLANMembershipStatusEntry
               MAX-ACCESS  not-accessible
               STATUS      current
               DESCRIPTION
                   "Vlan membership Status table.
                    INDEX for this table is ifIndex which is
                    equivalent to the panel port number."
               ::= {     sm24dp4xaVlanStatus 1 }

    sm24dp4xaVLANMembershipStatusEntry OBJECT-TYPE
               SYNTAX          SM24DP4XAVLANMembershipStatusEntry
               MAX-ACCESS  not-accessible
               STATUS      current
               DESCRIPTION
                   "Vlan membership Status entry."
               INDEX    {     ifIndex, sm24dp4xaVLANMembershipVlanID    }
               ::= {     sm24dp4xaVLANMembershipStatusTable 1 }

    SM24DP4XAVLANMembershipStatusEntry             ::= SEQUENCE {
                sm24dp4xaVLANMembershipVlanID      Integer32,
                sm24dp4xaVLANMembershipStatus      INTEGER
                }

    sm24dp4xaVLANMembershipVlanID OBJECT-TYPE
               SYNTAX      Integer32(1..4095)
               MAX-ACCESS  not-accessible
               STATUS      current
               DESCRIPTION
                   "VLAN ID for which the Port members are displayed."
               ::= {     sm24dp4xaVLANMembershipStatusEntry 2 }

    sm24dp4xaVLANMembershipStatus OBJECT-TYPE
               SYNTAX      INTEGER  { portIsNotInVlan  ( 0 ),
                                      portIncludedInVlan ( 1 ),
                                      portInForbiddenPortList( 2 ),
                                      portInForbiddenPortListAndVlan( 3 )
                                    }
               MAX-ACCESS  read-only
               STATUS      current
               DESCRIPTION
                   "portIsNotInVlan(0): A port is nothing in a VLAN.
                    portIncludedInVlan(1): A port is included in a VLAN.
                    portInForbiddenPortList(2): A port is in the forbidden port list.
                    portInForbiddenPortListAndVlan(3):
                     A port is in the forbidden port list and at the same
                     time attempted included in the VLAN."
               ::= {     sm24dp4xaVLANMembershipStatusEntry 3 }

--sm24dp4xaVLANPortStatusTable
    sm24dp4xaVLANPortStatusTable OBJECT-TYPE
               SYNTAX      SEQUENCE OF     SM24DP4XAVLANPortStatusEntry
               MAX-ACCESS  not-accessible
               STATUS      current
               DESCRIPTION
                   "The vlan port status table.
                    INDEX for this table is ifIndex which is
                    equivalent to the panel port number."
               ::= {     sm24dp4xaVlanStatus 2 }

    sm24dp4xaVLANPortStatusEntry OBJECT-TYPE
               SYNTAX          SM24DP4XAVLANPortStatusEntry
               MAX-ACCESS  not-accessible
               STATUS      current
               DESCRIPTION
                   "The vlan port status entry."
               INDEX    {     ifIndex }
               ::= {     sm24dp4xaVLANPortStatusTable 1 }

    SM24DP4XAVLANPortStatusEntry             ::= SEQUENCE {
                sm24dp4xaVLANPortStatusPortType          DisplayString,
                sm24dp4xaVLANPortStatusIngressFiltering  AdminMode,
                sm24dp4xaVLANPortStatusFrameType         DisplayString,
                sm24dp4xaVLANPortStatusPortVLANID        Integer32,
                sm24dp4xaVLANPortStatusTxTag             DisplayString,
                sm24dp4xaVLANPortStatusUntaggedVLANID    Integer32,
                sm24dp4xaVLANPortStatusConflicts         DisplayString
                }

    sm24dp4xaVLANPortStatusPortType OBJECT-TYPE
               SYNTAX      DisplayString
               MAX-ACCESS  read-only
               STATUS      current
               DESCRIPTION
                   "Shows the port type (Unaware, C-Port, S-Port,
                    S-Custom-Port.) that a given user wants to configure on
                    the port.The field is empty if not overridden by the selected user."
               ::= {     sm24dp4xaVLANPortStatusEntry 2 }

    sm24dp4xaVLANPortStatusIngressFiltering OBJECT-TYPE
               SYNTAX      AdminMode
               MAX-ACCESS  read-only
               STATUS      current
               DESCRIPTION
                   "Shows whether a given user wants ingress filtering enabled or not."
               ::= {     sm24dp4xaVLANPortStatusEntry 3 }

    sm24dp4xaVLANPortStatusFrameType OBJECT-TYPE
               SYNTAX      DisplayString
               MAX-ACCESS  read-only
               STATUS      current
               DESCRIPTION
                   "Shows the acceptable frame types (All, Taged,
                    Untagged) that a given user wants to configure on the port.
                    The field is empty if not overridden by the selected user."
               ::= {     sm24dp4xaVLANPortStatusEntry 4 }

    sm24dp4xaVLANPortStatusPortVLANID OBJECT-TYPE
               SYNTAX      Integer32 (1..4095)
               MAX-ACCESS  read-only
               STATUS      current
               DESCRIPTION
                   "Shows the Port VLAN ID (PVID) that a given user
                    wants the port to have.
                    The field is 0 if not overridden by the selected user."
               ::= {     sm24dp4xaVLANPortStatusEntry 5 }

    sm24dp4xaVLANPortStatusTxTag OBJECT-TYPE
               SYNTAX      DisplayString
               MAX-ACCESS  read-only
               STATUS      current
               DESCRIPTION
                   "Shows the Tx Tag requirements (Tag All, Tag PVID,
                    Tag UVID, Untag All, Untag PVID, Untag UVID)
                    that a given user has on a port.The field is empty
                    if not overridden by the selected user."
               ::= {     sm24dp4xaVLANPortStatusEntry 6 }

    sm24dp4xaVLANPortStatusUntaggedVLANID OBJECT-TYPE
               SYNTAX      Integer32(1..4095)
               MAX-ACCESS  read-only
               STATUS      current
               DESCRIPTION
                   "If Tx Tag is overridden by the selected user and is
                    set to Tag or Untag UVID, then this field will show
                    the VLAN ID the user wants to tag or untag on egress.
                    The field is 0 if not overridden by the selected
                    user."
               ::= {     sm24dp4xaVLANPortStatusEntry 7 }

    sm24dp4xaVLANPortStatusConflicts OBJECT-TYPE
               SYNTAX      DisplayString
               MAX-ACCESS  read-only
               STATUS      current
               DESCRIPTION
                   "Two users may have conflicting requirements to a port's
                    configuration. For instance, one user may require
                    all frames to be tagged on egress while another requires
                    all frames to be untagged on egress.Since both
                    users cannot win, this gives rise to a conflict,
                    which is solved in a prioritized way. The Administrator
                    has the least priority. Other software modules are
                    prioritized according to their position in the drop-down
                    list: The higher in the list, the higher priority.
                    If conflicts exist, it will be displayed as 'Yes'."
               ::= {     sm24dp4xaVLANPortStatusEntry 8 }

sm24dp4xaNTPConf   OBJECT IDENTIFIER ::= { sm24dp4xaSystem 12 }

sm24dp4xaNTPConfigAutomatic   OBJECT-TYPE
               SYNTAX      Integer32 (0|1)
               MAX-ACCESS  read-write
               STATUS      current
               DESCRIPTION
                   "Indicates the Automatic mode operation. Possible modes are:
                   0:Disable, NTP servers available from the config. 
                   1:Enable, NTP servers available from the DHCP."
               ::= { sm24dp4xaNTPConf 2 }
               
sm24dp4xaNTPConfigTimeSyncInterval   OBJECT-TYPE
               SYNTAX      Integer32 (5|10|15|30|60|120)
               MAX-ACCESS  read-write
               STATUS      current
               DESCRIPTION
                   "Time-Sync Interval.
                   Valid values are restricted to 5,10,15,30,60,120 minutes. "
               ::= { sm24dp4xaNTPConf 3 }   

sm24dp4xaNTPConfigServerAddress1   OBJECT-TYPE
               SYNTAX      DisplayString
               MAX-ACCESS  read-write
               STATUS      current
               DESCRIPTION
                   "Provide the IPv4 or IPv6 address of a NTP server."
               ::= { sm24dp4xaNTPConf 4 }   

sm24dp4xaNTPConfigServerAddress2   OBJECT-TYPE
               SYNTAX      DisplayString
               MAX-ACCESS  read-write
               STATUS      current
               DESCRIPTION
                   "Provide the IPv4 or IPv6 address of a NTP server."
               ::= { sm24dp4xaNTPConf 5 }                
        
sm24dp4xaNTPConfigServerAddress3   OBJECT-TYPE
               SYNTAX      DisplayString
               MAX-ACCESS  read-write
               STATUS      current
               DESCRIPTION
                   "Provide the IPv4 or IPv6 address of a NTP server."
               ::= { sm24dp4xaNTPConf 6 }          
               
sm24dp4xaNTPConfigServerAddress4   OBJECT-TYPE
               SYNTAX      DisplayString
               MAX-ACCESS  read-write
               STATUS      current
               DESCRIPTION
                   "Provide the IPv4 or IPv6 address of a NTP server."
               ::= { sm24dp4xaNTPConf 7 }                    
    
sm24dp4xaNTPConfigServerAddress5   OBJECT-TYPE
               SYNTAX      DisplayString
               MAX-ACCESS  read-write
               STATUS      current
               DESCRIPTION
                   "Provide the IPv4 or IPv6 address of a NTP server."
               ::= { sm24dp4xaNTPConf 8 }  
               
               
sm24dp4xaTemperature   OBJECT IDENTIFIER ::= { sm24dp4xaSystem 13 }

sm24dp4xaTemperature1   OBJECT IDENTIFIER ::= { sm24dp4xaTemperature 1 }

sm24dp4xaTemperature1Celsius   OBJECT-TYPE
               SYNTAX      DisplayString
               MAX-ACCESS  read-only
               STATUS      current
               DESCRIPTION
                   "Value of Celsius"
               ::= { sm24dp4xaTemperature1 1 } 

sm24dp4xaTemperature1Fahrenheit   OBJECT-TYPE
               SYNTAX      DisplayString
               MAX-ACCESS  read-only
               STATUS      current
               DESCRIPTION
                   "Value of Fahrenheit"
               ::= { sm24dp4xaTemperature1 2 } 
               
sm24dp4xaTemperature2   OBJECT IDENTIFIER ::= { sm24dp4xaTemperature 2 }

sm24dp4xaTemperature2Celsius   OBJECT-TYPE
               SYNTAX      DisplayString
               MAX-ACCESS  read-only
               STATUS      current
               DESCRIPTION
                   "Value of Celsius"
               ::= { sm24dp4xaTemperature2 1 } 

sm24dp4xaTemperature2Fahrenheit   OBJECT-TYPE
               SYNTAX      DisplayString
               MAX-ACCESS  read-only
               STATUS      current
               DESCRIPTION
                   "Value of Fahrenheit"
               ::= { sm24dp4xaTemperature2 2 }                
               
-- =======================================================================================================================
sm24dp4xaConfiguration                                         OBJECT IDENTIFIER ::= { sm24dp4xaProductId 2 }

sm24dp4xaPort                                                  OBJECT IDENTIFIER ::= { sm24dp4xaConfiguration 1 }

sm24dp4xaPortConfigurationTable OBJECT-TYPE
   SYNTAX      SEQUENCE OF SM24DP4XAPortConfigurationEntry
   MAX-ACCESS  not-accessible
   STATUS      current
   DESCRIPTION
       " Show port configurations. "
   ::= { sm24dp4xaPort 1 }

sm24dp4xaPortConfigurationEntry OBJECT-TYPE
   SYNTAX      SM24DP4XAPortConfigurationEntry
   MAX-ACCESS  not-accessible
   STATUS      current
   DESCRIPTION
       " "
   INDEX    { sm24dp4xaPortConfPort  }
   ::= { sm24dp4xaPortConfigurationTable 1 }

SM24DP4XAPortConfigurationEntry ::= SEQUENCE {
   sm24dp4xaPortConfPort                     Integer32,
   sm24dp4xaPortConfPortMedia                DisplayString,
   sm24dp4xaPortConfLink                     DisplayString,
   sm24dp4xaPortConfCurrentSpeed             DisplayString,
   sm24dp4xaPortConfSpeed                    Integer32,
--   sm24dp4xaPortConfCurrentFlowControlRx     Integer32,
--   sm24dp4xaPortConfCurrentFlowControlTx     Integer32,
--   sm24dp4xaPortConfFlowControl              Integer32,
   sm24dp4xaPortConfMaxFrameSize             Integer32,
   sm24dp4xaPortConfExcessiveCollisionMode   Integer32,
-- sm24dp4xaPortConfPowerControl             Integer32,
   sm24dp4xaPortConfDescription              DisplayString,
   sm24dp4xaPortConfFrameLengthCheck         Integer32
}

sm24dp4xaPortConfPort OBJECT-TYPE
   SYNTAX      Integer32 (1..4095)
   MAX-ACCESS  not-accessible
   STATUS      current
   DESCRIPTION
       " port, range : 1 - port number. "
   ::= { sm24dp4xaPortConfigurationEntry 1 }

sm24dp4xaPortConfPortMedia OBJECT-TYPE
   SYNTAX      DisplayString(SIZE (1..4))
   MAX-ACCESS  read-only
   STATUS      current
   DESCRIPTION
       " Show port media. "
   ::= { sm24dp4xaPortConfigurationEntry 2 }

sm24dp4xaPortConfLink OBJECT-TYPE
   SYNTAX      DisplayString(SIZE (2..4))
   MAX-ACCESS  read-only
   STATUS      current
   DESCRIPTION
       " The current link state. "
   ::= { sm24dp4xaPortConfigurationEntry 3 }

sm24dp4xaPortConfCurrentSpeed OBJECT-TYPE
   SYNTAX      DisplayString(SIZE (6..12))
   MAX-ACCESS  read-only
   STATUS      current
   DESCRIPTION
       " The current link speed of the port. "
   ::= { sm24dp4xaPortConfigurationEntry 4 }

sm24dp4xaPortConfSpeed OBJECT-TYPE
   SYNTAX      Integer32 (0..11)
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X,
        12: 10G Full. "
   ::= { sm24dp4xaPortConfigurationEntry 5 }

--sm24dp4xaPortConfCurrentFlowControlRx OBJECT-TYPE
--   SYNTAX      Integer32 (0|1)
--   MAX-ACCESS  read-only
--   STATUS      current
--   DESCRIPTION
--       "0: disable
--        1: enable
--        2: not support.  "
--   ::= { sm24dp4xaPortConfigurationEntry 6 }
--
--sm24dp4xaPortConfCurrentFlowControlTx OBJECT-TYPE
--   SYNTAX      Integer32 (0|1)
--   MAX-ACCESS  read-only
--   STATUS      current
--   DESCRIPTION
--       "0: disable
--        1: enable
--        2: not support.  "
--   ::= { sm24dp4xaPortConfigurationEntry 7 }
--
--sm24dp4xaPortConfFlowControl OBJECT-TYPE
--   SYNTAX      Integer32 (0|1)
--   MAX-ACCESS  read-write
--   STATUS      current
--   DESCRIPTION
--       "default: 0,
--        0: disable
--        1: enable
--        2: not support. "
--   ::= { sm24dp4xaPortConfigurationEntry 8 }

sm24dp4xaPortConfMaxFrameSize OBJECT-TYPE
   SYNTAX      Integer32 (1518..10056)
   MAX-ACCESS  read-write
   STATUS      current
   DESCRIPTION
       "default: 10056 , range : 1518 - 10056 "
   ::= { sm24dp4xaPortConfigurationEntry 9 }

sm24dp4xaPortConfExcessiveCollisionMode OBJECT-TYPE
   SYNTAX      Integer32 (0|1)
   MAX-ACCESS  read-write
   STATUS      current
   DESCRIPTION
       "default: 0,
        Excessive Collision Mode :
        0: Discard,
        1: Restart,
        2: not support.
       "
   ::= { sm24dp4xaPortConfigurationEntry 10 }

--sm24dp4xaPortConfPowerControl OBJECT-TYPE
--   SYNTAX      Integer32 (0..3)
--   MAX-ACCESS  read-write
--   STATUS      current
--   DESCRIPTION
--       "default: 0,
--        PowerControl :
--        0: disable,
--        1: Actiphy,
--        2: Dynamic (perfectReach),
--        3: Enable,
--        4: not support.
--       "
--   ::= { sm24dp4xaPortConfigurationEntry 11 }

sm24dp4xaPortConfDescription OBJECT-TYPE
   SYNTAX      DisplayString
   MAX-ACCESS  read-write
   STATUS      current
   DESCRIPTION
       " Interface specific description.
         Up to 128 characters describing this interface. "
   ::= { sm24dp4xaPortConfigurationEntry 12 }

sm24dp4xaPortConfFrameLengthCheck OBJECT-TYPE
   SYNTAX      Integer32 (0|1)
   MAX-ACCESS  read-write
   STATUS      current
   DESCRIPTION
       "default: 0,
        0: disable
        1: enable"
   ::= { sm24dp4xaPortConfigurationEntry 13 } 

sm24dp4xaPortTrafficStatisticsTable OBJECT-TYPE
   SYNTAX      SEQUENCE OF SM24DP4XAPortTrafficStatisticsEntry
   MAX-ACCESS  not-accessible
   STATUS      current
   DESCRIPTION
       " "
   ::= { sm24dp4xaPort 2 }

sm24dp4xaPortTrafficStatisticsEntry OBJECT-TYPE
   SYNTAX      SM24DP4XAPortTrafficStatisticsEntry
   MAX-ACCESS  not-accessible
   STATUS      current
   DESCRIPTION
       " "
   INDEX    { sm24dp4xaPortTrafficStatisticsPort  }
   ::= { sm24dp4xaPortTrafficStatisticsTable 1 }

SM24DP4XAPortTrafficStatisticsEntry ::= SEQUENCE {
   sm24dp4xaPortTrafficStatisticsPort          Integer32,
   sm24dp4xaPortTrafficStatisticsClear         Integer32,
   sm24dp4xaPortTrafficRxPackets               Counter64,
   sm24dp4xaPortTrafficRxOctets                Counter64,
   sm24dp4xaPortTrafficRxUnicast               Counter64,
   sm24dp4xaPortTrafficRxMulticast             Counter64,
   sm24dp4xaPortTrafficRxBroadcast             Counter64,
   sm24dp4xaPortTrafficRxPause                 Counter64,
   sm24dp4xaPortTrafficRx64Bytes               Counter64,
   sm24dp4xaPortTrafficRx65to127Bytes          Counter64,
   sm24dp4xaPortTrafficRx128to255Bytes         Counter64,
   sm24dp4xaPortTrafficRx256to511Bytes         Counter64,
   sm24dp4xaPortTrafficRx512to1023Bytes        Counter64,
   sm24dp4xaPortTrafficRx1024to1526Bytes       Counter64,
   sm24dp4xaPortTrafficRxExceecd1527Bytes      Counter64,
   sm24dp4xaPortTrafficRxQ0                    Counter64,
   sm24dp4xaPortTrafficRxQ1                    Counter64,
   sm24dp4xaPortTrafficRxQ2                    Counter64,
   sm24dp4xaPortTrafficRxQ3                    Counter64,
   sm24dp4xaPortTrafficRxQ4                    Counter64,
   sm24dp4xaPortTrafficRxQ5                    Counter64,
   sm24dp4xaPortTrafficRxQ6                    Counter64,
   sm24dp4xaPortTrafficRxQ7                    Counter64,
   sm24dp4xaPortTrafficRxDrops                 Counter64,
   sm24dp4xaPortTrafficRxCRCorAlignment        Counter64,
   sm24dp4xaPortTrafficRxUndersize             Counter64,
   sm24dp4xaPortTrafficRxOversize              Counter64,
   sm24dp4xaPortTrafficRxFragments             Counter64,
   sm24dp4xaPortTrafficRxJabber                Counter64,
   sm24dp4xaPortTrafficRxFiltered              Counter64,
   sm24dp4xaPortTrafficTxPackets               Counter64,
   sm24dp4xaPortTrafficTxOctets                Counter64,
   sm24dp4xaPortTrafficTxUnicast               Counter64,
   sm24dp4xaPortTrafficTxMulticast             Counter64,
   sm24dp4xaPortTrafficTxBroadcast             Counter64,
   sm24dp4xaPortTrafficTxPause                 Counter64,
   sm24dp4xaPortTrafficTx64Bytes               Counter64,
   sm24dp4xaPortTrafficTx65to127Bytes          Counter64,
   sm24dp4xaPortTrafficTx128to255Bytes         Counter64,
   sm24dp4xaPortTrafficTx256to511Bytes         Counter64,
   sm24dp4xaPortTrafficTx512to1023Bytes        Counter64,
   sm24dp4xaPortTrafficTx1024to1526Bytes       Counter64,
   sm24dp4xaPortTrafficTxExceecd1527Bytes      Counter64,
   sm24dp4xaPortTrafficTxQ0                    Counter64,
   sm24dp4xaPortTrafficTxQ1                    Counter64,
   sm24dp4xaPortTrafficTxQ2                    Counter64,
   sm24dp4xaPortTrafficTxQ3                    Counter64,
   sm24dp4xaPortTrafficTxQ4                    Counter64,
   sm24dp4xaPortTrafficTxQ5                    Counter64,
   sm24dp4xaPortTrafficTxQ6                    Counter64,
   sm24dp4xaPortTrafficTxQ7                    Counter64,
   sm24dp4xaPortTrafficTxDrops                 Counter64,
   sm24dp4xaPortTrafficTxLateOrExcColl         Counter64
}

sm24dp4xaPortTrafficStatisticsPort OBJECT-TYPE
   SYNTAX      Integer32 (1..4095)
   MAX-ACCESS  not-accessible
   STATUS      current
   DESCRIPTION
       " "
   ::= { sm24dp4xaPortTrafficStatisticsEntry 1 }

sm24dp4xaPortTrafficStatisticsClear OBJECT-TYPE
   SYNTAX      Integer32(0|1)
   MAX-ACCESS  read-write
   STATUS      current
   DESCRIPTION
       " "
   ::= { sm24dp4xaPortTrafficStatisticsEntry 2 }

sm24dp4xaPortTrafficRxPackets OBJECT-TYPE
   SYNTAX      Counter64
   MAX-ACCESS  read-only
   STATUS      current
   DESCRIPTION
       " "
   ::= { sm24dp4xaPortTrafficStatisticsEntry 3 }

sm24dp4xaPortTrafficRxOctets OBJECT-TYPE
   SYNTAX      Counter64
   MAX-ACCESS  read-only
   STATUS      current
   DESCRIPTION
       " "
   ::= { sm24dp4xaPortTrafficStatisticsEntry 4 }

sm24dp4xaPortTrafficRxUnicast OBJECT-TYPE
   SYNTAX      Counter64
   MAX-ACCESS  read-only
   STATUS      current
   DESCRIPTION
       " "
   ::= { sm24dp4xaPortTrafficStatisticsEntry 5 }

sm24dp4xaPortTrafficRxMulticast OBJECT-TYPE
   SYNTAX      Counter64
   MAX-ACCESS  read-only
   STATUS      current
   DESCRIPTION
       " "
   ::= { sm24dp4xaPortTrafficStatisticsEntry 6 }

sm24dp4xaPortTrafficRxBroadcast OBJECT-TYPE
   SYNTAX      Counter64
   MAX-ACCESS  read-only
   STATUS      current
   DESCRIPTION
       " "
   ::= { sm24dp4xaPortTrafficStatisticsEntry 7 }

sm24dp4xaPortTrafficRxPause OBJECT-TYPE
   SYNTAX      Counter64
   MAX-ACCESS  read-only
   STATUS      current
   DESCRIPTION
       " "
   ::= { sm24dp4xaPortTrafficStatisticsEntry 8 }

sm24dp4xaPortTrafficRx64Bytes OBJECT-TYPE
   SYNTAX      Counter64
   MAX-ACCESS  read-only
   STATUS      current
   DESCRIPTION
       " "
   ::= { sm24dp4xaPortTrafficStatisticsEntry 9 }

sm24dp4xaPortTrafficRx65to127Bytes OBJECT-TYPE
   SYNTAX      Counter64
   MAX-ACCESS  read-only
   STATUS      current
   DESCRIPTION
       " "
   ::= { sm24dp4xaPortTrafficStatisticsEntry 10 }

sm24dp4xaPortTrafficRx128to255Bytes OBJECT-TYPE
   SYNTAX      Counter64
   MAX-ACCESS  read-only
   STATUS      current
   DESCRIPTION
       " "
   ::= { sm24dp4xaPortTrafficStatisticsEntry 11 }

sm24dp4xaPortTrafficRx256to511Bytes OBJECT-TYPE
   SYNTAX      Counter64
   MAX-ACCESS  read-only
   STATUS      current
   DESCRIPTION
       " "
   ::= { sm24dp4xaPortTrafficStatisticsEntry 12 }

sm24dp4xaPortTrafficRx512to1023Bytes OBJECT-TYPE
   SYNTAX      Counter64
   MAX-ACCESS  read-only
   STATUS      current
   DESCRIPTION
       " "
   ::= { sm24dp4xaPortTrafficStatisticsEntry 13 }

sm24dp4xaPortTrafficRx1024to1526Bytes OBJECT-TYPE
   SYNTAX      Counter64
   MAX-ACCESS  read-only
   STATUS      current
   DESCRIPTION
       " "
   ::= { sm24dp4xaPortTrafficStatisticsEntry 14 }

sm24dp4xaPortTrafficRxExceecd1527Bytes OBJECT-TYPE
   SYNTAX      Counter64
   MAX-ACCESS  read-only
   STATUS      current
   DESCRIPTION
       " "
   ::= { sm24dp4xaPortTrafficStatisticsEntry 15 }

sm24dp4xaPortTrafficRxQ0 OBJECT-TYPE
   SYNTAX      Counter64
   MAX-ACCESS  read-only
   STATUS      current
   DESCRIPTION
       " "
   ::= { sm24dp4xaPortTrafficStatisticsEntry 16 }

sm24dp4xaPortTrafficRxQ1 OBJECT-TYPE
   SYNTAX      Counter64
   MAX-ACCESS  read-only
   STATUS      current
   DESCRIPTION
       " "
   ::= { sm24dp4xaPortTrafficStatisticsEntry 17 }

sm24dp4xaPortTrafficRxQ2 OBJECT-TYPE
   SYNTAX      Counter64
   MAX-ACCESS  read-only
   STATUS      current
   DESCRIPTION
       " "
   ::= { sm24dp4xaPortTrafficStatisticsEntry 18 }

sm24dp4xaPortTrafficRxQ3 OBJECT-TYPE
   SYNTAX      Counter64
   MAX-ACCESS  read-only
   STATUS      current
   DESCRIPTION
       " "
   ::= { sm24dp4xaPortTrafficStatisticsEntry 19 }

sm24dp4xaPortTrafficRxQ4 OBJECT-TYPE
   SYNTAX      Counter64
   MAX-ACCESS  read-only
   STATUS      current
   DESCRIPTION
       " "
   ::= { sm24dp4xaPortTrafficStatisticsEntry 20 }

sm24dp4xaPortTrafficRxQ5 OBJECT-TYPE
   SYNTAX      Counter64
   MAX-ACCESS  read-only
   STATUS      current
   DESCRIPTION
       " "
   ::= { sm24dp4xaPortTrafficStatisticsEntry 21 }

sm24dp4xaPortTrafficRxQ6 OBJECT-TYPE
   SYNTAX      Counter64
   MAX-ACCESS  read-only
   STATUS      current
   DESCRIPTION
       " "
   ::= { sm24dp4xaPortTrafficStatisticsEntry 22 }

sm24dp4xaPortTrafficRxQ7 OBJECT-TYPE
   SYNTAX      Counter64
   MAX-ACCESS  read-only
   STATUS      current
   DESCRIPTION
       " "
   ::= { sm24dp4xaPortTrafficStatisticsEntry 23 }

sm24dp4xaPortTrafficRxDrops OBJECT-TYPE
   SYNTAX      Counter64
   MAX-ACCESS  read-only
   STATUS      current
   DESCRIPTION
       " "
   ::= { sm24dp4xaPortTrafficStatisticsEntry 24 }

sm24dp4xaPortTrafficRxCRCorAlignment OBJECT-TYPE
   SYNTAX      Counter64
   MAX-ACCESS  read-only
   STATUS      current
   DESCRIPTION
       " "
   ::= { sm24dp4xaPortTrafficStatisticsEntry 25 }

sm24dp4xaPortTrafficRxUndersize OBJECT-TYPE
   SYNTAX      Counter64
   MAX-ACCESS  read-only
   STATUS      current
   DESCRIPTION
       " "
   ::= { sm24dp4xaPortTrafficStatisticsEntry 26 }

sm24dp4xaPortTrafficRxOversize OBJECT-TYPE
   SYNTAX      Counter64
   MAX-ACCESS  read-only
   STATUS      current
   DESCRIPTION
       " "
   ::= { sm24dp4xaPortTrafficStatisticsEntry 27 }

sm24dp4xaPortTrafficRxFragments OBJECT-TYPE
   SYNTAX      Counter64
   MAX-ACCESS  read-only
   STATUS      current
   DESCRIPTION
       " "
   ::= { sm24dp4xaPortTrafficStatisticsEntry 28 }

sm24dp4xaPortTrafficRxJabber OBJECT-TYPE
   SYNTAX      Counter64
   MAX-ACCESS  read-only
   STATUS      current
   DESCRIPTION
       " "
   ::= { sm24dp4xaPortTrafficStatisticsEntry 29 }

sm24dp4xaPortTrafficRxFiltered OBJECT-TYPE
   SYNTAX      Counter64
   MAX-ACCESS  read-only
   STATUS      current
   DESCRIPTION
       " "
   ::= { sm24dp4xaPortTrafficStatisticsEntry 30 }

sm24dp4xaPortTrafficTxPackets OBJECT-TYPE
   SYNTAX      Counter64
   MAX-ACCESS  read-only
   STATUS      current
   DESCRIPTION
       " "
   ::= { sm24dp4xaPortTrafficStatisticsEntry 31 }

sm24dp4xaPortTrafficTxOctets OBJECT-TYPE
   SYNTAX      Counter64
   MAX-ACCESS  read-only
   STATUS      current
   DESCRIPTION
       " "
   ::= { sm24dp4xaPortTrafficStatisticsEntry 32 }

sm24dp4xaPortTrafficTxUnicast OBJECT-TYPE
   SYNTAX      Counter64
   MAX-ACCESS  read-only
   STATUS      current
   DESCRIPTION
       " "
   ::= { sm24dp4xaPortTrafficStatisticsEntry 33 }

sm24dp4xaPortTrafficTxMulticast OBJECT-TYPE
   SYNTAX      Counter64
   MAX-ACCESS  read-only
   STATUS      current
   DESCRIPTION
       " "
   ::= { sm24dp4xaPortTrafficStatisticsEntry 34 }

sm24dp4xaPortTrafficTxBroadcast OBJECT-TYPE
   SYNTAX      Counter64
   MAX-ACCESS  read-only
   STATUS      current
   DESCRIPTION
       " "
   ::= { sm24dp4xaPortTrafficStatisticsEntry 35 }

sm24dp4xaPortTrafficTxPause OBJECT-TYPE
   SYNTAX      Counter64
   MAX-ACCESS  read-only
   STATUS      current
   DESCRIPTION
       " "
   ::= { sm24dp4xaPortTrafficStatisticsEntry 36 }

sm24dp4xaPortTrafficTx64Bytes OBJECT-TYPE
   SYNTAX      Counter64
   MAX-ACCESS  read-only
   STATUS      current
   DESCRIPTION
       " "
   ::= { sm24dp4xaPortTrafficStatisticsEntry 37 }

sm24dp4xaPortTrafficTx65to127Bytes OBJECT-TYPE
   SYNTAX      Counter64
   MAX-ACCESS  read-only
   STATUS      current
   DESCRIPTION
       " "
   ::= { sm24dp4xaPortTrafficStatisticsEntry 38 }

sm24dp4xaPortTrafficTx128to255Bytes OBJECT-TYPE
   SYNTAX      Counter64
   MAX-ACCESS  read-only
   STATUS      current
   DESCRIPTION
       " "
   ::= { sm24dp4xaPortTrafficStatisticsEntry 39 }

sm24dp4xaPortTrafficTx256to511Bytes OBJECT-TYPE
   SYNTAX      Counter64
   MAX-ACCESS  read-only
   STATUS      current
   DESCRIPTION
       " "
   ::= { sm24dp4xaPortTrafficStatisticsEntry 40 }

sm24dp4xaPortTrafficTx512to1023Bytes OBJECT-TYPE
   SYNTAX      Counter64
   MAX-ACCESS  read-only
   STATUS      current
   DESCRIPTION
       " "
   ::= { sm24dp4xaPortTrafficStatisticsEntry 41 }

sm24dp4xaPortTrafficTx1024to1526Bytes OBJECT-TYPE
   SYNTAX      Counter64
   MAX-ACCESS  read-only
   STATUS      current
   DESCRIPTION
       " "
   ::= { sm24dp4xaPortTrafficStatisticsEntry 42 }

sm24dp4xaPortTrafficTxExceecd1527Bytes OBJECT-TYPE
   SYNTAX      Counter64
   MAX-ACCESS  read-only
   STATUS      current
   DESCRIPTION
       " "
   ::= { sm24dp4xaPortTrafficStatisticsEntry 43 }

sm24dp4xaPortTrafficTxQ0 OBJECT-TYPE
   SYNTAX      Counter64
   MAX-ACCESS  read-only
   STATUS      current
   DESCRIPTION
       " "
   ::= { sm24dp4xaPortTrafficStatisticsEntry 44 }

sm24dp4xaPortTrafficTxQ1 OBJECT-TYPE
   SYNTAX      Counter64
   MAX-ACCESS  read-only
   STATUS      current
   DESCRIPTION
       " "
   ::= { sm24dp4xaPortTrafficStatisticsEntry 45 }

sm24dp4xaPortTrafficTxQ2 OBJECT-TYPE
   SYNTAX      Counter64
   MAX-ACCESS  read-only
   STATUS      current
   DESCRIPTION
       " "
   ::= { sm24dp4xaPortTrafficStatisticsEntry 46 }

sm24dp4xaPortTrafficTxQ3 OBJECT-TYPE
   SYNTAX      Counter64
   MAX-ACCESS  read-only
   STATUS      current
   DESCRIPTION
       " "
   ::= { sm24dp4xaPortTrafficStatisticsEntry 47 }

sm24dp4xaPortTrafficTxQ4 OBJECT-TYPE
   SYNTAX      Counter64
   MAX-ACCESS  read-only
   STATUS      current
   DESCRIPTION
       " "
   ::= { sm24dp4xaPortTrafficStatisticsEntry 48 }

sm24dp4xaPortTrafficTxQ5 OBJECT-TYPE
   SYNTAX      Counter64
   MAX-ACCESS  read-only
   STATUS      current
   DESCRIPTION
       " "
   ::= { sm24dp4xaPortTrafficStatisticsEntry 49 }

sm24dp4xaPortTrafficTxQ6 OBJECT-TYPE
   SYNTAX      Counter64
   MAX-ACCESS  read-only
   STATUS      current
   DESCRIPTION
       " "
   ::= { sm24dp4xaPortTrafficStatisticsEntry 50 }


sm24dp4xaPortTrafficTxQ7 OBJECT-TYPE
   SYNTAX      Counter64
   MAX-ACCESS  read-only
   STATUS      current
   DESCRIPTION
       " "
   ::= { sm24dp4xaPortTrafficStatisticsEntry 51 }

sm24dp4xaPortTrafficTxDrops OBJECT-TYPE
   SYNTAX      Counter64
   MAX-ACCESS  read-only
   STATUS      current
   DESCRIPTION
       " "
   ::= { sm24dp4xaPortTrafficStatisticsEntry 52 }

sm24dp4xaPortTrafficTxLateOrExcColl OBJECT-TYPE
   SYNTAX      Counter64
   MAX-ACCESS  read-only
   STATUS      current
   DESCRIPTION
       " "
   ::= { sm24dp4xaPortTrafficStatisticsEntry 53 }


sm24dp4xaPortQoSStatistics                                     OBJECT IDENTIFIER ::= { sm24dp4xaPort 3 }

sm24dp4xaPortQoSStatisticsClear OBJECT-TYPE
   SYNTAX      Integer32(0|1)
   MAX-ACCESS  read-only
   STATUS      current
   DESCRIPTION
       "default: 0
       0: none
       1: clear "
   ::= { sm24dp4xaPortQoSStatistics 1 }

sm24dp4xaPortQoSStatisticsTable OBJECT-TYPE
   SYNTAX      SEQUENCE OF SM24DP4XAPortQoSStatisticsEntry
   MAX-ACCESS  not-accessible
   STATUS      current
   DESCRIPTION
       " "
   ::= { sm24dp4xaPortQoSStatistics 2 }

sm24dp4xaPortQoSStatisticsEntry OBJECT-TYPE
   SYNTAX      SM24DP4XAPortQoSStatisticsEntry
   MAX-ACCESS  not-accessible
   STATUS      current
   DESCRIPTION
       " "
   INDEX    { sm24dp4xaPortQoSStatisticsPort  }
   ::= { sm24dp4xaPortQoSStatisticsTable 1 }

SM24DP4XAPortQoSStatisticsEntry ::= SEQUENCE {
   sm24dp4xaPortQoSStatisticsPort      Integer32,
   sm24dp4xaPortQoSQ0Rx                Counter64,
   sm24dp4xaPortQoSQ0Tx                Counter64,
   sm24dp4xaPortQoSQ1Rx                Counter64,
   sm24dp4xaPortQoSQ1Tx                Counter64,
   sm24dp4xaPortQoSQ2Rx                Counter64,
   sm24dp4xaPortQoSQ2Tx                Counter64,
   sm24dp4xaPortQoSQ3Rx                Counter64,
   sm24dp4xaPortQoSQ3Tx                Counter64,
   sm24dp4xaPortQoSQ4Rx                Counter64,
   sm24dp4xaPortQoSQ4Tx                Counter64,
   sm24dp4xaPortQoSQ5Rx                Counter64,
   sm24dp4xaPortQoSQ5Tx                Counter64,
   sm24dp4xaPortQoSQ6Rx                Counter64,
   sm24dp4xaPortQoSQ6Tx                Counter64,
   sm24dp4xaPortQoSQ7Rx                Counter64,
   sm24dp4xaPortQoSQ7Tx                Counter64
}

sm24dp4xaPortQoSStatisticsPort OBJECT-TYPE
   SYNTAX      Integer32 (1..4095)
   MAX-ACCESS  not-accessible
   STATUS      current
   DESCRIPTION
       " "
   ::= { sm24dp4xaPortQoSStatisticsEntry 1 }

sm24dp4xaPortQoSQ0Rx OBJECT-TYPE
   SYNTAX      Counter64
   MAX-ACCESS  read-only
   STATUS      current
   DESCRIPTION
       " "
   ::= { sm24dp4xaPortQoSStatisticsEntry 2 }

sm24dp4xaPortQoSQ0Tx OBJECT-TYPE
   SYNTAX      Counter64
   MAX-ACCESS  read-only
   STATUS      current
   DESCRIPTION
       " "
   ::= { sm24dp4xaPortQoSStatisticsEntry 3 }

sm24dp4xaPortQoSQ1Rx OBJECT-TYPE
   SYNTAX      Counter64
   MAX-ACCESS  read-only
   STATUS      current
   DESCRIPTION
       " "
   ::= { sm24dp4xaPortQoSStatisticsEntry 4 }

sm24dp4xaPortQoSQ1Tx OBJECT-TYPE
   SYNTAX      Counter64
   MAX-ACCESS  read-only
   STATUS      current
   DESCRIPTION
       " "
   ::= { sm24dp4xaPortQoSStatisticsEntry 5 }

sm24dp4xaPortQoSQ2Rx OBJECT-TYPE
   SYNTAX      Counter64
   MAX-ACCESS  read-only
   STATUS      current
   DESCRIPTION
       " "
   ::= { sm24dp4xaPortQoSStatisticsEntry 6 }

sm24dp4xaPortQoSQ2Tx OBJECT-TYPE
   SYNTAX      Counter64
   MAX-ACCESS  read-only
   STATUS      current
   DESCRIPTION
       " "
   ::= { sm24dp4xaPortQoSStatisticsEntry 7 }

sm24dp4xaPortQoSQ3Rx OBJECT-TYPE
   SYNTAX      Counter64
   MAX-ACCESS  read-only
   STATUS      current
   DESCRIPTION
       " "
   ::= { sm24dp4xaPortQoSStatisticsEntry 8 }

sm24dp4xaPortQoSQ3Tx OBJECT-TYPE
   SYNTAX      Counter64
   MAX-ACCESS  read-only
   STATUS      current
   DESCRIPTION
       " "
   ::= { sm24dp4xaPortQoSStatisticsEntry 9 }

sm24dp4xaPortQoSQ4Rx OBJECT-TYPE
   SYNTAX      Counter64
   MAX-ACCESS  read-only
   STATUS      current
   DESCRIPTION
       " "
   ::= { sm24dp4xaPortQoSStatisticsEntry 10 }

sm24dp4xaPortQoSQ4Tx OBJECT-TYPE
   SYNTAX      Counter64
   MAX-ACCESS  read-only
   STATUS      current
   DESCRIPTION
       " "
   ::= { sm24dp4xaPortQoSStatisticsEntry 11 }

sm24dp4xaPortQoSQ5Rx OBJECT-TYPE
   SYNTAX      Counter64
   MAX-ACCESS  read-only
   STATUS      current
   DESCRIPTION
       " "
   ::= { sm24dp4xaPortQoSStatisticsEntry 12 }

sm24dp4xaPortQoSQ5Tx OBJECT-TYPE
   SYNTAX      Counter64
   MAX-ACCESS  read-only
   STATUS      current
   DESCRIPTION
       " "
   ::= { sm24dp4xaPortQoSStatisticsEntry 13 }

sm24dp4xaPortQoSQ6Rx OBJECT-TYPE
   SYNTAX      Counter64
   MAX-ACCESS  read-only
   STATUS      current
   DESCRIPTION
       " "
   ::= { sm24dp4xaPortQoSStatisticsEntry 14 }

sm24dp4xaPortQoSQ6Tx OBJECT-TYPE
   SYNTAX      Counter64
   MAX-ACCESS  read-only
   STATUS      current
   DESCRIPTION
       " "
   ::= { sm24dp4xaPortQoSStatisticsEntry 15 }

sm24dp4xaPortQoSQ7Rx OBJECT-TYPE
   SYNTAX      Counter64
   MAX-ACCESS  read-only
   STATUS      current
   DESCRIPTION
       " "
   ::= { sm24dp4xaPortQoSStatisticsEntry 16 }

sm24dp4xaPortQoSQ7Tx OBJECT-TYPE
   SYNTAX      Counter64
   MAX-ACCESS  read-only
   STATUS      current
   DESCRIPTION
       " "
   ::= { sm24dp4xaPortQoSStatisticsEntry 17 }

sm24dp4xaSFPInfoTable OBJECT-TYPE
   SYNTAX      SEQUENCE OF SM24DP4XASFPInfoEntry
   MAX-ACCESS  not-accessible
   STATUS      current
   DESCRIPTION
       " "
   ::= { sm24dp4xaPort 4 }

sm24dp4xaSFPInfoEntry OBJECT-TYPE
   SYNTAX      SM24DP4XASFPInfoEntry
   MAX-ACCESS  not-accessible
   STATUS      current
   DESCRIPTION
       " "
   INDEX    { sm24dp4xaSFPInfoIndex }
   ::= { sm24dp4xaSFPInfoTable 1 }

SM24DP4XASFPInfoEntry ::= SEQUENCE {
   sm24dp4xaSFPInfoIndex               Integer32,
   sm24dp4xaSFPInfoPort                DisplayString,
   sm24dp4xaSFPConnectorType           DisplayString,
   sm24dp4xaSFPFiberType               DisplayString,
   sm24dp4xaSFPTxCentralWavelength     DisplayString,
   sm24dp4xaSFPBaudRate                DisplayString,
   sm24dp4xaSFPVendorOUI               DisplayString,
   sm24dp4xaSFPVendorName              DisplayString,
   sm24dp4xaSFPVendorPN                DisplayString,
   sm24dp4xaSFPVendorRev               DisplayString,
   sm24dp4xaSFPVendorSN                DisplayString,
   sm24dp4xaSFPDateCode                DisplayString,
   sm24dp4xaSFPTemperature             DisplayString,
   sm24dp4xaSFPVcc                     DisplayString,
   sm24dp4xaSFPMon1Bias                DisplayString,
   sm24dp4xaSFPMon2TxPWR               DisplayString,
   sm24dp4xaSFPMon3RxPWR               DisplayString
}

sm24dp4xaSFPInfoIndex OBJECT-TYPE
   SYNTAX      Integer32 (1..4095)
   MAX-ACCESS  not-accessible
   STATUS      current
   DESCRIPTION
       " "
   ::= { sm24dp4xaSFPInfoEntry 1 }

sm24dp4xaSFPInfoPort OBJECT-TYPE
   SYNTAX      DisplayString
   MAX-ACCESS  read-only
   STATUS      current
   DESCRIPTION
       " "
   ::= { sm24dp4xaSFPInfoEntry 2 }

sm24dp4xaSFPConnectorType OBJECT-TYPE
   SYNTAX      DisplayString
   MAX-ACCESS  read-only
   STATUS      current
   DESCRIPTION
       " "
   ::= { sm24dp4xaSFPInfoEntry 3 }

sm24dp4xaSFPFiberType OBJECT-TYPE
   SYNTAX      DisplayString
   MAX-ACCESS  read-only
   STATUS      current
   DESCRIPTION
       " "
   ::= { sm24dp4xaSFPInfoEntry 4 }

sm24dp4xaSFPTxCentralWavelength OBJECT-TYPE
   SYNTAX      DisplayString
   MAX-ACCESS  read-only
   STATUS      current
   DESCRIPTION
       " "
   ::= { sm24dp4xaSFPInfoEntry 5 }

sm24dp4xaSFPBaudRate OBJECT-TYPE
   SYNTAX      DisplayString
   MAX-ACCESS  read-only
   STATUS      current
   DESCRIPTION
       " "
   ::= { sm24dp4xaSFPInfoEntry 6 }

sm24dp4xaSFPVendorOUI OBJECT-TYPE
   SYNTAX      DisplayString
   MAX-ACCESS  read-only
   STATUS      current
   DESCRIPTION
       " "
   ::= { sm24dp4xaSFPInfoEntry 7 }

sm24dp4xaSFPVendorName OBJECT-TYPE
   SYNTAX      DisplayString
   MAX-ACCESS  read-only
   STATUS      current
   DESCRIPTION
       " "
   ::= { sm24dp4xaSFPInfoEntry 8 }

sm24dp4xaSFPVendorPN OBJECT-TYPE
   SYNTAX      DisplayString
   MAX-ACCESS  read-only
   STATUS      current
   DESCRIPTION
       " "
   ::= { sm24dp4xaSFPInfoEntry 9 }

sm24dp4xaSFPVendorRev OBJECT-TYPE
   SYNTAX      DisplayString
   MAX-ACCESS  read-only
   STATUS      current
   DESCRIPTION
       " "
   ::= { sm24dp4xaSFPInfoEntry 10 }

sm24dp4xaSFPVendorSN OBJECT-TYPE
   SYNTAX      DisplayString
   MAX-ACCESS  read-only
   STATUS      current
   DESCRIPTION
       " "
   ::= { sm24dp4xaSFPInfoEntry 11 }

sm24dp4xaSFPDateCode OBJECT-TYPE
   SYNTAX      DisplayString
   MAX-ACCESS  read-only
   STATUS      current
   DESCRIPTION
       " "
   ::= { sm24dp4xaSFPInfoEntry 12 }

sm24dp4xaSFPTemperature OBJECT-TYPE
   SYNTAX      DisplayString
   MAX-ACCESS  read-only
   STATUS      current
   DESCRIPTION
       "Value of Celsius"
   ::= { sm24dp4xaSFPInfoEntry 13 }

sm24dp4xaSFPVcc OBJECT-TYPE
   SYNTAX      DisplayString
   MAX-ACCESS  read-only
   STATUS      current
   DESCRIPTION
       "Value of V"
   ::= { sm24dp4xaSFPInfoEntry 14 }

sm24dp4xaSFPMon1Bias OBJECT-TYPE
   SYNTAX      DisplayString
   MAX-ACCESS  read-only
   STATUS      current
   DESCRIPTION
       "Value of mA"
   ::= { sm24dp4xaSFPInfoEntry 15 }

sm24dp4xaSFPMon2TxPWR OBJECT-TYPE
   SYNTAX      DisplayString
   MAX-ACCESS  read-only
   STATUS      current
   DESCRIPTION
       "Value of dBm"
   ::= { sm24dp4xaSFPInfoEntry 16 }

sm24dp4xaSFPMon3RxPWR OBJECT-TYPE
   SYNTAX      DisplayString
   MAX-ACCESS  read-only
   STATUS      current
   DESCRIPTION
       "Value of dBm"
   ::= { sm24dp4xaSFPInfoEntry 17 }


sm24dp4xaVoiceVLAN                                             OBJECT IDENTIFIER ::= { sm24dp4xaConfiguration 2 }

sm24dp4xaVoiceVLANConf                                         OBJECT IDENTIFIER ::= { sm24dp4xaVoiceVLAN 1 }

sm24dp4xaVoiceVLANMode OBJECT-TYPE
   SYNTAX      Integer32 (0|1)
   MAX-ACCESS  read-write
   STATUS      current
   DESCRIPTION
       " Voice VLAN mode operation.
       default: 0,
       0: disable
       1: enable"
   ::= { sm24dp4xaVoiceVLANConf 1 }

sm24dp4xaVoiceVLANVLANId OBJECT-TYPE
   SYNTAX      Integer32 (1..4094)
   MAX-ACCESS  read-write
   STATUS      current
   DESCRIPTION
       "Voice VLAN ID.
        default: 1000,
        range : 1-4094. "
   ::= { sm24dp4xaVoiceVLANConf 2 }

sm24dp4xaVoiceVLANAgingTime OBJECT-TYPE
   SYNTAX      Integer32 (10..10000000)
   MAX-ACCESS  read-write
   STATUS      current
   DESCRIPTION
       " Voice VLAN secure learning aging time.
         default: 86400,
         range : 10 - 10000000. "
   ::= { sm24dp4xaVoiceVLANConf 3 }

sm24dp4xaVoiceVLANTrafficClass OBJECT-TYPE
   SYNTAX      Integer32 (0..7)
   MAX-ACCESS  read-write
   STATUS      current
   DESCRIPTION
       " Voice VLAN traffic class, all traffic on the Voice VLAN
         will apply this class, available value is from 0(Low)
         to 7(High).
         default: 7. "
   ::= { sm24dp4xaVoiceVLANConf 4 }


sm24dp4xaVoiceVLANPortTable OBJECT-TYPE
   SYNTAX      SEQUENCE OF SM24DP4XAVoiceVLANPortEntry
   MAX-ACCESS  not-accessible
   STATUS      current
   DESCRIPTION
       " Show Voice Vlan configuration. "
   ::= { sm24dp4xaVoiceVLANConf 5 }

sm24dp4xaVoiceVLANPortEntry OBJECT-TYPE
   SYNTAX      SM24DP4XAVoiceVLANPortEntry
   MAX-ACCESS  not-accessible
   STATUS      current
   DESCRIPTION
       " "
   INDEX    { sm24dp4xaVoiceVLANPort  }
   ::= { sm24dp4xaVoiceVLANPortTable 1 }

SM24DP4XAVoiceVLANPortEntry ::= SEQUENCE {
   sm24dp4xaVoiceVLANPort                    Integer32,
   sm24dp4xaVoiceVLANPortMode                Integer32,
   sm24dp4xaVoiceVLANPortSecurity            Integer32,
   sm24dp4xaVoiceVLANPortDiscoveryProtocol   Integer32
}

sm24dp4xaVoiceVLANPort OBJECT-TYPE
   SYNTAX      Integer32 (1..4095)
   MAX-ACCESS  not-accessible
   STATUS      current
   DESCRIPTION
       " port, range : 1 - port number. "
   ::= { sm24dp4xaVoiceVLANPortEntry 1 }

sm24dp4xaVoiceVLANPortMode OBJECT-TYPE
   SYNTAX      Integer32 (0..2)
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { sm24dp4xaVoiceVLANPortEntry 2 }

sm24dp4xaVoiceVLANPortSecurity OBJECT-TYPE
   SYNTAX      Integer32 (0|1)
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { sm24dp4xaVoiceVLANPortEntry 3 }

sm24dp4xaVoiceVLANPortDiscoveryProtocol OBJECT-TYPE
   SYNTAX      Integer32 (0..2)
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { sm24dp4xaVoiceVLANPortEntry 4 }


sm24dp4xaVoiceVLANOUI                                          OBJECT IDENTIFIER ::= { sm24dp4xaVoiceVLAN 2 }

sm24dp4xaVoiceVLANOUICreate OBJECT-TYPE
   SYNTAX       Integer32(0|1)
   MAX-ACCESS   read-write
   STATUS       current
   DESCRIPTION
       "default: 0
        0 : None  (read only)
        1 : Create an OUI entry"
   ::= { sm24dp4xaVoiceVLANOUI 1 }

sm24dp4xaVoiceVLANOUITable OBJECT-TYPE
   SYNTAX      SEQUENCE OF SM24DP4XAVoiceVLANOUIEntry
   MAX-ACCESS  not-accessible
   STATUS      current
   DESCRIPTION
       " Create Voice VLAN OUI entry. Modify OUI table will
         restart auto detect OUI process. "
   ::= { sm24dp4xaVoiceVLANOUI 2 }

sm24dp4xaVoiceVLANOUIEntry OBJECT-TYPE
   SYNTAX      SM24DP4XAVoiceVLANOUIEntry
   MAX-ACCESS  not-accessible
   STATUS      current
   DESCRIPTION
       " "
   INDEX    { sm24dp4xaVoiceVLANOUIIndex  }
   ::= { sm24dp4xaVoiceVLANOUITable 1 }

SM24DP4XAVoiceVLANOUIEntry ::= SEQUENCE {
   sm24dp4xaVoiceVLANOUIIndex         Integer32,
   sm24dp4xaVoiceVLANTelephonyOUI     DisplayString,
   sm24dp4xaVoiceVLANDescription      DisplayString,
   sm24dp4xaVoiceVLANOUIRowStatus     Integer32
}

sm24dp4xaVoiceVLANOUIIndex OBJECT-TYPE
   SYNTAX      Integer32 (1..16)
   MAX-ACCESS  not-accessible
   STATUS      current
   DESCRIPTION
       " "
   ::= { sm24dp4xaVoiceVLANOUIEntry 1 }

sm24dp4xaVoiceVLANTelephonyOUI OBJECT-TYPE
   SYNTAX      DisplayString (SIZE (1..32))
   MAX-ACCESS  read-write
   STATUS      current
   DESCRIPTION
       "OUI address, format : 0a 1b 2c "
   ::= { sm24dp4xaVoiceVLANOUIEntry 2 }

sm24dp4xaVoiceVLANDescription OBJECT-TYPE
   SYNTAX      DisplayString (SIZE (1..32))
   MAX-ACCESS  read-write
   STATUS      current
   DESCRIPTION
       " Up to 32 characters describing OUI address. "
   ::= { sm24dp4xaVoiceVLANOUIEntry 3 }

sm24dp4xaVoiceVLANOUIRowStatus OBJECT-TYPE
   SYNTAX      Integer32 (1..5)
   MAX-ACCESS  read-write
   STATUS      current
   DESCRIPTION
       "1: active
        2: notInservice
        4: destroy
        5: undo"
   ::= { sm24dp4xaVoiceVLANOUIEntry 4 }

--sm24dp4xaGARP                                                   OBJECT IDENTIFIER ::= { sm24dp4xaConfiguration 3 }

--sm24dp4xaGARPConfTable OBJECT-TYPE
--   SYNTAX      SEQUENCE OF SM24DP4XAGARPConfEntry
--   MAX-ACCESS  not-accessible
--   STATUS      current
--   DESCRIPTION
--       " "
--   ::= { sm24dp4xaGARP 1 }

--sm24dp4xaGARPConfEntry OBJECT-TYPE
--   SYNTAX      SM24DP4XAGARPConfEntry
--   MAX-ACCESS  not-accessible
--   STATUS      current
--   DESCRIPTION
--       " "
--   INDEX    { sm24dp4xaGARPConfPort  }
--   ::= { sm24dp4xaGARPConfTable 1 }

--SM24DP4XAGARPConfEntry ::= SEQUENCE {
--   sm24dp4xaGARPConfPort           Integer32,
--   sm24dp4xaGARPJoinTimer          Integer32,
--   sm24dp4xaGARPLeaveTimer         Integer32,
--   sm24dp4xaGARPLeaveAllTimer      Integer32,
--   sm24dp4xaGARPApplicantion       Integer32,
--   sm24dp4xaGARPAttributeType      Integer32,
--   sm24dp4xaGARPApplicant          Integer32
--}

--sm24dp4xaGARPConfPort OBJECT-TYPE
--   SYNTAX      Integer32 (1..4095)
--   MAX-ACCESS  not-accessible
--   STATUS      current
--   DESCRIPTION
--       " "
--   ::= { sm24dp4xaGARPConfEntry 1 }

--sm24dp4xaGARPJoinTimer OBJECT-TYPE
--   SYNTAX      Integer32 (200..1000)
--   MAX-ACCESS  read-write
--   STATUS      current
--   DESCRIPTION
--       "default: 200, range : 200 - 1000 "
--   ::= { sm24dp4xaGARPConfEntry 2 }

--sm24dp4xaGARPLeaveTimer OBJECT-TYPE
--   SYNTAX      Integer32 (600..3000)
--   MAX-ACCESS  read-write
--   STATUS      current
--   DESCRIPTION
--       "default: 600 , range : 600 - 3000"
--   ::= { sm24dp4xaGARPConfEntry 3 }

--sm24dp4xaGARPLeaveAllTimer OBJECT-TYPE
--   SYNTAX      Integer32 (10000..50000)
--   MAX-ACCESS  read-write
--   STATUS      current
--   DESCRIPTION
--       "default: 10000, range : 10000 - 50000 "
--   ::= { sm24dp4xaGARPConfEntry 4 }

--sm24dp4xaGARPApplicantion OBJECT-TYPE
--   SYNTAX      Integer32(1)
--   MAX-ACCESS  read-write
--   STATUS      current
--   DESCRIPTION
--       "default: 1
--       1: GVRP"
--   ::= { sm24dp4xaGARPConfEntry 5 }

--sm24dp4xaGARPAttributeType OBJECT-TYPE
--   SYNTAX      Integer32(1)
--   MAX-ACCESS  read-write
--   STATUS      current
--   DESCRIPTION
--       "default: 1
--       1: VLAN"
--   ::= { sm24dp4xaGARPConfEntry 6 }

--sm24dp4xaGARPApplicant OBJECT-TYPE
--   SYNTAX      Integer32(0|1)
--   MAX-ACCESS  read-write
--   STATUS      current
--   DESCRIPTION
--       "default: 0
--       0: normal-participant
--       1: non-participant"
--   ::= { sm24dp4xaGARPConfEntry 7 }

--sm24dp4xaGARPStatisticsTable OBJECT-TYPE
--   SYNTAX      SEQUENCE OF SM24DP4XAGARPStatisticsEntry
--   MAX-ACCESS  not-accessible
--   STATUS      current
--   DESCRIPTION
--       " Show the basic GARP port statistics. "
--   ::= { sm24dp4xaGARP 2 }

--sm24dp4xaGARPStatisticsEntry OBJECT-TYPE
--   SYNTAX      SM24DP4XAGARPStatisticsEntry
--   MAX-ACCESS  not-accessible
--   STATUS      current
--   DESCRIPTION
--       " "
--   INDEX    { sm24dp4xaGARPStatisticsPort  }
--   ::= { sm24dp4xaGARPStatisticsTable 1 }

--SM24DP4XAGARPStatisticsEntry ::= SEQUENCE {
--   sm24dp4xaGARPStatisticsPort             Integer32,
--   sm24dp4xaGARPStatisticsPeerMAC          DisplayString,
--   sm24dp4xaGARPStatisticsFailedCount      Counter32
--}

--sm24dp4xaGARPStatisticsPort OBJECT-TYPE
--   SYNTAX      Integer32 (1..4095)
--   MAX-ACCESS  not-accessible
--   STATUS      current
--   DESCRIPTION
--       " port, range : 1 - port number. "
--   ::= { sm24dp4xaGARPStatisticsEntry 1 }

--sm24dp4xaGARPStatisticsPeerMAC OBJECT-TYPE
--   SYNTAX      DisplayString
--   MAX-ACCESS  read-only
--   STATUS      current
--   DESCRIPTION
--       " Peer MAC is MAC address of the neighbour Switch from with GARP frame is received.  "
--   ::= { sm24dp4xaGARPStatisticsEntry 2 }

--sm24dp4xaGARPStatisticsFailedCount OBJECT-TYPE
--   SYNTAX      Counter32
--   MAX-ACCESS  read-only
--   STATUS      current
--   DESCRIPTION
--       " explain Failed count here. "
--   ::= { sm24dp4xaGARPStatisticsEntry 3 }

sm24dp4xaGVRP                                                   OBJECT IDENTIFIER ::= { sm24dp4xaConfiguration 4 }

sm24dp4xaGVRPConf                                                   OBJECT IDENTIFIER ::= { sm24dp4xaGVRP 1 }

sm24dp4xaGVRPMode OBJECT-TYPE
   SYNTAX      Integer32(0|1)
   MAX-ACCESS  read-write
   STATUS      current
   DESCRIPTION
       "default: 0,
        0: disable,
        1: enable. "
   ::= { sm24dp4xaGVRPConf 1 }

sm24dp4xaGVRPMaxVlan OBJECT-TYPE
   SYNTAX      Integer32(1..4095)
   MAX-ACCESS  read-write
   STATUS      current
   DESCRIPTION
       "Number of simultaniously VLANs that GVRP can control. "
   ::= { sm24dp4xaGVRPConf 2 }

sm24dp4xaGVRPJoinTime OBJECT-TYPE
   SYNTAX      Integer32(1..20)
   MAX-ACCESS  read-write
   STATUS      current
   DESCRIPTION
       "join-time in units of centi seconds. Range is 1-20. Default is 20. "
   ::= { sm24dp4xaGVRPConf 3 }

sm24dp4xaGVRPLeaveTime OBJECT-TYPE
   SYNTAX      Integer32(60..300)
   MAX-ACCESS  read-write
   STATUS      current
   DESCRIPTION
       "leave-time in units of centi seconds. Range is 60-300. Default is 60. "
   ::= { sm24dp4xaGVRPConf 4 }

sm24dp4xaGVRPLeaveAllTime OBJECT-TYPE
   SYNTAX      Integer32(1000..5000)
   MAX-ACCESS  read-write
   STATUS      current
   DESCRIPTION
       "leave-all-time in units of centi seconds Range is 1000-5000. Default is 1000"
   ::= { sm24dp4xaGVRPConf 5 }

sm24dp4xaGVRPConfTable OBJECT-TYPE
   SYNTAX      SEQUENCE OF SM24DP4XAGVRPConfEntry
   MAX-ACCESS  not-accessible
   STATUS      current
   DESCRIPTION
       " "
   ::= { sm24dp4xaGVRPConf 6 }

sm24dp4xaGVRPConfEntry OBJECT-TYPE
   SYNTAX      SM24DP4XAGVRPConfEntry
   MAX-ACCESS  not-accessible
   STATUS      current
   DESCRIPTION
       " "
   INDEX    { sm24dp4xaGVRPConfPort  }
   ::= { sm24dp4xaGVRPConfTable 1 }

SM24DP4XAGVRPConfEntry ::= SEQUENCE {
   sm24dp4xaGVRPConfPort           Integer32,
   sm24dp4xaGVRPConfPortMode       Integer32
-- sm24dp4xaGVRPConfPortRRole      Integer32
}

sm24dp4xaGVRPConfPort OBJECT-TYPE
   SYNTAX      Integer32 (1..4095)
   MAX-ACCESS  not-accessible
   STATUS      current
   DESCRIPTION
       " "
   ::= { sm24dp4xaGVRPConfEntry 1 }

sm24dp4xaGVRPConfPortMode OBJECT-TYPE
   SYNTAX      Integer32(0|1)
   MAX-ACCESS  read-write
   STATUS      current
   DESCRIPTION
       "default: 0
       1: enable
       0: disable"
   ::= { sm24dp4xaGVRPConfEntry 2 }

--sm24dp4xaGVRPConfPortRRole OBJECT-TYPE
--   SYNTAX      Integer32(0|1)
--   MAX-ACCESS  read-write
--   STATUS      current
--   DESCRIPTION
--       "default: 0
--       1: enable
--       0: disable"
--   ::= { sm24dp4xaGVRPConfEntry 3 }

--sm24dp4xaGVRPStatisticsTable OBJECT-TYPE
--   SYNTAX      SEQUENCE OF SM24DP4XAGVRPStatisticsEntry
--   MAX-ACCESS  not-accessible
--   STATUS      current
--   DESCRIPTION
--       " "
--   ::= { sm24dp4xaGVRP 2 }

--sm24dp4xaGVRPStatisticsEntry OBJECT-TYPE
--   SYNTAX      SM24DP4XAGVRPStatisticsEntry
--   MAX-ACCESS  not-accessible
--   STATUS      current
--   DESCRIPTION
--       " "
--   INDEX    { sm24dp4xaGVRPStatisticsPort  }
--   ::= { sm24dp4xaGVRPStatisticsTable 1 }

--SM24DP4XAGVRPStatisticsEntry ::= SEQUENCE {
--   sm24dp4xaGVRPStatisticsPort         Integer32,
--   sm24dp4xaGVRPStatisticsJoinTxCnt    Counter32,
--   sm24dp4xaGVRPStatisticsLeaveTxCnt   Counter32
--}

--sm24dp4xaGVRPStatisticsPort OBJECT-TYPE
--   SYNTAX      Integer32 (1..4095)
--   MAX-ACCESS  not-accessible
--   STATUS      current
--   DESCRIPTION
--       " "
--   ::= { sm24dp4xaGVRPStatisticsEntry 1 }

--sm24dp4xaGVRPStatisticsJoinTxCnt OBJECT-TYPE
--   SYNTAX      Counter32
--   MAX-ACCESS  read-only
--   STATUS      current
--   DESCRIPTION
--       " "
--   ::= { sm24dp4xaGVRPStatisticsEntry 2 }

--sm24dp4xaGVRPStatisticsLeaveTxCnt OBJECT-TYPE
--   SYNTAX      Counter32
--   MAX-ACCESS  read-only
--   STATUS      current
--   DESCRIPTION
--       " "
--   ::= { sm24dp4xaGVRPStatisticsEntry 3 }


sm24dp4xaMirroring                                             OBJECT IDENTIFIER ::= { sm24dp4xaConfiguration 6 }

--sm24dp4xaPortToMirrorOn OBJECT-TYPE
--   SYNTAX      Integer32(0..10)
--   MAX-ACCESS  read-write
--   STATUS      current
--   DESCRIPTION
--       "default: 0
--        0: disable,
--        range : 1 - port number. "
--   ::= { sm24dp4xaMirroring 2 }
--
--sm24dp4xaMirrorTable OBJECT-TYPE
--   SYNTAX      SEQUENCE OF SM24DP4XAMirrorEntry
--   MAX-ACCESS  not-accessible
--   STATUS      current
--   DESCRIPTION
--       " "
--   ::= { sm24dp4xaMirroring 3 }
--
--sm24dp4xaMirrorEntry OBJECT-TYPE
--   SYNTAX      SM24DP4XAMirrorEntry
--   MAX-ACCESS  not-accessible
--   STATUS      current
--   DESCRIPTION
--       " "
--   INDEX    { sm24dp4xaMirrorPort  }
--   ::= { sm24dp4xaMirrorTable 1 }
--
--SM24DP4XAMirrorEntry ::= SEQUENCE {
--   sm24dp4xaMirrorPort		Integer32,
--   sm24dp4xaMirrorMode		Integer32
--}
--
--sm24dp4xaMirrorPort OBJECT-TYPE
--   SYNTAX      Integer32 (1..4095)
--   MAX-ACCESS  not-accessible
--   STATUS      current
--   DESCRIPTION
--       " "
--   ::= { sm24dp4xaMirrorEntry 1 }
--
--sm24dp4xaMirrorMode OBJECT-TYPE
--   SYNTAX      Integer32(0..3)
--   MAX-ACCESS  read-write
--   STATUS      current
--   DESCRIPTION
--       "default: 0
--       0: disable
--       1: enable
--       2: rx only
--       3: tx only
--       Setting Tx mirroring for analyzer port has no effect. Tx mirroring ignored"
--   ::= { sm24dp4xaMirrorEntry 2 }

sm24dp4xaRMirrorMode OBJECT-TYPE
   SYNTAX      Integer32(0|1)
   MAX-ACCESS  read-write
   STATUS      current
   DESCRIPTION
       "default: 0
        0: disable,
        1: enable"
   ::= { sm24dp4xaMirroring 4 }

sm24dp4xaRMirrorType OBJECT-TYPE
   SYNTAX      Integer32(0..3)
   MAX-ACCESS  read-write
   STATUS      current
   DESCRIPTION
       "0: Mirror
        1: Source(RMirror)
        2: Intermediate(RMirror)
        3: Destination(RMirror)"
   ::= { sm24dp4xaMirroring 5 }

sm24dp4xaRMirrorVLANID OBJECT-TYPE
   SYNTAX      Integer32(1..4095)
   MAX-ACCESS  read-write
   STATUS      current
   DESCRIPTION
       "VLAN ID"
   ::= { sm24dp4xaMirroring 6 }

sm24dp4xaRMirrorReflectorPort OBJECT-TYPE
   SYNTAX      Integer32(1..4095)
   MAX-ACCESS  read-write
   STATUS      current
   DESCRIPTION
       "Reflector Port range: 1 - port number."
   ::= { sm24dp4xaMirroring 7 }
   
sm24dp4xaRMirrorSourceVLANs OBJECT-TYPE
   SYNTAX      DisplayString
   MAX-ACCESS  read-write
   STATUS      current
   DESCRIPTION
       "VLAN-based Mirroring."
   ::= { sm24dp4xaMirroring 8 }   
   
sm24dp4xaRMirrorCPUSource OBJECT-TYPE
   SYNTAX      Integer32(0..3)
   MAX-ACCESS  read-write
   STATUS      current
   DESCRIPTION
       "0: Disable
        1: RX Only
        2: TX Only
        3: Both"
   ::= { sm24dp4xaMirroring 9 }
   
sm24dp4xaRMirrorTable OBJECT-TYPE
   SYNTAX      SEQUENCE OF SM24DP4XARMirrorEntry
   MAX-ACCESS  not-accessible
   STATUS      current
   DESCRIPTION
       " "
   ::= { sm24dp4xaMirroring 12 }

sm24dp4xaRMirrorEntry OBJECT-TYPE
   SYNTAX      SM24DP4XARMirrorEntry
   MAX-ACCESS  not-accessible
   STATUS      current
   DESCRIPTION
       " "
   INDEX    { sm24dp4xaRMirrorPort  }
   ::= { sm24dp4xaRMirrorTable 1 }

SM24DP4XARMirrorEntry ::= SEQUENCE {
   sm24dp4xaRMirrorPort             Integer32,
   sm24dp4xaRMirrorPortSource       Integer32,
   sm24dp4xaRMirrorPortIntermediate Integer32,
   sm24dp4xaRMirrorPortDestination  Integer32
}

sm24dp4xaRMirrorPort OBJECT-TYPE
   SYNTAX      Integer32(1..65535)
   MAX-ACCESS  not-accessible
   STATUS      current
   DESCRIPTION
       " "
   ::= { sm24dp4xaRMirrorEntry 1 }

sm24dp4xaRMirrorPortSource OBJECT-TYPE
   SYNTAX      Integer32(0..3)
   MAX-ACCESS  read-write
   STATUS      current
   DESCRIPTION
       "0: Disable
        1: RX Only
        2: TX Only
        3: Both"
   ::= { sm24dp4xaRMirrorEntry 2 }

sm24dp4xaRMirrorPortIntermediate OBJECT-TYPE
   SYNTAX      Integer32(0|1)
   MAX-ACCESS  read-write
   STATUS      current
   DESCRIPTION
       "0: disable,
        1: enable"
   ::= { sm24dp4xaRMirrorEntry 3 }

sm24dp4xaRMirrorPortDestination OBJECT-TYPE
   SYNTAX      Integer32(0|1)
   MAX-ACCESS  read-write
   STATUS      current
   DESCRIPTION
       "0: disable,
        1: enable"
   ::= { sm24dp4xaRMirrorEntry 4 }


sm24dp4xaTrapEventSeverity                                             OBJECT IDENTIFIER ::= { sm24dp4xaConfiguration 7 }

sm24dp4xaTrapEventSeverityTable OBJECT-TYPE
   SYNTAX      SEQUENCE OF SM24DP4XATrapEventSeverityEntry
   MAX-ACCESS  not-accessible
   STATUS      current
   DESCRIPTION
       " "
   ::= { sm24dp4xaTrapEventSeverity 1 }

sm24dp4xaTrapEventSeverityEntry OBJECT-TYPE
   SYNTAX      SM24DP4XATrapEventSeverityEntry
   MAX-ACCESS  not-accessible
   STATUS      current
   DESCRIPTION
       " "
   INDEX    { sm24dp4xaTrapEventSeverityIndex }
   ::= { sm24dp4xaTrapEventSeverityTable 1 }

SM24DP4XATrapEventSeverityEntry ::= SEQUENCE {
   sm24dp4xaTrapEventSeverityIndex        Integer32,
   sm24dp4xaTrapEventSeverityGroupName    DisplayString,
   sm24dp4xaTrapEventSeverityLevel        Integer32,
   sm24dp4xaTrapEventSeveritySyslog       Integer32,
   sm24dp4xaTrapEventSeverityTrap         Integer32,
   sm24dp4xaTrapEventSeveritySMTP         Integer32,
   sm24dp4xaTrapEventSeveritySwitch2go    Integer32,
   sm24dp4xaTrapEventSeverityDigitalOut   Integer32
}

sm24dp4xaTrapEventSeverityIndex OBJECT-TYPE
   SYNTAX      Integer32(1..65535)
   MAX-ACCESS  not-accessible
   STATUS      current
   DESCRIPTION
       " "
   ::= { sm24dp4xaTrapEventSeverityEntry 1 }

sm24dp4xaTrapEventSeverityGroupName OBJECT-TYPE
   SYNTAX      DisplayString
   MAX-ACCESS  read-only
   STATUS      current
   DESCRIPTION
       "Group Name"
   ::= { sm24dp4xaTrapEventSeverityEntry 2 }

sm24dp4xaTrapEventSeverityLevel OBJECT-TYPE
   SYNTAX      Integer32
   MAX-ACCESS  not-accessible
   STATUS      current
   DESCRIPTION
       "0:Emergency
       1:Alert
       2:Critical
       3:Error
       4:Warning
       5:Notice
       6:Information
       7:Debug"
   ::= { sm24dp4xaTrapEventSeverityEntry 3 }

sm24dp4xaTrapEventSeveritySyslog OBJECT-TYPE
   SYNTAX      Integer32
   MAX-ACCESS  not-accessible
   STATUS      current
   DESCRIPTION
       "0:disable
       1:enable"
   ::= { sm24dp4xaTrapEventSeverityEntry 4 }

sm24dp4xaTrapEventSeverityTrap OBJECT-TYPE
   SYNTAX      Integer32
   MAX-ACCESS  not-accessible
   STATUS      current
   DESCRIPTION
       "0:disable
       1:enable"
   ::= { sm24dp4xaTrapEventSeverityEntry 5 }

sm24dp4xaTrapEventSeveritySMTP OBJECT-TYPE
   SYNTAX      Integer32
   MAX-ACCESS  not-accessible
   STATUS      current
   DESCRIPTION
       "0:disable
       1:enable"
   ::= { sm24dp4xaTrapEventSeverityEntry 6 }

sm24dp4xaTrapEventSeveritySwitch2go OBJECT-TYPE
   SYNTAX      Integer32
   MAX-ACCESS  not-accessible
   STATUS      current
   DESCRIPTION
       "0:disable
       1:enable"
   ::= { sm24dp4xaTrapEventSeverityEntry 7 }
   
sm24dp4xaTrapEventSeverityDigitalOut OBJECT-TYPE
   SYNTAX      Integer32
   MAX-ACCESS  not-accessible
   STATUS      current
   DESCRIPTION
       "0:disable
       1:enable
	   -1:not support"
   ::= { sm24dp4xaTrapEventSeverityEntry 8 }   


sm24dp4xaPortEventSettingTable OBJECT-TYPE
   SYNTAX      SEQUENCE OF SM24DP4XAPortEventSettingEntry
   MAX-ACCESS  not-accessible
   STATUS      current
   DESCRIPTION
       " "
   ::= { sm24dp4xaTrapEventSeverity 2 }

sm24dp4xaPortEventSettingEntry OBJECT-TYPE
   SYNTAX      SM24DP4XAPortEventSettingEntry
   MAX-ACCESS  not-accessible
   STATUS      current
   DESCRIPTION
       " "
   INDEX    { sm24dp4xaPortEventSettingIndex }
   ::= { sm24dp4xaPortEventSettingTable 1 }

SM24DP4XAPortEventSettingEntry ::= SEQUENCE {
   sm24dp4xaPortEventSettingIndex           Integer32,
   sm24dp4xaPortEventSettingActive          Integer32,
   sm24dp4xaPortEventSettingLinkOn          Integer32,
   sm24dp4xaPortEventSettingLinkOff         Integer32,
   sm24dp4xaPortEventSettingOverload        Integer32,
   sm24dp4xaPortEventSettingThreshold       Integer32,
   sm24dp4xaPortEventSettingTrafficDuration Integer32,
   sm24dp4xaPortEventSettingSyslog          Integer32,
   sm24dp4xaPortEventSettingTrap            Integer32,
   sm24dp4xaPortEventSettingSmtp            Integer32,
   sm24dp4xaPortEventSettingSwitch2go       Integer32,
   sm24dp4xaPortEventSettingDigitialout     Integer32,
   sm24dp4xaPortEventSettingSeverity        Integer32
}

sm24dp4xaPortEventSettingIndex OBJECT-TYPE
   SYNTAX      Integer32(1..65535)
   MAX-ACCESS  not-accessible
   STATUS      current
   DESCRIPTION
       " "
   ::= { sm24dp4xaPortEventSettingEntry 1 }

sm24dp4xaPortEventSettingActive OBJECT-TYPE
   SYNTAX      Integer32
   MAX-ACCESS  not-accessible
   STATUS      current
   DESCRIPTION
       "0:disable
       1:enable"
   ::= { sm24dp4xaPortEventSettingEntry 2}   
   
sm24dp4xaPortEventSettingLinkOn OBJECT-TYPE
   SYNTAX      Integer32
   MAX-ACCESS  not-accessible
   STATUS      current
   DESCRIPTION
       "0:disable
       1:enable"
   ::= { sm24dp4xaPortEventSettingEntry 3}      
   
sm24dp4xaPortEventSettingLinkOff OBJECT-TYPE
   SYNTAX      Integer32
   MAX-ACCESS  not-accessible
   STATUS      current
   DESCRIPTION
       "0:disable
       1:enable"
   ::= { sm24dp4xaPortEventSettingEntry 4}     
   
sm24dp4xaPortEventSettingOverload OBJECT-TYPE
   SYNTAX      Integer32
   MAX-ACCESS  not-accessible
   STATUS      current
   DESCRIPTION
       "0:disable
       1:enable"
   ::= { sm24dp4xaPortEventSettingEntry 5}    
 
sm24dp4xaPortEventSettingThreshold OBJECT-TYPE
   SYNTAX      Integer32
   MAX-ACCESS  not-accessible
   STATUS      current
   DESCRIPTION
       "Range:0-100"
   ::= { sm24dp4xaPortEventSettingEntry 6} 
 
sm24dp4xaPortEventSettingTrafficDuration OBJECT-TYPE
   SYNTAX      Integer32
   MAX-ACCESS  not-accessible
   STATUS      current
   DESCRIPTION
       "Range:1-300"
   ::= { sm24dp4xaPortEventSettingEntry 7} 
 
sm24dp4xaPortEventSettingSyslog OBJECT-TYPE
   SYNTAX      Integer32
   MAX-ACCESS  not-accessible
   STATUS      current
   DESCRIPTION
       "0:disable
       1:enable"
   ::= { sm24dp4xaPortEventSettingEntry 8}  

sm24dp4xaPortEventSettingTrap OBJECT-TYPE
   SYNTAX      Integer32
   MAX-ACCESS  not-accessible
   STATUS      current
   DESCRIPTION
       "0:disable
       1:enable"
   ::= { sm24dp4xaPortEventSettingEntry 9}  

sm24dp4xaPortEventSettingSmtp OBJECT-TYPE
   SYNTAX      Integer32
   MAX-ACCESS  not-accessible
   STATUS      current
   DESCRIPTION
       "0:disable
       1:enable"
   ::= { sm24dp4xaPortEventSettingEntry 10} 
   
sm24dp4xaPortEventSettingSwitch2go OBJECT-TYPE
   SYNTAX      Integer32
   MAX-ACCESS  not-accessible
   STATUS      current
   DESCRIPTION
       "0:disable
       1:enable"
   ::= { sm24dp4xaPortEventSettingEntry 11}    
 
sm24dp4xaPortEventSettingDigitialout OBJECT-TYPE
   SYNTAX      Integer32
   MAX-ACCESS  not-accessible
   STATUS      current
   DESCRIPTION
       "0:disable
       1:enable"
   ::= { sm24dp4xaPortEventSettingEntry 12}   
   
sm24dp4xaPortEventSettingSeverity OBJECT-TYPE
   SYNTAX      Integer32
   MAX-ACCESS  not-accessible
   STATUS      current
   DESCRIPTION
       "0:Emergency
       1:Alert
       2:Critical
       3:Error
       4:Warning
       5:Notice
       6:Information
       7:Debug"
   ::= { sm24dp4xaPortEventSettingEntry 13 }

-- =======================================================================================================================
sm24dp4xaSMTP                                             OBJECT IDENTIFIER ::= { sm24dp4xaConfiguration 8 }

sm24dp4xaSMTPMailServer OBJECT-TYPE
   SYNTAX      DisplayString
   MAX-ACCESS  read-write
   STATUS      current
   DESCRIPTION
       " Up to 47 characters describing email server. "
   ::= { sm24dp4xaSMTP 1 }

sm24dp4xaSMTPUserName OBJECT-TYPE
   SYNTAX      DisplayString
   MAX-ACCESS  read-write
   STATUS      current
   DESCRIPTION
       " Up to 47 characters describing user name. "
   ::= { sm24dp4xaSMTP 2 }

sm24dp4xaSMTPPassword OBJECT-TYPE
   SYNTAX      DisplayString
   MAX-ACCESS  read-write
   STATUS      current
   DESCRIPTION
       " Up to 47 characters describing password. "
   ::= { sm24dp4xaSMTP 3 }

sm24dp4xaSMTPSender OBJECT-TYPE
   SYNTAX      DisplayString
   MAX-ACCESS  read-write
   STATUS      current
   DESCRIPTION
       " Up to 47 characters describing sender. "
   ::= { sm24dp4xaSMTP 5 }

sm24dp4xaSMTPReturnPath OBJECT-TYPE
   SYNTAX      DisplayString
   MAX-ACCESS  read-write
   STATUS      current
   DESCRIPTION
       " Up to 47 characters describing return path. "
   ::= { sm24dp4xaSMTP 6 }

sm24dp4xaSMTPEmailAddress1 OBJECT-TYPE
   SYNTAX      DisplayString
   MAX-ACCESS  read-write
   STATUS      current
   DESCRIPTION
       " Up to 47 characters describing mail address. "
   ::= { sm24dp4xaSMTP 7 }

sm24dp4xaSMTPEmailAddress2 OBJECT-TYPE
   SYNTAX      DisplayString
   MAX-ACCESS  read-write
   STATUS      current
   DESCRIPTION
       " Up to 47 characters describing mail address. "
   ::= { sm24dp4xaSMTP 8 }

sm24dp4xaSMTPEmailAddress3 OBJECT-TYPE
   SYNTAX      DisplayString
   MAX-ACCESS  read-write
   STATUS      current
   DESCRIPTION
       " Up to 47 characters describing mail address. "
   ::= { sm24dp4xaSMTP 9 }

sm24dp4xaSMTPEmailAddress4 OBJECT-TYPE
   SYNTAX      DisplayString
   MAX-ACCESS  read-write
   STATUS      current
   DESCRIPTION
       " Up to 47 characters describing mail address. "
   ::= { sm24dp4xaSMTP 10 }

sm24dp4xaSMTPEmailAddress5 OBJECT-TYPE
   SYNTAX      DisplayString
   MAX-ACCESS  read-write
   STATUS      current
   DESCRIPTION
       " Up to 47 characters describing mail address. "
   ::= { sm24dp4xaSMTP 11 }

sm24dp4xaSMTPEmailAddress6 OBJECT-TYPE
   SYNTAX      DisplayString
   MAX-ACCESS  read-write
   STATUS      current
   DESCRIPTION
       " Up to 47 characters describing mail address. "
   ::= { sm24dp4xaSMTP 12 }

-- =======================================================================================================================
sm24dp4xaACLConf                                              OBJECT IDENTIFIER ::= { sm24dp4xaConfiguration 9 }

-- RowStatus Info:  createAndGo, notReady not supported.
-- =======================================================================================================================
-- Textual Conventions for the sm24dp4xa Acl Mib
-- =======================================================================================================================
--
    sm24dp4xaACL                     OBJECT IDENTIFIER  ::= { sm24dp4xaACLConf 1 }
    sm24dp4xaACLACE                  OBJECT IDENTIFIER  ::= { sm24dp4xaACLConf 3 }

--
-- =======================================================================================================================
-- Start sm24dp4xaACLPortConf group
-- =======================================================================================================================
--sm24dp4xaACLPortConfTable

    sm24dp4xaACLPortConfTable OBJECT-TYPE
               SYNTAX      SEQUENCE OF     SM24DP4XAACLPortConfEntry
               MAX-ACCESS  not-accessible
               STATUS      current
               DESCRIPTION
                   "The ACL Port Conf Table.
                    INDEX for this table is ifIndex which is
                    equivalent to the panel port number."
               ::= {     sm24dp4xaACL 1 }

    sm24dp4xaACLPortConfEntry OBJECT-TYPE
               SYNTAX          SM24DP4XAACLPortConfEntry
               MAX-ACCESS  not-accessible
               STATUS      current
               DESCRIPTION
                   "The ACL Port Conf Entry. "
               INDEX    {     ifIndex  }
               ::= {     sm24dp4xaACLPortConfTable 1 }

    SM24DP4XAACLPortConfEntry             ::=
            SEQUENCE {
                 sm24dp4xaACLPortConfPolicyID        Integer32,
                 sm24dp4xaACLPortConfAction          INTEGER,
                 sm24dp4xaACLPortConfRateLimiterID   Integer32,
                 sm24dp4xaACLPortConfPortRedirect    Integer32,
                 sm24dp4xaACLPortConfMirror          AdminMode,
                 sm24dp4xaACLPortConfLogging         AdminMode,
                 sm24dp4xaACLPortConfShutdown        AdminMode,
                 sm24dp4xaACLPortConfState           AdminMode,
                 sm24dp4xaACLPortConfCounter         Counter32
                 }

    sm24dp4xaACLPortConfPolicyID OBJECT-TYPE
               SYNTAX       Integer32 (0..63)
               MAX-ACCESS   read-write
               STATUS       current
               DESCRIPTION
                   "The policy to apply to this port.
                    default: 0, range : 0 - 63. "
               ::= {     sm24dp4xaACLPortConfEntry 2 }

    sm24dp4xaACLPortConfAction OBJECT-TYPE
               SYNTAX      INTEGER { deny(0), permit(1) }
               MAX-ACCESS  read-write
               STATUS      current
               DESCRIPTION
                   "Whether forwarding is permitted ('Permit') or denied ('Deny').
                    default: 1,
                    0: Deny,
                    1: Permit."
               ::= {     sm24dp4xaACLPortConfEntry 3 }

    sm24dp4xaACLPortConfRateLimiterID OBJECT-TYPE
               SYNTAX      Integer32 (0..16)
               MAX-ACCESS  read-write
               STATUS      current
               DESCRIPTION
                   "The rate limiter to apply on this port.
                    0: Disable,
                    range : 0 - 16. "
               ::= {     sm24dp4xaACLPortConfEntry 4 }

    sm24dp4xaACLPortConfPortRedirect OBJECT-TYPE
               SYNTAX      Integer32 (0..4095)
               MAX-ACCESS  read-write
               STATUS      current
               DESCRIPTION
                   "Port frames are redirected on.
                    0: Disable,
                    range : 0 - end port number. "
               ::= {     sm24dp4xaACLPortConfEntry 5 }

    sm24dp4xaACLPortConfMirror OBJECT-TYPE
               SYNTAX      AdminMode
               MAX-ACCESS  read-write
               STATUS      current
               DESCRIPTION
                   "The mirror operation of this port."
               ::= {     sm24dp4xaACLPortConfEntry 6 }

    sm24dp4xaACLPortConfLogging OBJECT-TYPE
               SYNTAX      AdminMode
               MAX-ACCESS  read-write
               STATUS      current
               DESCRIPTION
                   "Specify the logging operation of this port."
               ::= {     sm24dp4xaACLPortConfEntry 7 }

    sm24dp4xaACLPortConfShutdown OBJECT-TYPE
               SYNTAX      AdminMode
               MAX-ACCESS  read-write
               STATUS      current
               DESCRIPTION
                   "Specify the port shut down operation of this port."
               DEFVAL  { disable }
               ::= {     sm24dp4xaACLPortConfEntry 8 }

    sm24dp4xaACLPortConfState OBJECT-TYPE
               SYNTAX      AdminMode
               MAX-ACCESS  read-write
               STATUS      current
               DESCRIPTION
                   "Specify the port state of this port."
               DEFVAL  { enable }
               ::= {     sm24dp4xaACLPortConfEntry 9 }

    sm24dp4xaACLPortConfCounter OBJECT-TYPE
               SYNTAX      Counter32
               MAX-ACCESS  read-only
               STATUS      current
               DESCRIPTION
                   "Counts the number of frames that match this ACE. "
               ::= {     sm24dp4xaACLPortConfEntry 10 }

--
-- =======================================================================================================================
-- Start sm24dp4xaACLRateLimiter group
-- =======================================================================================================================
--sm24dp4xaACLRateLimiterTable

    sm24dp4xaACLRateLimiterTable OBJECT-TYPE
               SYNTAX      SEQUENCE OF     SM24DP4XAACLRateLimiterEntry
               MAX-ACCESS  not-accessible
               STATUS      current
               DESCRIPTION
                   "The ACL Rate Limiter Table."
               ::= {     sm24dp4xaACL 2 }

    sm24dp4xaACLRateLimiterEntry OBJECT-TYPE
               SYNTAX          SM24DP4XAACLRateLimiterEntry
               MAX-ACCESS  not-accessible
               STATUS      current
               DESCRIPTION
                   "The ACL Rate Limiter Entry. "
               INDEX    {     sm24dp4xaACLRateLimiterID  }
               ::= {     sm24dp4xaACLRateLimiterTable 1 }

    SM24DP4XAACLRateLimiterEntry             ::= SEQUENCE {
                 sm24dp4xaACLRateLimiterID       Integer32,
                 sm24dp4xaACLRateLimiterRate     Integer32,
                 sm24dp4xaACLRateLimiterUnit     INTEGER
                 }

    sm24dp4xaACLRateLimiterID OBJECT-TYPE
               SYNTAX      Integer32 (1..16)
               MAX-ACCESS  not-accessible
               STATUS      current
               DESCRIPTION
                   "Rate Limiter ID.
                    range : 1-16 "
               ::= {     sm24dp4xaACLRateLimiterEntry 1 }

    sm24dp4xaACLRateLimiterRate OBJECT-TYPE
               SYNTAX      Integer32(0..3276700)
               MAX-ACCESS  read-write
               STATUS      current
               DESCRIPTION
                   "default: 1,
                    range :
                    <0-3276700> pps,The valid rate is 0 - 99, 100, 200, 300,
                    ..., 3276700 in pps.
                    <0-10000> kbps,The valid rate is 0, 100, 200, 300,...,
                    1000000 in kbps."
               ::= {     sm24dp4xaACLRateLimiterEntry 2 }

    sm24dp4xaACLRateLimiterUnit OBJECT-TYPE
               SYNTAX      INTEGER { pps(0), kbps(1) }
               MAX-ACCESS  read-write
               STATUS      current
               DESCRIPTION
                   "Specify the rate unit.
                    sm24dp4xa(e){0: pps, 1: kbps.}
                    sm24dp4xa{0: pps}"
               ::= {     sm24dp4xaACLRateLimiterEntry 3 }

--
-- =======================================================================================================================
-- Start sm24dp4xaACLACE group
-- =======================================================================================================================
--sm24dp4xaACLACEClear

    sm24dp4xaACLACEClear OBJECT-TYPE
               SYNTAX      ActivateCmd
               MAX-ACCESS  read-write
               STATUS      current
               DESCRIPTION
                   "Clear all ACE counters."
               ::= {     sm24dp4xaACLACE 1 }

--sm24dp4xaACLACETable

    sm24dp4xaACLACETable OBJECT-TYPE
               SYNTAX      SEQUENCE OF     SM24DP4XAACLACEEntry
               MAX-ACCESS  not-accessible
               STATUS      current
               DESCRIPTION
                   "Create ACL ACE entry. "
               ::= {     sm24dp4xaACLACE 2 }

    sm24dp4xaACLACEEntry OBJECT-TYPE
               SYNTAX          SM24DP4XAACLACEEntry
               MAX-ACCESS  not-accessible
               STATUS      current
               DESCRIPTION
                   "The ACLACE Table."
               INDEX    {     sm24dp4xaACLACEIndex  }
               ::= {     sm24dp4xaACLACETable 1 }

    SM24DP4XAACLACEEntry             ::= SEQUENCE {
                 sm24dp4xaACLACEIndex                Integer32,
                 sm24dp4xaACLACEID                   Integer32,
                 sm24dp4xaACLACENextID               Integer32,
--               sm24dp4xaACLACELoopUp               AdminMode,
                 sm24dp4xaACLACEIngressPort          DisplayString,
                 sm24dp4xaACLACEPortPolicyNumber     Integer32,
                 sm24dp4xaACLACEPortPolicyBitmask    Integer32,
                 sm24dp4xaACLACEFrameType            INTEGER,
                 sm24dp4xaACLACEAction               INTEGER,
                 sm24dp4xaACLACEFilterPort           Integer32,
                 sm24dp4xaACLACEDenyPortRedirect     DisplayString,
                 sm24dp4xaACLACERateLimiter          Integer32,
                 sm24dp4xaACLACEMirror               AdminMode,
                 sm24dp4xaACLACELogging              AdminMode,
                 sm24dp4xaACLACEShutdown             AdminMode,
                 sm24dp4xaACLACECounter              Counter32,
                 sm24dp4xaACLACEVLAN8021QTagged      INTEGER,
                 sm24dp4xaACLACEVLANVID              Integer32,
                 sm24dp4xaACLACEVLANTagPriority      DisplayString,
                 sm24dp4xaACLACESMAC                 DisplayString,
                 sm24dp4xaACLACEDMACType             INTEGER,
                 sm24dp4xaACLACEDMAC                 DisplayString,
                 sm24dp4xaACLACEEtherType            Integer32,
                 sm24dp4xaACLACEArpOpCode            INTEGER,
                 sm24dp4xaACLACEArpFlagsRequestReply INTEGER,
                 sm24dp4xaACLACEArpFlagsArpSMac      INTEGER,
                 sm24dp4xaACLACEArpFlagsRarpDmac     INTEGER,
                 sm24dp4xaACLACEArpFlagsLength       INTEGER,
                 sm24dp4xaACLACEArpFlagsIp           INTEGER,
                 sm24dp4xaACLACEArpFlagsEthernet     INTEGER,
                 sm24dp4xaACLACESIPType              INTEGER,
                 sm24dp4xaACLACESIPIPAddress         IpAddress,
                 sm24dp4xaACLACESIPIPMask            IpAddress,
                 sm24dp4xaACLACEDIPType              INTEGER,
                 sm24dp4xaACLACEDIPIPAddress         IpAddress,
                 sm24dp4xaACLACEDIPIPMask            IpAddress,
                 sm24dp4xaACLACEIPProtocol           INTEGER,
                 sm24dp4xaACLACEIPProtocolValue      Integer32,
                 sm24dp4xaACLACEIPFlagsTTL           INTEGER,
                 sm24dp4xaACLACEIPFlagsFragment      INTEGER,
                 sm24dp4xaACLACEIPFlagsOptions       INTEGER,
                 sm24dp4xaACLACEICMPType             Integer32,
                 sm24dp4xaACLACEICMPCode             Integer32,
                 sm24dp4xaACLACESourcePort           DisplayString,
                 sm24dp4xaACLACEDestPort             DisplayString,
                 sm24dp4xaACLACETCPFlagsFin          INTEGER,
                 sm24dp4xaACLACETCPFlagsSyn          INTEGER,
                 sm24dp4xaACLACETCPFlagsRst          INTEGER,
                 sm24dp4xaACLACETCPFlagsPsh          INTEGER,
                 sm24dp4xaACLACETCPFlagsAck          INTEGER,
                 sm24dp4xaACLACETCPFlagsUrg          INTEGER,
                 sm24dp4xaACLACEIPv6SIPAddress       DisplayString,
                 sm24dp4xaACLACEIPv6SIPBitmask       DisplayString,
                 sm24dp4xaACLACEIPv6HopLimit         INTEGER,
                 sm24dp4xaACLACERowStatus            RowStatus
                 }

    sm24dp4xaACLACEIndex OBJECT-TYPE
               SYNTAX      Integer32(1..256)
               MAX-ACCESS  not-accessible
               STATUS      current
               DESCRIPTION
                   "The index. "
               ::= {     sm24dp4xaACLACEEntry 1 }

    sm24dp4xaACLACEID OBJECT-TYPE
               SYNTAX      Integer32(1..256)
               MAX-ACCESS  read-create
               STATUS      current
               DESCRIPTION
                   "If the ACE ID is specified and an entry with this ACE ID
                    already exists, the ACE will be modified. Otherwise, a
                    new ACE will be added.
                    range : 1 - 256. "
               ::= {     sm24dp4xaACLACEEntry 2 }

    sm24dp4xaACLACENextID OBJECT-TYPE
               SYNTAX      Integer32 (0..256)
               MAX-ACCESS  read-create
               STATUS      current
               DESCRIPTION
                   "If the next ACE ID is non zero, the ACE will be placed
                    before this ACE in the list. If the next ACE ID is zero,
                    the ACE will be placed last in the list.
                    range : 0 - 256. "
               ::= {     sm24dp4xaACLACEEntry 3 }

--    sm24dp4xaACLACELoopUp OBJECT-TYPE
--               SYNTAX      AdminMode
--               MAX-ACCESS  read-create
--               STATUS      current
--               DESCRIPTION
--                   "Specify the second lookup operation of the ACE."
--               ::= {     sm24dp4xaACLACEEntry 4 }

    sm24dp4xaACLACEIngressPort OBJECT-TYPE
               SYNTAX      DisplayString
               MAX-ACCESS  read-create
               STATUS      current
               DESCRIPTION
                   "Indicates the ingress port of the ACE. Possible values are:
                    0: All,The ACE will match all ingress port.
                    Port n: The ACE will match a specific ingress port."
               ::= {     sm24dp4xaACLACEEntry 5 }

    sm24dp4xaACLACEPortPolicyNumber OBJECT-TYPE
               SYNTAX      Integer32(0..64)
               MAX-ACCESS  read-create
               STATUS      current
               DESCRIPTION
                   "policy value.
                    range : 0 - 64.
                    64: Any. "
               ::= {     sm24dp4xaACLACEEntry 6 }

    sm24dp4xaACLACEPortPolicyBitmask OBJECT-TYPE
               SYNTAX      Integer32(0..256)
               MAX-ACCESS  read-create
               STATUS      current
               DESCRIPTION
                   "When 'Specific' is selected for the policy filter,
                    you can enter a specific policy bitmask.
                    sm24dp4xa{range : 0 - 63(0x3f), 64: no data.}
                    sm24dp4xa{range : 0 - 255(0xff), 256: no data.}"
               ::= {     sm24dp4xaACLACEEntry 7 }

    sm24dp4xaACLACEFrameType OBJECT-TYPE
               SYNTAX      INTEGER {   any(0), etype(1), arp(2),
                                       ipv4(3), ipv6(4) }
               MAX-ACCESS  read-create
               STATUS      current
               DESCRIPTION
                   "Select the frame type for this ACE.
                    When change the type Related oid will set default.
                    0: any,
                    1: etype,
                    2: arp,
                    3: ipv4,
                    4: ipv6."
               ::= {     sm24dp4xaACLACEEntry 8 }

    sm24dp4xaACLACEAction OBJECT-TYPE
               SYNTAX      INTEGER { deny(0), permit(1), filter(2) }
               MAX-ACCESS  read-create
               STATUS      current
               DESCRIPTION
                   "sm24dp4xa{0: Deny,1: Permit,2: Filter, range: 0-2.}
                    sm24dp4xa{0: Deny,1: Permit }"
               ::= {     sm24dp4xaACLACEEntry 9 }

    sm24dp4xaACLACEFilterPort OBJECT-TYPE
               SYNTAX      Integer32(-1..255)
               MAX-ACCESS  read-create
               STATUS      current
               DESCRIPTION
                   "When 'Action' is 'Filter' can set.
                    0: All,
                    Port n: The ACE applies to this port number, where n is
                    the number of the switch port.
                    -1: no data.
                    range: -1 - Port number."
               ::= {     sm24dp4xaACLACEEntry 10 }

    sm24dp4xaACLACEDenyPortRedirect OBJECT-TYPE
               SYNTAX      DisplayString
               MAX-ACCESS  read-create
               STATUS      current
               DESCRIPTION
                   "Frames that hit the ACE are redirected to the port
                    number specified here.Disabled,indicates that the port
                    redirect operation is disabled.
                    When 'Action' is 'Deny' can set.
                    0: disabled,
                    Port no: The ACE applies to this port number, where n is
                    the number of the switch port."
               ::= {     sm24dp4xaACLACEEntry 11 }

    sm24dp4xaACLACERateLimiter OBJECT-TYPE
               SYNTAX      Integer32(0..16)
               MAX-ACCESS  read-create
               STATUS      current
               DESCRIPTION
                   "default: 0,
                    0: Disable
                    range : 0 - 16 "
               ::= {     sm24dp4xaACLACEEntry 12 }

    sm24dp4xaACLACEMirror OBJECT-TYPE
               SYNTAX      AdminMode
               MAX-ACCESS  read-create
               STATUS      current
               DESCRIPTION
                   "default: 0,
                    0: disable - Frames matching the ACE are not mirrored.
                    1: enable - Frames matching the ACE are mirrored."
               ::= {     sm24dp4xaACLACEEntry 13 }

    sm24dp4xaACLACELogging OBJECT-TYPE
               SYNTAX      AdminMode
               MAX-ACCESS  read-create
               STATUS      current
               DESCRIPTION
                   "default: 0,
                    0: disable - Frames matching the ACE are not logged.
                    1: enable - Frames matching the ACE are stored in the
                   system log."
               ::= {     sm24dp4xaACLACEEntry 14 }

    sm24dp4xaACLACEShutdown OBJECT-TYPE
               SYNTAX      AdminMode
               MAX-ACCESS  read-create
               STATUS      current
               DESCRIPTION
                   "default: 0,
                    0: disable - Port shut down is disabled for the AC.
                    1: enable - If a frame matches the ACE, the ingress port
                    will be disabled."
               ::= {     sm24dp4xaACLACEEntry 15 }

    sm24dp4xaACLACECounter OBJECT-TYPE
               SYNTAX      Counter32
               MAX-ACCESS  read-only
               STATUS      current
               DESCRIPTION
                   "The counter indicates the number of times the ACE was
                    hit by a frame. "
               ::= {     sm24dp4xaACLACEEntry 16 }

    sm24dp4xaACLACEVLAN8021QTagged OBJECT-TYPE
               SYNTAX      INTEGER { disable(0), enable(1), any(2) }
               MAX-ACCESS  read-create
               STATUS      current
               DESCRIPTION
                   "Specify whether frames can hit the action according to
                    the 802.1Q tagged.
                    default: 2,
                    0: disable - Untagged frame only.
                    1: enable - Tagged frame only.
                    2: Any - Any value is allowed."
               ::= {     sm24dp4xaACLACEEntry 17 }

    sm24dp4xaACLACEVLANVID OBJECT-TYPE
               SYNTAX      Integer32(0..4095)
               MAX-ACCESS  read-create
               STATUS      current
               DESCRIPTION
                   "Specify the VLAN ID filter for this ACE.
                    The vid can't be set when 802.1Q Tagged is disabled.
                    default: 0,
                    0: Any - No VLAN ID filter is specified.
                    range : 0 - 4095 "
               ::= {     sm24dp4xaACLACEEntry 18 }

    sm24dp4xaACLACEVLANTagPriority OBJECT-TYPE
               SYNTAX      DisplayString
               MAX-ACCESS  read-create
               STATUS      current
               DESCRIPTION
                   "Specify the tag priority for this ACE.
                    The tag priority can't be set when 802.1Q Tagged is disabled.
                    range: 0~7,0-1,2-3,4-5,6-7,0-3,4-7."
               ::= {     sm24dp4xaACLACEEntry 19 }

    sm24dp4xaACLACESMAC OBJECT-TYPE
               SYNTAX      DisplayString
               MAX-ACCESS  read-create
               STATUS      current
               DESCRIPTION
                   "Configure source MAC address for this ACE.
                    <mac-address>: A frame that hits this ACE matches this
                    source MAC address value. xx-xx-xx-xx-xx-xx.
                    Any: Don't care."
               ::= {    sm24dp4xaACLACEEntry 20 }

    sm24dp4xaACLACEDMACType OBJECT-TYPE
               SYNTAX      INTEGER { any(0), mc(1), bc(2), uc(3) ,
                                     macAddress(4) , noData(5) }
               MAX-ACCESS  read-create
               STATUS      current
               DESCRIPTION
                   "DMAC Type.
                    default: 0,
                    0: Any - Don't care.
                    1: Multicast - Frame must be multicast.
                    2: Broadcast - Frame must be broadcast.
                    3: Unicast - Frame must be unicast.
                    4: mac address.
                    5: no data."
               DEFVAL  { any }
               ::= {    sm24dp4xaACLACEEntry 21 }

    sm24dp4xaACLACEDMAC OBJECT-TYPE
               SYNTAX      DisplayString
               MAX-ACCESS  read-create
               STATUS      current
               DESCRIPTION
                   "Configure destination MAC address for this ACE.
                    <mac-address>: A frame that hits this ACE matches this
                    destination MAC address value. xx-xx-xx-xx-xx-xx."
               ::= {     sm24dp4xaACLACEEntry 22 }

    sm24dp4xaACLACEEtherType OBJECT-TYPE
               SYNTAX      Integer32(-1..65535)
               MAX-ACCESS  read-create
               STATUS      current
               DESCRIPTION
                   "0: Any - Any but excluding 0x0800(IPv4) 0x0806(ARP) and
                    0x86DD(IPv6).
                    range : 0 or 1536(0x0600), 65535(0xffff).
                    -1: No data. "
               ::= {     sm24dp4xaACLACEEntry 23 }

    sm24dp4xaACLACEArpOpCode OBJECT-TYPE
               SYNTAX      INTEGER { any(0), arp(1), rarp(2),
                                     other(3), noData(4) }
               MAX-ACCESS  read-create
               STATUS      current
               DESCRIPTION
                   "Configure ARP opcode for this ACE.
                    default: 0,
                    0: Any - Don't care.
                    1: arp.
                    2: rarp.
                    3: other.
                    4: No data."
               DEFVAL  { any }
               ::= {     sm24dp4xaACLACEEntry 24 }

    sm24dp4xaACLACEArpFlagsRequestReply OBJECT-TYPE
               SYNTAX      INTEGER { reply(0), request(1), any(2), noData(3)}
               MAX-ACCESS  read-create
               STATUS      current
               DESCRIPTION
                   "Specify the available ARP/RARP opcode (OP) flag for this ACE.
                    default: 2,
                    0: Frame must have ARP Reply or RARP Reply OP flag.
                    1: Frame must have ARP Request or RARP Request OP flag set.
                    2: Any - Don't care.
                    3: No data."
               DEFVAL  { any }
               ::= {     sm24dp4xaACLACEEntry 25 }

    sm24dp4xaACLACEArpFlagsArpSMac OBJECT-TYPE
               SYNTAX      INTEGER { notEqualSMAC(0), equalSMAC(1),
                                     any(2), noData(3)}
               MAX-ACCESS  read-create
               STATUS      current
               DESCRIPTION
                   "Specify whether frames can hit the action according to their
                    sender hardware address field (SHA) settings.
                    default: 2,
                    0: ARP frames where SHA is not equal to the SMAC address.
                    1: ARP frames where SHA is equal to the SMAC address.
                    2: Any - Don't care.
                    3: No data."
               DEFVAL  { any }
               ::= {     sm24dp4xaACLACEEntry 26 }

    sm24dp4xaACLACEArpFlagsRarpDmac OBJECT-TYPE
               SYNTAX      INTEGER { notEqualDMAC(0), equalDMAC(1),
                                     any(2), noData(3)}
               MAX-ACCESS  read-create
               STATUS      current
               DESCRIPTION
                   "Specify whether frames can hit the action according to
                    their target hardware address field (THA) settings.
                    default: 2,
                    0: RARP frames where THA is not equal to the DMAC address.
                    1: RARP frames where THA is equal to the DMAC address.
                    2: Any - Don't care.
                    3: No data."
               DEFVAL  { any }
               ::= {     sm24dp4xaACLACEEntry 27 }

    sm24dp4xaACLACEArpFlagsLength OBJECT-TYPE
               SYNTAX      INTEGER { notEqualEthIpV4 (0), equalEthIpV4(1),
                                     any(2), noData(3)}
               MAX-ACCESS  read-create
               STATUS      current
               DESCRIPTION
                   "Specify whether frames can hit the action according to
                    their ARP/RARP hardware address length (HLN) and protocol
                    address length (PLN) settings.
                    default: 2,
                    0: ARP/RARP frames where the HLN is not equal to
                    Ethernet(0x06) or the (PLN) is not equal to IPv4(0x04).
                    1: ARP/RARP frames where the HLN is equal to Ethernet (0x06)
                    and the (PLN) is equal to IPv4(0x04).
                    2: Any - Don't care.
                    3: No data."
                DEFVAL  { any }
                ::= {     sm24dp4xaACLACEEntry 28 }

    sm24dp4xaACLACEArpFlagsIp OBJECT-TYPE
               SYNTAX      INTEGER { notEqualEth(0), equalEth(1),
                                     any(2), noData(3)}
               MAX-ACCESS  read-create
               STATUS      current
               DESCRIPTION
                   "Specify whether frames can hit the action according to
                    their ARP/RARP hardware address space (HRD) settings.
                    default: 2,
                    0: ARP/RARP frames where the HLD is not equal to Ethernet(1).
                    1: ARP/RARP frames where the HLD is equal to Ethernet(1).
                    2: Any - Don't care.
                    3: No data."
               DEFVAL  { any }
               ::= {     sm24dp4xaACLACEEntry 29 }

    sm24dp4xaACLACEArpFlagsEthernet OBJECT-TYPE
               SYNTAX      INTEGER { notEqualIp(0), equalIp(1),
                                     any(2), noData(3)}
               MAX-ACCESS  read-create
               STATUS      current
               DESCRIPTION
                   "Specify whether frames can hit the action
                    according to their ARP/RARP protocol address space (PRO) settings.
                    default: 2,
                    0: ARP/RARP frames where the PRO is not equal to IP\n(0x800).
                    1: ARP/RARP frames where the PRO is equal to IP(0x800).
                    2: Any - Don't care.
                    3: No data."
               DEFVAL  { any }
               ::= {     sm24dp4xaACLACEEntry 30 }

    sm24dp4xaACLACESIPType OBJECT-TYPE
               SYNTAX      INTEGER { any(0), ip(1), network(2), noData(3) }
               MAX-ACCESS  read-create
               STATUS      current
               DESCRIPTION
                   "Configure source IP address for this ACE.
                    default: 0,
                    0: Any - Don't care.
                    1: IP Address.
                    2: Network.
                    3: No data."
               DEFVAL  { any }
               ::= {     sm24dp4xaACLACEEntry 31 }

    sm24dp4xaACLACESIPIPAddress OBJECT-TYPE
               SYNTAX      IpAddress
               MAX-ACCESS  read-create
               STATUS      current
               DESCRIPTION
                   "A frame that hits this ACE matches this source IP address
                    value."
               ::= {     sm24dp4xaACLACEEntry 32 }

    sm24dp4xaACLACESIPIPMask OBJECT-TYPE
               SYNTAX      IpAddress
               MAX-ACCESS  read-create
               STATUS      current
               DESCRIPTION
                   "Specific sender IP mask in dotted decimal notation."
               ::= {     sm24dp4xaACLACEEntry 33 }

    sm24dp4xaACLACEDIPType OBJECT-TYPE
               SYNTAX      INTEGER { any(0), ip(1), network(2), noData(3) }
               MAX-ACCESS  read-create
               STATUS      current
               DESCRIPTION
                   "Configure destination IP address for this ACE.
                    default: 0,
                    0: Any - Don't care.
                    1: IP Address.
                    2: Network.
                    3: No data."
               DEFVAL  { any }
               ::= {     sm24dp4xaACLACEEntry 34 }

    sm24dp4xaACLACEDIPIPAddress OBJECT-TYPE
               SYNTAX      IpAddress
               MAX-ACCESS  read-create
               STATUS      current
               DESCRIPTION
                   "A frame that hits this ACE matches this destination IP
                    address value."
               ::= {     sm24dp4xaACLACEEntry 35 }

    sm24dp4xaACLACEDIPIPMask OBJECT-TYPE
               SYNTAX      IpAddress
               MAX-ACCESS  read-create
               STATUS      current
               DESCRIPTION
                   "Specific sender IP mask in dotted decimal notation."
               ::= {     sm24dp4xaACLACEEntry 36 }

    sm24dp4xaACLACEIPProtocol OBJECT-TYPE
               SYNTAX      INTEGER{ any(0), icmp(1), udp(2), tcp(3),
                                    other(4), noData(5)}
               MAX-ACCESS  read-create
               STATUS      current
               DESCRIPTION
                   "Specify the IP protocol filter for this ACE.
                    default: 0,
                    0: Any,
                    1: ICMP,
                    2: UDP,
                    3: TCP,
                    4: Other,
                    5: no data."
               DEFVAL  { any }
               ::= {     sm24dp4xaACLACEEntry 37 }

    sm24dp4xaACLACEIPProtocolValue OBJECT-TYPE
               SYNTAX      Integer32(0..256)
               MAX-ACCESS  read-create
               STATUS      current
               DESCRIPTION
                   "Configure IP protocol value for this ACE when IP Protocol
                    is 'other'.
                    default: 256,
                    256: No data.
                    range : 0 - 256"
               ::= {     sm24dp4xaACLACEEntry 38 }

    sm24dp4xaACLACEIPFlagsTTL OBJECT-TYPE
               SYNTAX      INTEGER { nonZero(0), zero(1), any(2), noData(3) }
               MAX-ACCESS  read-create
               STATUS      current
               DESCRIPTION
                   "Specify the Time-to-Live settings for this ACE.
                    default: 0,
                    0: zero,
                    1: Non-Zero
                    2: Any,,
                    3: No data."
               DEFVAL  { nonZero }
               ::= {     sm24dp4xaACLACEEntry 39 }

    sm24dp4xaACLACEIPFlagsFragment OBJECT-TYPE
               SYNTAX      INTEGER{yes(0), no(1), any(2), noData(3)}
               MAX-ACCESS  read-create
               STATUS      current
               DESCRIPTION
                   "Specify the fragment offset settings for this ACE.
                    default: 2,
                    0: No,
                    1: Yes,
                    2: Any,
                    3: No data."
               DEFVAL  { any }
               ::= {     sm24dp4xaACLACEEntry 40 }

    sm24dp4xaACLACEIPFlagsOptions OBJECT-TYPE
               SYNTAX      INTEGER{yes(0), no(1), any(2),  noData(3)}
               MAX-ACCESS  read-create
               STATUS      current
               DESCRIPTION
                   "Specify the options flag setting for this ACE.
                    default: 2,
                    0: No,
                    1: Yes,
                    2: Any,
                    3: No data."
               DEFVAL  { any }
               ::= {     sm24dp4xaACLACEEntry 41 }

    sm24dp4xaACLACEICMPType OBJECT-TYPE
               SYNTAX      Integer32(0..257)
               MAX-ACCESS  read-create
               STATUS      current
               DESCRIPTION
                   "Configure ICMP type for this ACE.
                    default: 256,
                    256: Any - Don't care.
                    257: No data.
                    range : 0 - 257."
               ::= { sm24dp4xaACLACEEntry 42 }

    sm24dp4xaACLACEICMPCode OBJECT-TYPE
               SYNTAX      Integer32(0..257)
               MAX-ACCESS  read-create
               STATUS      current
               DESCRIPTION
                   "Configure ICMP code for this ACE.
                    default: 256,
                    256: Any - Don't care.
                    257: No data.
                    range : 0 - 257."
               ::= {     sm24dp4xaACLACEEntry 43 }

    sm24dp4xaACLACESourcePort OBJECT-TYPE
               SYNTAX      DisplayString
               MAX-ACCESS  read-create
               STATUS      current
               DESCRIPTION
                   "Configure Source UDP/TCP port range for this ACE.
                    default: any,
                    specific: 0~65535,
                    range : 0 - 65535."
               ::= {     sm24dp4xaACLACEEntry 44 }

    sm24dp4xaACLACEDestPort OBJECT-TYPE
               SYNTAX      DisplayString
               MAX-ACCESS  read-create
               STATUS      current
               DESCRIPTION
                   "Configure Destination UDP/TCP port range for this ACE.
                    default: any,
                    specific: 0~65535,
                    range : 0 - 65535."
               ::= {     sm24dp4xaACLACEEntry 45 }

    sm24dp4xaACLACETCPFlagsFin OBJECT-TYPE
               SYNTAX      INTEGER { unset(0), set(1), any(2), noData(3) }
               MAX-ACCESS  read-create
               STATUS      current
               DESCRIPTION
                   "Configure TCP (FIN) flags for this ACE.
                    default: 2,
                    0: TCP frames where the FIN field is unset.
                    1: TCP frames where the FIN field is set.
                    2: Any - Don't care.
                    3: No data."
               DEFVAL  { any }
               ::= {     sm24dp4xaACLACEEntry 46 }

    sm24dp4xaACLACETCPFlagsSyn OBJECT-TYPE
               SYNTAX      INTEGER { unset(0), set(1), any(2), noData(3) }
               MAX-ACCESS  read-create
               STATUS      current
               DESCRIPTION
                   "Configure TCP (SYN) flags for this ACE.
                    default: 2,
                    0: TCP frames where the SYN field is unset.
                    1: TCP frames where the SYN field is set.
                    2: Any - Don't care.
                    3: No data."
               DEFVAL  { any }
               ::= {     sm24dp4xaACLACEEntry 47 }

    sm24dp4xaACLACETCPFlagsRst OBJECT-TYPE
               SYNTAX      INTEGER { unset(0), set(1), any(2), noData(3) }
               MAX-ACCESS  read-create
               STATUS      current
               DESCRIPTION
                   "Configure TCP (RST) flags for this ACE.
                    default: 2,
                    0: TCP frames where the RST field is unset.
                    1: TCP frames where the RST field is set.
                    2: Any - Don't care.
                    3: No data."
               DEFVAL  { any }
               ::= {     sm24dp4xaACLACEEntry 48 }

    sm24dp4xaACLACETCPFlagsPsh OBJECT-TYPE
               SYNTAX      INTEGER { unset(0), set(1), any(2), noData(3) }
               MAX-ACCESS  read-create
               STATUS      current
               DESCRIPTION
                   "Configure TCP (PSH) flags for this ACE.
                    default: 2,
                    0: TCP frames where the PSH field is unset.
                    1: TCP frames where the PSH field is set.
                    2: Any - Don't care.
                    3: No data."
               DEFVAL  { any }
               ::= {     sm24dp4xaACLACEEntry 49 }

    sm24dp4xaACLACETCPFlagsAck OBJECT-TYPE
               SYNTAX      INTEGER { unset(0), set(1), any(2), noData(3) }
               MAX-ACCESS  read-create
               STATUS      current
               DESCRIPTION
                   "Configure TCP (ACK) flags for this ACE.
                    default: 2,
                    0: TCP frames where the ACK field is unset.
                    1: TCP frames where the ACK field is set.
                    2: Any - Don't care.
                    3: No data."
               DEFVAL  { any }
               ::= {     sm24dp4xaACLACEEntry 50 }

    sm24dp4xaACLACETCPFlagsUrg OBJECT-TYPE
               SYNTAX      INTEGER { unset(0), set(1), any(2), noData(3) }
               MAX-ACCESS  read-create
               STATUS      current
               DESCRIPTION
                   "Configure TCP (URG) flags for this ACE.
                    default: 2,
                    0: TCP frames where the URG field is unset.
                    1: TCP frames where the URG field is set.
                    2: Any - Don't care.
                    3: No data."
               DEFVAL  { any }
               ::= {     sm24dp4xaACLACEEntry 51 }

    sm24dp4xaACLACEIPv6SIPAddress OBJECT-TYPE
               SYNTAX      DisplayString
               MAX-ACCESS  read-create
               STATUS      current
               DESCRIPTION
                   "When 'Specific' is selected for the source IPv6 filter,
                    you can enter a specific SIPv6 address.
                    The field only supported last 32 bits for IPv6 address. "
               ::= {     sm24dp4xaACLACEEntry 52 }

    sm24dp4xaACLACEIPv6SIPBitmask OBJECT-TYPE
               SYNTAX      DisplayString
               MAX-ACCESS  read-create
               STATUS      current
               DESCRIPTION
                   "When 'Specific' is selected for the source IPv6 filter,
                    you can enter a specific SIPv6 mask.
                    The field only supported last 32 bits for IPv6 address. "
               ::= {     sm24dp4xaACLACEEntry 53 }

    sm24dp4xaACLACEIPv6HopLimit OBJECT-TYPE
               SYNTAX      INTEGER { unset(0), set(1), any(2), noData(3) }
               MAX-ACCESS  read-create
               STATUS      current
               DESCRIPTION
                   "Specify the hop limit settings for this ACE.
                    default: 2,
                    0: Where the Hop Limit field is unset.
                    1: Where the Hop Limit field is set.
                    2: Any - Don't care,
                    3: No data."
               DEFVAL  { any }
               ::= {     sm24dp4xaACLACEEntry 54 }

    sm24dp4xaACLACERowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sm24dp4xaACLACEEntry 56 }

--
-- =======================================================================================================================
-- Start sm24dp4xaACLStatus group
-- =======================================================================================================================
--sm24dp4xaACLStatusTable

    sm24dp4xaACLStatusTable OBJECT-TYPE
               SYNTAX      SEQUENCE OF     SM24DP4XAACLStatusEntry
               MAX-ACCESS  not-accessible
               STATUS      current
               DESCRIPTION
                   " ACL ACE Status entry. "
               ::= {     sm24dp4xaACL 4 }

    sm24dp4xaACLStatusEntry OBJECT-TYPE
               SYNTAX          SM24DP4XAACLStatusEntry
               MAX-ACCESS  not-accessible
               STATUS      current
               DESCRIPTION
                   "The ACL Status Entry."
               INDEX    {    sm24dp4xaACLStatusIndex  }
               ::= {     sm24dp4xaACLStatusTable 1 }

    SM24DP4XAACLStatusEntry             ::= SEQUENCE {
                 sm24dp4xaACLStatusIndex          Integer32,
                 sm24dp4xaACLStatusUser           DisplayString,
                 sm24dp4xaACLStatusID             Integer32,
                 sm24dp4xaACLStatusIngressPort    DisplayString,
                 sm24dp4xaACLStatusFrameType      DisplayString,
                 sm24dp4xaACLStatusAction         DisplayString,
                 sm24dp4xaACLStatusRateLimiter    DisplayString,
                 sm24dp4xaACLStatusPortRedirect   DisplayString,
                 sm24dp4xaACLStatusMirror         DisplayString,
                 sm24dp4xaACLStatusCPU            DisplayString,
--               sm24dp4xaACLStatusCPUOnce        DisplayString,
                 sm24dp4xaACLStatusCounter        Counter32,
                 sm24dp4xaACLStatusConflict       DisplayString
                 }

    sm24dp4xaACLStatusIndex OBJECT-TYPE
               SYNTAX      Integer32(1..256)
               MAX-ACCESS  not-accessible
               STATUS      current
               DESCRIPTION
                   "The ACL status index. "
               ::= {     sm24dp4xaACLStatusEntry 1 }

    sm24dp4xaACLStatusUser OBJECT-TYPE
               SYNTAX      DisplayString
               MAX-ACCESS  read-only
               STATUS      current
               DESCRIPTION
                   "Indicates the ACL user.
                    S : Static,
                    IPMG : IP Management,
                    IPSG : IP Source Guard,
                    IPMC : IPMC,
                    ARPI : Arp Inspection,
                    UPnP : UPnP,
                    DHCP : DHCP. "
               ::= {     sm24dp4xaACLStatusEntry 2 }

    sm24dp4xaACLStatusID OBJECT-TYPE
               SYNTAX      Integer32(1..256)
               MAX-ACCESS  read-only
               STATUS      current
               DESCRIPTION
                   "ACE ID.
                    range : 1 - 256. "
               ::= {     sm24dp4xaACLStatusEntry 3 }

    sm24dp4xaACLStatusIngressPort OBJECT-TYPE
               SYNTAX      DisplayString
               MAX-ACCESS  read-only
               STATUS      current
               DESCRIPTION
                   "Indicates the ingress port of the ACE. Possible values are:
                    All: The ACE will match all ingress port.
                    Port: The ACE will match a specific ingress port. "
               ::= {     sm24dp4xaACLStatusEntry 4 }

    sm24dp4xaACLStatusFrameType OBJECT-TYPE
               SYNTAX      DisplayString
               MAX-ACCESS  read-only
               STATUS      current
               DESCRIPTION
                   "Indicates the frame type of the ACE.
                    Any: The ACE will match any frame type.
                    EType: The ACE will match Ethernet Type frames.
                    Note that an Ethernet Type based ACE will not get matched
                    by IP and ARP frames.
                    ARP: The ACE will match ARP/RARP frames.
                    IPv4: The ACE will match all IPv4 frames.
                    IPv4/ICMP: The ACE will match IPv4 frames with ICMP protocol.
                    IPv4/UDP: The ACE will match IPv4 frames with UDP protocol.
                    IPv4/TCP: The ACE will match IPv4 frames with TCP protocol.
                    IPv4/Other: The ACE will match IPv4 frames, which are not
                    ICMP/UDP/TCP.
                    IPv6: The ACE will match all IPv6 standard frames. "
               ::= {     sm24dp4xaACLStatusEntry 5 }

    sm24dp4xaACLStatusAction OBJECT-TYPE
               SYNTAX      DisplayString
               MAX-ACCESS  read-only
               STATUS      current
               DESCRIPTION
                   "Indicates the forwarding action of the ACE. "
               ::= {     sm24dp4xaACLStatusEntry 6 }

    sm24dp4xaACLStatusRateLimiter OBJECT-TYPE
               SYNTAX      DisplayString
               MAX-ACCESS  read-only
               STATUS      current
               DESCRIPTION
                   "Indicates the rate limiter number of the ACE. "
               ::= {     sm24dp4xaACLStatusEntry 7 }

    sm24dp4xaACLStatusPortRedirect OBJECT-TYPE
               SYNTAX      DisplayString
               MAX-ACCESS  read-only
               STATUS      current
               DESCRIPTION
                   "Indicates the port redirect operation of the ACE.
                    Frames matching the ACE are redirected to the port number. "
               ::= {     sm24dp4xaACLStatusEntry 8 }

    sm24dp4xaACLStatusMirror OBJECT-TYPE
               SYNTAX      DisplayString
               MAX-ACCESS  read-only
               STATUS      current
               DESCRIPTION
                   "Specify the mirror operation of this port.
                    Not support 'sm24dp4xa'."
               ::= {     sm24dp4xaACLStatusEntry 9 }

    sm24dp4xaACLStatusCPU OBJECT-TYPE
               SYNTAX      DisplayString
               MAX-ACCESS  read-only
               STATUS      current
               DESCRIPTION
                   "Forward packet that matched the specific ACE to CPU. "
               ::= {     sm24dp4xaACLStatusEntry 10 }

--    sm24dp4xaACLStatusCPUOnce OBJECT-TYPE
--               SYNTAX      DisplayString
--               MAX-ACCESS  read-only
--               STATUS      current
--               DESCRIPTION
--                   "Forward first packet that matched the specific ACE to CPU. "
--               ::= {     sm24dp4xaACLStatusEntry 11 }

    sm24dp4xaACLStatusCounter OBJECT-TYPE
               SYNTAX      Counter32
               MAX-ACCESS  read-only
               STATUS      current
               DESCRIPTION
                   "The counter indicates the number of times the ACE was hit
                    by a frame. "
               ::= {     sm24dp4xaACLStatusEntry 12 }

    sm24dp4xaACLStatusConflict OBJECT-TYPE
               SYNTAX      DisplayString
               MAX-ACCESS  read-only
               STATUS      current
               DESCRIPTION
                   "Indicates the hardware status of the specific ACE.
                    The specific ACE is not applied to the hardware due to
                    hardware limitations. "
               ::= {     sm24dp4xaACLStatusEntry 13 }


-- =======================================================================================================================
-- sm24dp4xaAclConformance
-- =======================================================================================================================
sm24dp4xaAclConformance OBJECT IDENTIFIER ::= { sm24dp4xaACL 200 }

sm24dp4xaAclCompliances OBJECT IDENTIFIER ::= { sm24dp4xaAclConformance 1 }

sm24dp4xaAclGroups    OBJECT IDENTIFIER ::= { sm24dp4xaAclConformance 2 }

sm24dp4xaACLPortConfGroup OBJECT-GROUP
    OBJECTS {
                -- sm24dp4xaACLPortConfTable
                 sm24dp4xaACLPortConfPolicyID,
                 sm24dp4xaACLPortConfAction,
                 sm24dp4xaACLPortConfRateLimiterID,
                 sm24dp4xaACLPortConfPortRedirect,
--               sm24dp4xaACLPortConfMirror,
                 sm24dp4xaACLPortConfLogging,
                 sm24dp4xaACLPortConfShutdown,
                 sm24dp4xaACLPortConfState,
                 sm24dp4xaACLPortConfCounter
            }
     STATUS  current
     DESCRIPTION
            "The collection of objects which are used to indicate
            sm24dp4xa ACL information."
    ::= { sm24dp4xaAclGroups 1 }

sm24dp4xaACLRateLimiterGroup OBJECT-GROUP
    OBJECTS {
                -- sm24dp4xaACLRateLimiterTable
                 sm24dp4xaACLRateLimiterRate
--               sm24dp4xaACLRateLimiterUnit
            }
     STATUS  current
     DESCRIPTION
            "The collection of objects which are used to indicate
            sm24dp4xa ACL information."
    ::= { sm24dp4xaAclGroups 2 }

sm24dp4xaACLACEGroup OBJECT-GROUP
    OBJECTS {
                -- sm24dp4xaACLACEClear
                 sm24dp4xaACLACEClear,

                -- sm24dp4xaACLACETable
                 sm24dp4xaACLACEID,
                 sm24dp4xaACLACENextID,
--               sm24dp4xaACLACELoopUp,
                 sm24dp4xaACLACEIngressPort,
                 sm24dp4xaACLACEPortPolicyNumber,
                 sm24dp4xaACLACEPortPolicyBitmask,
                 sm24dp4xaACLACEFrameType,
                 sm24dp4xaACLACEAction,
--               sm24dp4xaACLACEFilterPort,
                 sm24dp4xaACLACEDenyPortRedirect,
                 sm24dp4xaACLACERateLimiter,
--               sm24dp4xaACLACEMirror,
                 sm24dp4xaACLACELogging,
                 sm24dp4xaACLACEShutdown,
                 sm24dp4xaACLACECounter,
--               sm24dp4xaACLACEVLAN8021QTagged,
                 sm24dp4xaACLACEVLANVID,
                 sm24dp4xaACLACEVLANTagPriority,
                 sm24dp4xaACLACESMAC,
                 sm24dp4xaACLACEDMACType,
                 sm24dp4xaACLACEDMAC,
                 sm24dp4xaACLACEEtherType,
                 sm24dp4xaACLACEArpOpCode,
                 sm24dp4xaACLACEArpFlagsRequestReply,
                 sm24dp4xaACLACEArpFlagsArpSMac,
                 sm24dp4xaACLACEArpFlagsRarpDmac,
                 sm24dp4xaACLACEArpFlagsLength,
                 sm24dp4xaACLACEArpFlagsIp,
                 sm24dp4xaACLACEArpFlagsEthernet,
                 sm24dp4xaACLACESIPType,
                 sm24dp4xaACLACESIPIPAddress,
                 sm24dp4xaACLACESIPIPMask,
                 sm24dp4xaACLACEDIPType,
                 sm24dp4xaACLACEDIPIPAddress,
                 sm24dp4xaACLACEDIPIPMask,
                 sm24dp4xaACLACEIPProtocol,
                 sm24dp4xaACLACEIPProtocolValue,
                 sm24dp4xaACLACEIPFlagsTTL,
                 sm24dp4xaACLACEIPFlagsFragment,
                 sm24dp4xaACLACEIPFlagsOptions,
                 sm24dp4xaACLACEICMPType,
                 sm24dp4xaACLACEICMPCode,
                 sm24dp4xaACLACESourcePort,
                 sm24dp4xaACLACEDestPort,
                 sm24dp4xaACLACETCPFlagsFin,
                 sm24dp4xaACLACETCPFlagsSyn,
                 sm24dp4xaACLACETCPFlagsRst,
                 sm24dp4xaACLACETCPFlagsPsh,
                 sm24dp4xaACLACETCPFlagsAck,
                 sm24dp4xaACLACETCPFlagsUrg,
                 sm24dp4xaACLACEIPv6SIPAddress,
                 sm24dp4xaACLACEIPv6SIPBitmask,
                 sm24dp4xaACLACEIPv6HopLimit,
                 sm24dp4xaACLACERowStatus
            }
     STATUS  current
     DESCRIPTION
            "The collection of objects which are used to indicate
            sm24dp4xa ACL information."
    ::= { sm24dp4xaAclGroups 3 }

sm24dp4xaACLStatusGroup OBJECT-GROUP
    OBJECTS {
                -- sm24dp4xaACLStatusTable
                 sm24dp4xaACLStatusUser,
                 sm24dp4xaACLStatusID,
                 sm24dp4xaACLStatusIngressPort,
                 sm24dp4xaACLStatusFrameType,
                 sm24dp4xaACLStatusAction,
                 sm24dp4xaACLStatusRateLimiter,
                 sm24dp4xaACLStatusPortRedirect,
                 sm24dp4xaACLStatusMirror,
                 sm24dp4xaACLStatusCPU,
--               sm24dp4xaACLStatusCPUOnce,
                 sm24dp4xaACLStatusCounter,
                 sm24dp4xaACLStatusConflict
            }
     STATUS  current
     DESCRIPTION
            "The collection of objects which are used to indicate
            sm24dp4xa ACL information."
    ::= { sm24dp4xaAclGroups 4 }


-- =======================================================================================================================
-- =======================================================================================================================
 -- RowStatus Info:  createAndGo, notReady not supported.
-- =======================================================================================================================
-- Textual Conventions for the sm24dp4xa Qos Mib
-- =======================================================================================================================
--
sm24dp4xaQosConf                    OBJECT IDENTIFIER ::= { sm24dp4xaConfiguration 10 }
    sm24dp4xaQos                        OBJECT IDENTIFIER   ::= { sm24dp4xaQosConf  1  }
    sm24dp4xaQosPortClassification      OBJECT IDENTIFIER   ::= { sm24dp4xaQos 1 }
    sm24dp4xaQosPortPolicing            OBJECT IDENTIFIER   ::= { sm24dp4xaQos 2 }
    sm24dp4xaQosQueuePolicing           OBJECT IDENTIFIER   ::= { sm24dp4xaQos 3 }
    sm24dp4xaQosPortScheduler           OBJECT IDENTIFIER   ::= { sm24dp4xaQos 4 }
    sm24dp4xaQosPortEgressTagRemarking  OBJECT IDENTIFIER   ::= { sm24dp4xaQos 6 }
    sm24dp4xaQosPortDSCP                OBJECT IDENTIFIER   ::= { sm24dp4xaQos 7 }
    sm24dp4xaQosDSCP                    OBJECT IDENTIFIER   ::= { sm24dp4xaQos 8 }
    sm24dp4xaQosDSCPTranslation         OBJECT IDENTIFIER   ::= { sm24dp4xaQos 9 }
    sm24dp4xaQosDSCPClassification      OBJECT IDENTIFIER   ::= { sm24dp4xaQos 10 }
    sm24dp4xaQosControlList             OBJECT IDENTIFIER   ::= { sm24dp4xaQos 11 }
    sm24dp4xaQosStormControl            OBJECT IDENTIFIER   ::= { sm24dp4xaQos 12 }
    sm24dp4xaQosPortStormControl        OBJECT IDENTIFIER   ::= { sm24dp4xaQos 13 }
    sm24dp4xaQosWRED                    OBJECT IDENTIFIER   ::= { sm24dp4xaQos 14 }
    sm24dp4xaQosQCLStatus               OBJECT IDENTIFIER   ::= { sm24dp4xaQos 15 }


--
-- =======================================================================================================================
-- Start sm24dp4xaQosPortClassification group
-- =======================================================================================================================
--sm24dp4xaQosPortClassificationTable

     sm24dp4xaQosPortClassificationTable OBJECT-TYPE
               SYNTAX      SEQUENCE OF     SM24DP4XAQosPortClassificationEntry
               MAX-ACCESS  not-accessible
               STATUS      current
               DESCRIPTION
                   "QoS Ingress Port Classification.
                    INDEX for this table is ifIndex which is
                    equivalent to the panel port number."
               ::= {     sm24dp4xaQosPortClassification  1 }

    sm24dp4xaQosPortClassificationEntry OBJECT-TYPE
               SYNTAX          SM24DP4XAQosPortClassificationEntry
               MAX-ACCESS  not-accessible
               STATUS      current
               DESCRIPTION
                   "The Qos Port Classification Table."
               INDEX    {     ifIndex  }
               ::= {     sm24dp4xaQosPortClassificationTable 1 }

    SM24DP4XAQosPortClassificationEntry             ::= SEQUENCE {
                sm24dp4xaQosPortClassificationQoSClass        Integer32,
                sm24dp4xaQosPortClassificationDPlevel         Integer32,
                sm24dp4xaQosPortClassificationPCP             Integer32,
                sm24dp4xaQosPortClassificationDEI             Integer32,
                sm24dp4xaQosPortClassificationTagClass        AdminMode,
                sm24dp4xaQosPortClassificationDSCPBased       AdminMode,
                sm24dp4xaQosPortClassificationQCLAddr         INTEGER,
                sm24dp4xaQosPortClassificationKeyType         KeyType,
		sm24dp4xaQosPortClassificationWredGroup       Integer32 
                }

    sm24dp4xaQosPortClassificationQoSClass OBJECT-TYPE
               SYNTAX      Integer32(0..7)
               MAX-ACCESS  read-write
               STATUS      current
               DESCRIPTION
                  "Controls the default QoS class, i.e., the QoS class for
                   frames not classified
                   in any way. There is a one to one mapping between
                   QoS class, queue and
                   priority. A QoS class of 0 (zero) has the lowest priority.
                   NOTe: If the QoS class has been dynamically changed, then
                   the actual QoS class
                   is shown in parentheses after the configured QoS class.
                   range: 0~7,
                   default: 0."
               ::= {     sm24dp4xaQosPortClassificationEntry 2 }

    sm24dp4xaQosPortClassificationDPlevel OBJECT-TYPE
               SYNTAX      Integer32(0..3)
               MAX-ACCESS  read-write
               STATUS      current
               DESCRIPTION
                   "DP level for frames not classified in any way.
                    range: 0~3,
                    default: 0."
               ::= {     sm24dp4xaQosPortClassificationEntry 3 }

    sm24dp4xaQosPortClassificationPCP OBJECT-TYPE
               SYNTAX      Integer32(0..7)
               MAX-ACCESS  read-write
               STATUS      current
               DESCRIPTION
                  "Priority Code Point. It is a 3-bit field storing
                   the priority level for the 802.1Q frame.
                   range: 0~7,
                   default: 0.
                   Not support JAGUAR."
               ::= {     sm24dp4xaQosPortClassificationEntry 4 }

    sm24dp4xaQosPortClassificationDEI OBJECT-TYPE
               SYNTAX      Integer32(0|1)
               MAX-ACCESS  read-write
               STATUS      current
               DESCRIPTION
                  "Drop Eligible Indicator. It is a 1-bit field in the VLAN.
                   range 0~1,
                   default: 0.
                   Not support JAGUAR."
               ::= {     sm24dp4xaQosPortClassificationEntry 5 }

    sm24dp4xaQosPortClassificationTagClass OBJECT-TYPE
               SYNTAX      AdminMode
               MAX-ACCESS  read-write
               STATUS      current
               DESCRIPTION
                  "Configure the classification mode for tagged frames.
                  Not support SMB and JAGUAR."
               DEFVAL  { disable }
               ::= {     sm24dp4xaQosPortClassificationEntry 6 }

    sm24dp4xaQosPortClassificationDSCPBased OBJECT-TYPE
               SYNTAX      AdminMode
               MAX-ACCESS  read-write
               STATUS      current
               DESCRIPTION
                  "Click to Enable DSCP Based QoS Ingress Port Classification."
               DEFVAL  { disable }
               ::= {     sm24dp4xaQosPortClassificationEntry 7 }

    sm24dp4xaQosPortClassificationQCLAddr OBJECT-TYPE
               SYNTAX      INTEGER { sMacSip(0), dMacDip (1) }
               MAX-ACCESS  read-write
               STATUS      current
               DESCRIPTION
                  "Controls the QCL address matching mode.
                   0: SMAC/SIP,
                   1: DMAC/DIP,
                  default: SMAC/SIP.
                  Only support SPARX_III."
               DEFVAL  { sMacSip }
               ::= {     sm24dp4xaQosPortClassificationEntry 8 }

    sm24dp4xaQosPortClassificationKeyType OBJECT-TYPE
               SYNTAX      KeyType
               MAX-ACCESS  read-write
               STATUS      current
               DESCRIPTION
                  "The key type specifying the key generated for frames received
                   on the port.
                   0: Normal, Half key, match outer tag, SIP/DIP and SMAC/DMAC.
                   1: Double Tag: Quarter key, match inner and outer tag.
                   2: IP Address: Half key, match inner and outer tag, SIP and
                      DIP. For non-IP frames, match outer tag only.
                   3: MAC and IP Address: Full key, match inner and outer tag,
                      SMAC, DMAC, SIP and DIP.
                   Only support on SERVAL version."
               DEFVAL  { normal }
               ::= {     sm24dp4xaQosPortClassificationEntry 9 }
			   
    sm24dp4xaQosPortClassificationWredGroup OBJECT-TYPE
               SYNTAX      Integer32
               MAX-ACCESS  read-write
               STATUS      current
               DESCRIPTION
                  "Controls the WRED group membership. Range:1-3."
               ::= {     sm24dp4xaQosPortClassificationEntry 10 }			   

--sm24dp4xaQoSIngressPortTagClassificationTable
    sm24dp4xaQoSIngressPortTagClassificationTable OBJECT-TYPE
               SYNTAX      SEQUENCE OF     SM24DP4XAQoSIngressPortTagClassificationEntry
               MAX-ACCESS  not-accessible
               STATUS      current
               DESCRIPTION
                   "Show QoS Ingress Port Tag Classification.
                    INDEX for this table is ifIndex which is
                    equivalent to the panel port number."
               ::= {     sm24dp4xaQosPortClassification 2 }

    sm24dp4xaQoSIngressPortTagClassificationEntry OBJECT-TYPE
               SYNTAX          SM24DP4XAQoSIngressPortTagClassificationEntry
               MAX-ACCESS  not-accessible
               STATUS      current
               DESCRIPTION
                   "QoS Ingress Port Tag Classification entry."
               INDEX    {     ifIndex,
                              sm24dp4xaQoSIngressPortTagPCP,
                              sm24dp4xaQoSIngressPortTagDEI  }
               ::= {     sm24dp4xaQoSIngressPortTagClassificationTable 1 }

    SM24DP4XAQoSIngressPortTagClassificationEntry             ::= SEQUENCE {
                sm24dp4xaQoSIngressPortTagPCP                   INTEGER,
                sm24dp4xaQoSIngressPortTagDEI                   INTEGER,
                sm24dp4xaQoSIngressPortTagQosClass              Integer32,
                sm24dp4xaQoSIngressPortTagDPLevel               Integer32
                }

    sm24dp4xaQoSIngressPortTagPCP OBJECT-TYPE
               SYNTAX      INTEGER { pcp0(1),
                                     pcp1(2),
                                     pcp2(3),
                                     pcp3(4),
                                     pcp4(5),
                                     pcp5(6),
                                     pcp6(7),
                                     pcp7(8) }
               MAX-ACCESS  not-accessible
               STATUS      current
               DESCRIPTION
                   "range: 1-8,
                    PCP0:1, PCP1:2..."
               ::= {     sm24dp4xaQoSIngressPortTagClassificationEntry 2 }

    sm24dp4xaQoSIngressPortTagDEI OBJECT-TYPE
               SYNTAX      INTEGER { dei0(1), dei1(2) }
               MAX-ACCESS  not-accessible
               STATUS      current
               DESCRIPTION
                   "Ingress Port Tag dei,
                    DEI0:1, DEI1:2."
               ::= {     sm24dp4xaQoSIngressPortTagClassificationEntry 3 }

    sm24dp4xaQoSIngressPortTagQosClass OBJECT-TYPE
               SYNTAX      Integer32(0..7)
               MAX-ACCESS  read-write
               STATUS      current
               DESCRIPTION
                   "range: 0-7."
               ::= {     sm24dp4xaQoSIngressPortTagClassificationEntry 4 }

    sm24dp4xaQoSIngressPortTagDPLevel OBJECT-TYPE
               SYNTAX      Integer32(0|1)
               MAX-ACCESS  read-write
               STATUS      current
               DESCRIPTION
                   "range: 0-1."
               ::= {     sm24dp4xaQoSIngressPortTagClassificationEntry 5 }


--
-- =======================================================================================================================
-- Start sm24dp4xaQosPortPolicing group
-- =======================================================================================================================
--sm24dp4xaQosPortPolicingTable
   sm24dp4xaQosPortPolicingTable OBJECT-TYPE
               SYNTAX      SEQUENCE OF     SM24DP4XAQosPortPolicingEntry
               MAX-ACCESS  not-accessible
               STATUS      current
               DESCRIPTION
                   "The Policer settings.
                    INDEX for this table is ifIndex which is
                    equivalent to the panel port number."
               ::= {     sm24dp4xaQosPortPolicing 1 }

    sm24dp4xaQosPortPolicingEntry OBJECT-TYPE
               SYNTAX          SM24DP4XAQosPortPolicingEntry
               MAX-ACCESS  not-accessible
               STATUS      current
               DESCRIPTION
                   "The Policer setting entry."
               INDEX    {     ifIndex  }
               ::= {     sm24dp4xaQosPortPolicingTable 1 }

    SM24DP4XAQosPortPolicingEntry             ::= SEQUENCE {
                sm24dp4xaQosPortPolicingEnabled         AdminMode,
                sm24dp4xaQosPortPolicingRate            Integer32,
                sm24dp4xaQosPortPolicingUnit            Integer32
--              sm24dp4xaQosPortPolicingFlowControl     AdminMode
                }

    sm24dp4xaQosPortPolicingEnabled OBJECT-TYPE
               SYNTAX      AdminMode
               MAX-ACCESS  read-write
               STATUS      current
               DESCRIPTION
                  "Controls whether the policer is enabled on this switch port."
               DEFVAL  { disable }
               ::= {     sm24dp4xaQosPortPolicingEntry 2 }

    sm24dp4xaQosPortPolicingRate OBJECT-TYPE
               SYNTAX      Integer32
               MAX-ACCESS  read-write
               STATUS      current
               DESCRIPTION
                   "Controls the rate for the policer.
                    default: 500(kbps)."
               ::= {     sm24dp4xaQosPortPolicingEntry 3 }

    sm24dp4xaQosPortPolicingUnit OBJECT-TYPE
               SYNTAX      Integer32
               MAX-ACCESS  read-write
               STATUS      current
               DESCRIPTION
                   "Controls the unit of measure for the policer rate.
                    0: kbps
                    1: Mbps
		    2: fps
		    3: kfps
		    "
               ::= {     sm24dp4xaQosPortPolicingEntry 4 }

--    sm24dp4xaQosPortPolicingFlowControl OBJECT-TYPE
--               SYNTAX      AdminMode
--               MAX-ACCESS  read-write
--               STATUS      current
--               DESCRIPTION
--                   "If flow control is enabled and the port is in flow control mode,
--                    then pause frames are sent instead of discarding frames."
--               DEFVAL  { disable }
--               ::= {     sm24dp4xaQosPortPolicingEntry 5 }

--
-- =======================================================================================================================
-- Start sm24dp4xaQosQueuePolicing group
-- =======================================================================================================================
--sm24dp4xaQosQueuePolicingTable
    sm24dp4xaQosQueuePolicingTable OBJECT-TYPE
               SYNTAX      SEQUENCE OF     SM24DP4XAQosQueuePolicingEntry
               MAX-ACCESS  not-accessible
               STATUS      current
               DESCRIPTION
                   "The Queue Policer settings.
                    INDEX for this table is ifIndex which is
                    equivalent to the panel port number."
               ::= {     sm24dp4xaQosQueuePolicing 1 }

    sm24dp4xaQosQueuePolicingEntry OBJECT-TYPE
               SYNTAX          SM24DP4XAQosQueuePolicingEntry
               MAX-ACCESS  not-accessible
               STATUS      current
               DESCRIPTION
                   "The Qos Queue Policing Entry."
               INDEX    {     ifIndex  }
               ::= {     sm24dp4xaQosQueuePolicingTable 1 }

    SM24DP4XAQosQueuePolicingEntry             ::= SEQUENCE {
                sm24dp4xaQosQueuePolicingQueue0Enable   AdminMode,
                sm24dp4xaQosQueuePolicingQueue0Rate     Integer32,
		sm24dp4xaQosQueuePolicingQueue0Unit     Integer32,
                sm24dp4xaQosQueuePolicingQueue1Enable   AdminMode,
                sm24dp4xaQosQueuePolicingQueue1Rate     Integer32,
		sm24dp4xaQosQueuePolicingQueue1Unit     Integer32,
                sm24dp4xaQosQueuePolicingQueue2Enable   AdminMode,
                sm24dp4xaQosQueuePolicingQueue2Rate     Integer32,
                sm24dp4xaQosQueuePolicingQueue2Unit     Integer32,
                sm24dp4xaQosQueuePolicingQueue3Enable   AdminMode,
                sm24dp4xaQosQueuePolicingQueue3Rate     Integer32,
                sm24dp4xaQosQueuePolicingQueue3Unit     Integer32,
                sm24dp4xaQosQueuePolicingQueue4Enable   AdminMode,
                sm24dp4xaQosQueuePolicingQueue4Rate     Integer32,
		sm24dp4xaQosQueuePolicingQueue4Unit     Integer32,
                sm24dp4xaQosQueuePolicingQueue5Enable   AdminMode,
                sm24dp4xaQosQueuePolicingQueue5Rate     Integer32,
		sm24dp4xaQosQueuePolicingQueue5Unit     Integer32,
                sm24dp4xaQosQueuePolicingQueue6Enable   AdminMode,
                sm24dp4xaQosQueuePolicingQueue6Rate     Integer32,
		sm24dp4xaQosQueuePolicingQueue6Unit     Integer32,
                sm24dp4xaQosQueuePolicingQueue7Enable   AdminMode,
                sm24dp4xaQosQueuePolicingQueue7Rate     Integer32,
		sm24dp4xaQosQueuePolicingQueue7Unit     Integer32
                }

    sm24dp4xaQosQueuePolicingQueue0Enable OBJECT-TYPE
               SYNTAX      AdminMode
               MAX-ACCESS  read-write
               STATUS      current
               DESCRIPTION
                   "Controls whether the queue 0 policer is enabled on this switch port."
               DEFVAL  { disable }
               ::= {     sm24dp4xaQosQueuePolicingEntry 3 }

    sm24dp4xaQosQueuePolicingQueue0Rate OBJECT-TYPE
               SYNTAX      Integer32
               MAX-ACCESS  read-write
               STATUS      current
               DESCRIPTION
                   "Controls whether the queue 0 policer is enabled on this switch port.
                    default: 500(Kbps)"
               ::= {     sm24dp4xaQosQueuePolicingEntry 4 }

    sm24dp4xaQosQueuePolicingQueue0Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sm24dp4xaQosQueuePolicingEntry 5 }			   
			   
    sm24dp4xaQosQueuePolicingQueue1Enable OBJECT-TYPE
               SYNTAX      AdminMode
               MAX-ACCESS  read-write
               STATUS      current
               DESCRIPTION
                   "Controls whether the queue 1 policer is enabled on this switch port."
               DEFVAL  { disable }
               ::= {     sm24dp4xaQosQueuePolicingEntry 6 }

    sm24dp4xaQosQueuePolicingQueue1Rate OBJECT-TYPE
               SYNTAX      Integer32
               MAX-ACCESS  read-write
               STATUS      current
               DESCRIPTION
                   "Controls whether the queue 1 policer is enabled on this switch port.,
                    default: 500(Kbps)"
               ::= {     sm24dp4xaQosQueuePolicingEntry 7 }
			   
    sm24dp4xaQosQueuePolicingQueue1Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sm24dp4xaQosQueuePolicingEntry 8 }			   
			   
    sm24dp4xaQosQueuePolicingQueue2Enable OBJECT-TYPE
               SYNTAX      AdminMode
               MAX-ACCESS  read-write
               STATUS      current
               DESCRIPTION
                   "Controls whether the queue 2 policer is enabled on this switch port."
               DEFVAL  { disable }
               ::= {     sm24dp4xaQosQueuePolicingEntry 9 }

    sm24dp4xaQosQueuePolicingQueue2Rate OBJECT-TYPE
               SYNTAX      Integer32
               MAX-ACCESS  read-write
               STATUS      current
               DESCRIPTION
                   "Controls whether the queue 2 policer is enabled on this switch port.
                    default: 500(Kbps)"
               ::= {     sm24dp4xaQosQueuePolicingEntry 10 }
			   
    sm24dp4xaQosQueuePolicingQueue2Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sm24dp4xaQosQueuePolicingEntry 11 }			   
			  
    sm24dp4xaQosQueuePolicingQueue3Enable OBJECT-TYPE
               SYNTAX      AdminMode
               MAX-ACCESS  read-write
               STATUS      current
               DESCRIPTION
                   "Controls whether the queue 3 policer is enabled on this switch port."
               DEFVAL  { disable }
               ::= {     sm24dp4xaQosQueuePolicingEntry 12 }

    sm24dp4xaQosQueuePolicingQueue3Rate OBJECT-TYPE
               SYNTAX      Integer32
               MAX-ACCESS  read-write
               STATUS      current
               DESCRIPTION
                   "Controls whether the queue 3 policer is enabled on this switch port.
                    default: 500(Kbps)"
               ::= {     sm24dp4xaQosQueuePolicingEntry 13 }
			   
    sm24dp4xaQosQueuePolicingQueue3Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sm24dp4xaQosQueuePolicingEntry 14 }			   
			   
    sm24dp4xaQosQueuePolicingQueue4Enable OBJECT-TYPE
               SYNTAX      AdminMode
               MAX-ACCESS  read-write
               STATUS      current
               DESCRIPTION
                   "Controls whether the queue 4 policer is enabled on this switch port."
               DEFVAL  { disable }
               ::= {     sm24dp4xaQosQueuePolicingEntry 15 }

    sm24dp4xaQosQueuePolicingQueue4Rate OBJECT-TYPE
               SYNTAX      Integer32
               MAX-ACCESS  read-write
               STATUS      current
               DESCRIPTION
                   "Controls whether the queue 4 policer is enabled on this switch port.
                    default: 500(Kbps)"
               ::= {     sm24dp4xaQosQueuePolicingEntry 16 }
			   
    sm24dp4xaQosQueuePolicingQueue4Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sm24dp4xaQosQueuePolicingEntry 17 }			   
			   
    sm24dp4xaQosQueuePolicingQueue5Enable OBJECT-TYPE
               SYNTAX      AdminMode
               MAX-ACCESS  read-write
               STATUS      current
               DESCRIPTION
                   "Controls whether the queue 5 policer is enabled on this switch port."
               DEFVAL  { disable }
               ::= {     sm24dp4xaQosQueuePolicingEntry 18 }

    sm24dp4xaQosQueuePolicingQueue5Rate OBJECT-TYPE
               SYNTAX      Integer32
               MAX-ACCESS  read-write
               STATUS      current
               DESCRIPTION
                   "Controls whether the queue 5 policer is enabled on this switch port.
                    default: 500(Kbps)"
               ::= {     sm24dp4xaQosQueuePolicingEntry 19 }

    sm24dp4xaQosQueuePolicingQueue5Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sm24dp4xaQosQueuePolicingEntry 20 }			   
			   			   
    sm24dp4xaQosQueuePolicingQueue6Enable OBJECT-TYPE
               SYNTAX      AdminMode
               MAX-ACCESS  read-write
               STATUS      current
               DESCRIPTION
                   "Controls whether the queue 6 policer is enabled on this switch port."
               DEFVAL  { disable }
               ::= {     sm24dp4xaQosQueuePolicingEntry 21 }

    sm24dp4xaQosQueuePolicingQueue6Rate OBJECT-TYPE
               SYNTAX      Integer32
               MAX-ACCESS  read-write
               STATUS      current
               DESCRIPTION
                   "Controls whether the queue 6 policer is enabled on this switch port.
                    default: 500(Kbps)"
               ::= {     sm24dp4xaQosQueuePolicingEntry 22 }
			   
    sm24dp4xaQosQueuePolicingQueue6Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sm24dp4xaQosQueuePolicingEntry 23 }			   
			   
    sm24dp4xaQosQueuePolicingQueue7Enable OBJECT-TYPE
               SYNTAX      AdminMode
               MAX-ACCESS  read-write
               STATUS      current
               DESCRIPTION
                   "Controls whether the queue 7 policer is enabled on this switch port."
               DEFVAL  { disable }
               ::= {     sm24dp4xaQosQueuePolicingEntry 24 }

    sm24dp4xaQosQueuePolicingQueue7Rate OBJECT-TYPE
               SYNTAX      Integer32
               MAX-ACCESS  read-write
               STATUS      current
               DESCRIPTION
                   "Controls whether the queue 7 policer is enabled on this switch port.
                    default: 500(Kbps)"
               ::= {     sm24dp4xaQosQueuePolicingEntry 25 }

    sm24dp4xaQosQueuePolicingQueue7Unit OBJECT-TYPE
               SYNTAX      Integer32(0|1)
               MAX-ACCESS  read-write
               STATUS      current
               DESCRIPTION
                   "Controls the unit of measure for the queue policer rate as kbps or Mbps.
                    range:
		    0:kbs
		    1:Mbps
                    default: 0(kbps)"
               ::= {     sm24dp4xaQosQueuePolicingEntry 26 }			   

--
-- =======================================================================================================================
-- Start sm24dp4xaQosPortScheduler group
-- =======================================================================================================================
--sm24dp4xaQosPortSchedulerModeTable

     sm24dp4xaQosPortSchedulerModeTable OBJECT-TYPE
               SYNTAX      SEQUENCE OF     SM24DP4XAQosPortSchedulerModeEntry
               MAX-ACCESS  not-accessible
               STATUS      current
               DESCRIPTION
                   "The basic QoS Port Scheduler Mode settings.
                    INDEX for this table is ifIndex which is
                    equivalent to the panel port number."
               ::= {     sm24dp4xaQosPortScheduler  1 }

    sm24dp4xaQosPortSchedulerModeEntry OBJECT-TYPE
               SYNTAX          SM24DP4XAQosPortSchedulerModeEntry
               MAX-ACCESS  not-accessible
               STATUS      current
               DESCRIPTION
                   "The Qos Port Scheduler Mode entry."
               INDEX    {     ifIndex  }
               ::= {     sm24dp4xaQosPortSchedulerModeTable 1 }

    SM24DP4XAQosPortSchedulerModeEntry             ::= SEQUENCE {
                sm24dp4xaQosSchedulerMode            Integer32,
                sm24dp4xaQosSchedulerShaper          AdminMode,
                sm24dp4xaQosSchedulerShaperRate      Integer32
                }

    sm24dp4xaQosSchedulerMode OBJECT-TYPE
               SYNTAX      Integer32
               MAX-ACCESS  read-write
               STATUS      current
               DESCRIPTION
                   "Controls whether the scheduler mode is Strict Priority or Weighted
                    on this switch port.
                    0:Strict Priority,
		    2: 2 Queues Weighted
		    3: 3 Queues Weighted: only Jaguar2 support
		    4: 4 Queues Weighted: only Jaguar2 support
		    5: 5 Queues Weighted: only Jaguar2 support
                    6: 6 Queues Weighted
		    7: 7 Queues Weighted: only Jaguar2 support
		    8: 8 Queues Weighted: only Jaguar2 support"
               ::= {     sm24dp4xaQosPortSchedulerModeEntry 2 }

    sm24dp4xaQosSchedulerShaper OBJECT-TYPE
               SYNTAX      AdminMode
               MAX-ACCESS  read-write
               STATUS      current
               DESCRIPTION
                   "Controls whether the port shaper is enabled."
               DEFVAL  { disable }
               ::= {     sm24dp4xaQosPortSchedulerModeEntry 3 }

    sm24dp4xaQosSchedulerShaperRate OBJECT-TYPE
               SYNTAX      Integer32
               MAX-ACCESS  read-write
               STATUS      current
               DESCRIPTION
                   "Controls the rate for the port shaper.
                    default: 500 kbps."
               ::= {     sm24dp4xaQosPortSchedulerModeEntry 4 }

--sm24dp4xaQosPortSchedulerTable
    sm24dp4xaQosPortSchedulerTable OBJECT-TYPE
               SYNTAX      SEQUENCE OF     SM24DP4XAQosPortSchedulerEntry
               MAX-ACCESS  not-accessible
               STATUS      current
               DESCRIPTION
                   "Show Qos Port Scheduler.
                    INDEX for this table is ifIndex which is
                    equivalent to the panel port number."
               ::= {     sm24dp4xaQosPortScheduler 2 }

    sm24dp4xaQosPortSchedulerEntry OBJECT-TYPE
               SYNTAX          SM24DP4XAQosPortSchedulerEntry
               MAX-ACCESS  not-accessible
               STATUS      current
               DESCRIPTION
                   "The Qos Port Scheduler Entry."
               INDEX    {     ifIndex,
                              sm24dp4xaQosSchedulerPortQueue}
               ::= {     sm24dp4xaQosPortSchedulerTable 1 }

    SM24DP4XAQosPortSchedulerEntry             ::= SEQUENCE {
                sm24dp4xaQosSchedulerPortQueue                  INTEGER,
                sm24dp4xaQosSchedulerPortQueueShaper            AdminMode,
                sm24dp4xaQosSchedulerPortQueueShaperRate        Integer32,
                sm24dp4xaQosSchedulerPortQueueShaperExcess      AdminMode,
                sm24dp4xaQosSchedulerPortQueueSchedulerWeight   Integer32,
                sm24dp4xaQosSchedulerPortQueueSchedulerPercent  DisplayString
                }

    sm24dp4xaQosSchedulerPortQueue OBJECT-TYPE
               SYNTAX      INTEGER { q0(1),
                                     q1(2),
                                     q2(3),
                                     q3(4),
                                     q4(5),
                                     q5(6),
                                     q6(7),
                                     q7(8) }
               MAX-ACCESS  not-accessible
               STATUS      current
               DESCRIPTION
                   "range: 1-8.
                    Q0: 1, Q1: 2, ..."
               ::= {     sm24dp4xaQosPortSchedulerEntry 2 }

    sm24dp4xaQosSchedulerPortQueueShaper OBJECT-TYPE
               SYNTAX     AdminMode
               MAX-ACCESS  read-write
               STATUS      current
               DESCRIPTION
                   "Qos scheduler admin state."
               DEFVAL  { disable }
               ::= {     sm24dp4xaQosPortSchedulerEntry 3 }

    sm24dp4xaQosSchedulerPortQueueShaperRate OBJECT-TYPE
               SYNTAX      Integer32(100..1000000)
               MAX-ACCESS  read-write
               STATUS      current
               DESCRIPTION
                   "range: 100..1000000 kbps. "
               ::= {     sm24dp4xaQosPortSchedulerEntry 4 }

    sm24dp4xaQosSchedulerPortQueueShaperExcess OBJECT-TYPE
               SYNTAX      AdminMode
               MAX-ACCESS  read-write
               STATUS      current
               DESCRIPTION
                   "admin state sm24dp4xaQosSchedulerPortQueueShaperExcess"
               DEFVAL  { disable }
               ::= {     sm24dp4xaQosPortSchedulerEntry 5 }

    sm24dp4xaQosSchedulerPortQueueSchedulerWeight OBJECT-TYPE
               SYNTAX      Integer32(0..100)
               MAX-ACCESS  read-write
               STATUS      current
               DESCRIPTION
                   "range: 1-100,
                    default: 17.
                    Only use in Q0 - Q5.  Q6 & Q7 show 0"
               ::= {     sm24dp4xaQosPortSchedulerEntry 6 }

    sm24dp4xaQosSchedulerPortQueueSchedulerPercent OBJECT-TYPE
               SYNTAX      DisplayString
               MAX-ACCESS  read-only
               STATUS      current
               DESCRIPTION
                   "Only use in Q0 - Q5. Q6 & Q7 show empty"
               ::= {     sm24dp4xaQosPortSchedulerEntry 7 }
--
-- =======================================================================================================================
-- Start sm24dp4xaQosPortEgressTagRemarking group
-- =======================================================================================================================
--sm24dp4xaQosPortEgressTagRemarkingTable
    sm24dp4xaQosPortEgressTagRemarkingTable OBJECT-TYPE
               SYNTAX      SEQUENCE OF     SM24DP4XAQosPortEgressTagRemarkingEntry
               MAX-ACCESS  not-accessible
               STATUS      current
               DESCRIPTION
                   "The basic QoS Port Egress Tag Remark
                    Configuration settings.
                    INDEX for this table is ifIndex which is
                    equivalent to the panel port number."
               ::= {     sm24dp4xaQosPortEgressTagRemarking  1 }

    sm24dp4xaQosPortEgressTagRemarkingEntry OBJECT-TYPE
               SYNTAX          SM24DP4XAQosPortEgressTagRemarkingEntry
               MAX-ACCESS  not-accessible
               STATUS      current
               DESCRIPTION
                   "The Qos Port Egress Tag Remarking Entry."
               INDEX    {     ifIndex  }
               ::= {     sm24dp4xaQosPortEgressTagRemarkingTable 1 }

    SM24DP4XAQosPortEgressTagRemarkingEntry             ::= SEQUENCE {
                sm24dp4xaQosEgressTagRemarkingMode                    INTEGER
                }

    sm24dp4xaQosEgressTagRemarkingMode OBJECT-TYPE
               SYNTAX      INTEGER { classified(0), default(1), mapped(2) }
               MAX-ACCESS  read-write
               STATUS      current
               DESCRIPTION
                   "the tag remarking mode for this port.
                    0:Classified, Use classified PCP/DEI values.
                    1:Default, Use default PCP/DEI values.
                    2:Mapped, Use mapped versions of QoS class and DP level."
               ::= {     sm24dp4xaQosPortEgressTagRemarkingEntry 2 }

--sm24dp4xaQosPortEgressTagRemarkingDefTable
    sm24dp4xaQosPortEgressTagRemarkingDefTable OBJECT-TYPE
               SYNTAX      SEQUENCE OF     SM24DP4XAQosPortEgressTagRemarkingDefEntry
               MAX-ACCESS  not-accessible
               STATUS      current
               DESCRIPTION
                   "The basic QoS Port Egress Tag Remark
                    Configuration settings.
                    INDEX for this table is ifIndex which is
                    equivalent to the panel port number."
               ::= {     sm24dp4xaQosPortEgressTagRemarking  2 }

    sm24dp4xaQosPortEgressTagRemarkingDefEntry OBJECT-TYPE
               SYNTAX          SM24DP4XAQosPortEgressTagRemarkingDefEntry
               MAX-ACCESS  not-accessible
               STATUS      current
               DESCRIPTION
                   "The oQos Port Egress Tag Remarking Default Entry."
               INDEX    {     ifIndex  }
               ::= {     sm24dp4xaQosPortEgressTagRemarkingDefTable 1 }

    SM24DP4XAQosPortEgressTagRemarkingDefEntry             ::= SEQUENCE {
                sm24dp4xaQosEgressTagRemarkingDefPCP                Integer32,
                sm24dp4xaQosEgressTagRemarkingDefDEI                AdminMode
                }

    sm24dp4xaQosEgressTagRemarkingDefPCP OBJECT-TYPE
               SYNTAX      Integer32(0..7)
               MAX-ACCESS  read-write
               STATUS      current
               DESCRIPTION
                   "Controls the default PCP
                    Range : 0-7"
               ::= {     sm24dp4xaQosPortEgressTagRemarkingDefEntry 2 }

    sm24dp4xaQosEgressTagRemarkingDefDEI OBJECT-TYPE
               SYNTAX      AdminMode
               MAX-ACCESS  read-write
               STATUS      current
               DESCRIPTION
                   "controls the admin state of DEI"
               ::= {     sm24dp4xaQosPortEgressTagRemarkingDefEntry 3 }

--sm24dp4xaQosPortEgressTagRemarkingMapDPTable
--    sm24dp4xaQosPortEgressTagRemarkingMapDPTable OBJECT-TYPE
--               SYNTAX      SEQUENCE OF     SM24DP4XAQosPortEgressTagRemarkingMapDPEntry
--               MAX-ACCESS  not-accessible
--               STATUS      current
--               DESCRIPTION
--                   "Show Qos Port Egress Tag Remarking Map DP.
--                    INDEX for this table is ifIndex which is
--                    equivalent to the panel port number."
--               ::= {     sm24dp4xaQosPortEgressTagRemarking 3 }

--    sm24dp4xaQosPortEgressTagRemarkingMapDPEntry OBJECT-TYPE
--               SYNTAX          SM24DP4XAQosPortEgressTagRemarkingMapDPEntry
--               MAX-ACCESS  not-accessible
--               STATUS      current
--               DESCRIPTION
--                   "The Qos Port Egress Tag Remarking Map DP Entry."
--               INDEX    {     ifIndex,
--                              sm24dp4xaQosPortEgressTagRemarkingClassifiedDPLevel}
--               ::= {     sm24dp4xaQosPortEgressTagRemarkingMapDPTable 1 }

--    SM24DP4XAQosPortEgressTagRemarkingMapDPEntry             ::= SEQUENCE {
--                sm24dp4xaQosPortEgressTagRemarkingClassifiedDPLevel      Integer32,
--                sm24dp4xaQosPortEgressTagRemarkingDPLevel                AdminMode
--                }

--    sm24dp4xaQosPortEgressTagRemarkingClassifiedDPLevel OBJECT-TYPE
--               SYNTAX      Integer32(1..4)
--               MAX-ACCESS  not-accessible
--               STATUS      current
--               DESCRIPTION
--                   "range: 1-4."
--               ::= {     sm24dp4xaQosPortEgressTagRemarkingMapDPEntry 2 }

--    sm24dp4xaQosPortEgressTagRemarkingDPLevel OBJECT-TYPE
--               SYNTAX      AdminMode
--               MAX-ACCESS  read-write
--               STATUS      current
--               DESCRIPTION
--                   "admin state of Tag remark"
--               ::= {     sm24dp4xaQosPortEgressTagRemarkingMapDPEntry 3 }

--sm24dp4xaQosPortEgressTagRemarkingMapTable
    sm24dp4xaQosPortEgressTagRemarkingMapTable OBJECT-TYPE
               SYNTAX      SEQUENCE OF     SM24DP4XAQosPortEgressTagRemarkingMapEntry
               MAX-ACCESS  not-accessible
               STATUS      current
               DESCRIPTION
                   "Show Qos Port Egress Tag Remarking Map.
                    INDEX for this table is ifIndex which is
                    equivalent to the panel port number."
               ::= {     sm24dp4xaQosPortEgressTagRemarking 4 }

    sm24dp4xaQosPortEgressTagRemarkingMapEntry OBJECT-TYPE
               SYNTAX          SM24DP4XAQosPortEgressTagRemarkingMapEntry
               MAX-ACCESS  not-accessible
               STATUS      current
               DESCRIPTION
                   "The Qos Port Egress Tag Remarking Map Entry."
               INDEX    {     ifIndex,
                              sm24dp4xaQosTagRemarkingQoSClass,
                              sm24dp4xaQosTagRemarkingDPLevel  }
               ::= {     sm24dp4xaQosPortEgressTagRemarkingMapTable 1 }

    SM24DP4XAQosPortEgressTagRemarkingMapEntry             ::= SEQUENCE {
                sm24dp4xaQosTagRemarkingQoSClass               INTEGER,
                sm24dp4xaQosTagRemarkingDPLevel                INTEGER,
                sm24dp4xaQosTagRemarkingPCP                    Integer32,
                sm24dp4xaQosTagRemarkingDEI                    Integer32
                }

    sm24dp4xaQosTagRemarkingQoSClass OBJECT-TYPE
               SYNTAX      INTEGER {
                        class0(1),
                        class1(2),
                        class2(3),
                        class3(4),
                        class4(5),
                        class5(6),
                        class6(7),
                        class7(8)
                        }
               MAX-ACCESS  not-accessible
               STATUS      current
               DESCRIPTION
                   "range: 1-8,
                    QoS Class0: 1, QoS Class1: 2..."
               ::= {     sm24dp4xaQosPortEgressTagRemarkingMapEntry 2 }

    sm24dp4xaQosTagRemarkingDPLevel OBJECT-TYPE
               SYNTAX      INTEGER { level0(1), level1(2) }
               MAX-ACCESS  not-accessible
               STATUS      current
               DESCRIPTION
                   "range: 1-2,
                    DP Level0: 1, DP Level1: 2."
               ::= {     sm24dp4xaQosPortEgressTagRemarkingMapEntry 3 }

    sm24dp4xaQosTagRemarkingPCP OBJECT-TYPE
               SYNTAX      Integer32(0..7)
               MAX-ACCESS  read-write
               STATUS      current
               DESCRIPTION
                   "range: 0-7."
               ::= {     sm24dp4xaQosPortEgressTagRemarkingMapEntry 4 }

    sm24dp4xaQosTagRemarkingDEI OBJECT-TYPE
               SYNTAX      Integer32 (0|1)
               MAX-ACCESS  read-write
               STATUS      current
               DESCRIPTION
                   "range: 0-1."
               ::= {     sm24dp4xaQosPortEgressTagRemarkingMapEntry 5 }

--
-- =======================================================================================================================
-- Start sm24dp4xaQosPortDSCP group
-- =======================================================================================================================
--sm24dp4xaQosPortDSCPTable
    sm24dp4xaQosPortDSCPTable OBJECT-TYPE
               SYNTAX      SEQUENCE OF     SM24DP4XAQosPortDSCPEntry
               MAX-ACCESS  not-accessible
               STATUS      current
               DESCRIPTION
                   "The basic QoS Port DSCP Configuration settings.
                    INDEX for this table is ifIndex which is
                    equivalent to the panel port number."
               ::= {     sm24dp4xaQosPortDSCP 1 }

    sm24dp4xaQosPortDSCPEntry OBJECT-TYPE
               SYNTAX          SM24DP4XAQosPortDSCPEntry
               MAX-ACCESS  not-accessible
               STATUS      current
               DESCRIPTION
                   "The Qos Port DSCP Entry."
               INDEX    {     ifIndex  }
               ::= {     sm24dp4xaQosPortDSCPTable 1 }

    SM24DP4XAQosPortDSCPEntry             ::= SEQUENCE {
                sm24dp4xaQosPortDSCPIngressTranslate        AdminMode,
                sm24dp4xaQosPortDSCPIngressClassify         INTEGER,
                sm24dp4xaQosPortDSCPEgressRewrite           INTEGER
                }

    sm24dp4xaQosPortDSCPIngressTranslate OBJECT-TYPE
               SYNTAX      AdminMode
               MAX-ACCESS  read-write
               STATUS      current
               DESCRIPTION
                  "Configure DSCP ingress translation mode."
               DEFVAL  { disable }
               ::= {     sm24dp4xaQosPortDSCPEntry 2 }

    sm24dp4xaQosPortDSCPIngressClassify OBJECT-TYPE
               SYNTAX      INTEGER { disable (0), dscp (1), selected (2), all(3) }
               MAX-ACCESS  read-write
               STATUS      current
               DESCRIPTION
                   "Classification for a port have 4 different values.
                    0: disable,
                    1: DSCP=0,
                    2: Selected,
                    3: All."
               DEFVAL  { disable }
               ::= {     sm24dp4xaQosPortDSCPEntry 3 }

    sm24dp4xaQosPortDSCPEgressRewrite OBJECT-TYPE
               SYNTAX      INTEGER { disable (0),enable (1),
                                     remapDPUnaware (2), remapDPaware (3) }
               MAX-ACCESS  read-write
               STATUS      current
               DESCRIPTION
                   "Configure the port egress rewriting mode.
                    LUTON26:{0: Disable,1: Enable,2: Remap DP Unaware,
                    3: Remap DP Aware,range: 0-3}
                    Others:{0: Disable,1: Enable,2: Remap,range: 0-2}"
               ::= {     sm24dp4xaQosPortDSCPEntry 4 }

--
-- =======================================================================================================================
-- Start sm24dp4xaQosDSCP group
-- =======================================================================================================================
    sm24dp4xaQosDSCPTable OBJECT-TYPE
               SYNTAX      SEQUENCE OF     SM24DP4XAQosDSCPEntry
               MAX-ACCESS  not-accessible
               STATUS      current
               DESCRIPTION
                   "configure the basic QoS DSCP based QoS Ingress
                    Classification settings for all switches."
               ::= {     sm24dp4xaQosDSCP 1 }

    sm24dp4xaQosDSCPEntry OBJECT-TYPE
               SYNTAX          SM24DP4XAQosDSCPEntry
               MAX-ACCESS  not-accessible
               STATUS      current
               DESCRIPTION
                   "The Qos DSCP Entry."
               INDEX    {     sm24dp4xaQosDSCPList  }
               ::= {     sm24dp4xaQosDSCPTable 1 }

    SM24DP4XAQosDSCPEntry             ::= SEQUENCE {
                sm24dp4xaQosDSCPList       Integer32,
                sm24dp4xaQosBasedDSCP      DisplayString,
                sm24dp4xaQosDSCPTrust      AdminMode,
                sm24dp4xaQosDSCPQosClass   Integer32,
                sm24dp4xaQosDSCPDPL        Integer32
                }

    sm24dp4xaQosDSCPList OBJECT-TYPE
               SYNTAX      Integer32(1..64)
               MAX-ACCESS  not-accessible
               STATUS      current
               DESCRIPTION
                  "DSCP mapping table index(1-64)."
               ::= {     sm24dp4xaQosDSCPEntry 1 }

    sm24dp4xaQosBasedDSCP OBJECT-TYPE
               SYNTAX      DisplayString
               MAX-ACCESS  read-only
               STATUS      current
               DESCRIPTION
                  "Maximum number of supported DSCP values are 64."
               ::= {     sm24dp4xaQosDSCPEntry 2 }

    sm24dp4xaQosDSCPTrust OBJECT-TYPE
               SYNTAX      AdminMode
               MAX-ACCESS  read-write
               STATUS      current
               DESCRIPTION
                  "Controls whether a specific DSCP value is trusted. Only frames with
                   trusted DSCP values are mapped to a specific QoS class
                   and Drop Precedence
                   Level. Frames with untrusted DSCP values are
                   treated as a non-IP frame."
               DEFVAL  { disable }
              ::= {     sm24dp4xaQosDSCPEntry 3 }

    sm24dp4xaQosDSCPQosClass OBJECT-TYPE
               SYNTAX      Integer32(0..7)
               MAX-ACCESS  read-write
               STATUS      current
               DESCRIPTION
                  "QoS class.
                   range: 0-7,
                   default: 0."
               ::= {     sm24dp4xaQosDSCPEntry 4 }

    sm24dp4xaQosDSCPDPL OBJECT-TYPE
               SYNTAX      Integer32(0|1)
               MAX-ACCESS  read-write
               STATUS      current
               DESCRIPTION
                  "Drop Precedence Level.
                   range: 0-1,
                   default: 0."
               ::= {     sm24dp4xaQosDSCPEntry 5 }

--
-- =======================================================================================================================
-- Start sm24dp4xaQosDSCPTranslation group
-- =======================================================================================================================
--sm24dp4xaQosDSCPTranslationTable
    sm24dp4xaQosDSCPTranslationTable OBJECT-TYPE
               SYNTAX      SEQUENCE OF     SM24DP4XAQosDSCPTranslationEntry
               MAX-ACCESS  not-accessible
               STATUS      current
               DESCRIPTION
                   "The basic QoS DSCP Translation settings for all switches."
               ::= {     sm24dp4xaQosDSCPTranslation  1 }

    sm24dp4xaQosDSCPTranslationEntry OBJECT-TYPE
               SYNTAX          SM24DP4XAQosDSCPTranslationEntry
               MAX-ACCESS  not-accessible
               STATUS      current
               DESCRIPTION
                   "The Qos DSCP Translation Entry."
               INDEX    {     sm24dp4xaQosDSCPTranslationList  }
               ::= {     sm24dp4xaQosDSCPTranslationTable 1 }

    SM24DP4XAQosDSCPTranslationEntry             ::= SEQUENCE {
                sm24dp4xaQosDSCPTranslationList                 Integer32,
                sm24dp4xaQosDSCPTranslationDSCPBasedId          DisplayString,
                sm24dp4xaQosDSCPTranslationIngressTranslate     Integer32,
                sm24dp4xaQosDSCPTranslationIngressClassify      AdminMode,
                sm24dp4xaQosDSCPTranslationEgressRemapDP0       Integer32,
                sm24dp4xaQosDSCPTranslationEgressRemapDP1       Integer32
                }

    sm24dp4xaQosDSCPTranslationList OBJECT-TYPE
               SYNTAX      Integer32(1..64)
               MAX-ACCESS  not-accessible
               STATUS      current
               DESCRIPTION
                  "DSCP translation table index(1-64)."
               ::= {     sm24dp4xaQosDSCPTranslationEntry 1 }

    sm24dp4xaQosDSCPTranslationDSCPBasedId OBJECT-TYPE
               SYNTAX      DisplayString
               MAX-ACCESS  read-only
               STATUS      current
               DESCRIPTION
                  "Configure global ingress DSCP translation table."
               ::= {     sm24dp4xaQosDSCPTranslationEntry 2 }

    sm24dp4xaQosDSCPTranslationIngressTranslate OBJECT-TYPE
               SYNTAX      Integer32(0..63)
               MAX-ACCESS  read-write
               STATUS      current
               DESCRIPTION
                  "DSCP at Ingress side can be translated to any of DSCP values.
                   range: 0-63,
                   default: 0."
               ::= {     sm24dp4xaQosDSCPTranslationEntry 3 }

    sm24dp4xaQosDSCPTranslationIngressClassify OBJECT-TYPE
               SYNTAX      AdminMode
               MAX-ACCESS  read-write
               STATUS      current
               DESCRIPTION
                  "Configure DSCP ingress classification."
               DEFVAL  { disable }
               ::= {     sm24dp4xaQosDSCPTranslationEntry 4 }

    sm24dp4xaQosDSCPTranslationEgressRemapDP0 OBJECT-TYPE
               SYNTAX      Integer32(0..63)
               MAX-ACCESS  read-write
               STATUS      current
               DESCRIPTION
                  "Select the DSCP value from select menu to which you want to remap.
                   range: 0-63,
                   default: 0."
               ::= {     sm24dp4xaQosDSCPTranslationEntry 5 }

    sm24dp4xaQosDSCPTranslationEgressRemapDP1 OBJECT-TYPE
               SYNTAX      Integer32(0..63)
               MAX-ACCESS  read-write
               STATUS      current
               DESCRIPTION
                  "Select the DSCP value from select menu to which you want to remap.
                   range: 0-63,
                   default: 0.
                   Only support LUTON26."
               ::= {     sm24dp4xaQosDSCPTranslationEntry 6 }

--
-- =======================================================================================================================
-- Start sm24dp4xaQosDSCPClassification group
-- =======================================================================================================================
--sm24dp4xaQosDSCPClassificationTable
    sm24dp4xaQosDSCPClassificationTable OBJECT-TYPE
               SYNTAX      SEQUENCE OF     SM24DP4XAQosDSCPClassificationEntry
               MAX-ACCESS  not-accessible
               STATUS      current
               DESCRIPTION
                   "The mapping of QoS class  to DSCP value."
               ::= {     sm24dp4xaQosDSCPClassification 1 }

    sm24dp4xaQosDSCPClassificationEntry OBJECT-TYPE
               SYNTAX          SM24DP4XAQosDSCPClassificationEntry
               MAX-ACCESS  not-accessible
               STATUS      current
               DESCRIPTION
                   "The Qos DSCP Classification Entry."
               INDEX    {     sm24dp4xaQosDSCPClassificationQoSClass  }
               ::= {     sm24dp4xaQosDSCPClassificationTable 1 }

    SM24DP4XAQosDSCPClassificationEntry             ::= SEQUENCE {
                sm24dp4xaQosDSCPClassificationQoSClass   Integer32,
                sm24dp4xaQosDSCPClassificationDSCPDP0    Integer32,
		sm24dp4xaQosDSCPClassificationDSCPDP1    Integer32,
		sm24dp4xaQosDSCPClassificationDSCPDP2    Integer32,
		sm24dp4xaQosDSCPClassificationDSCPDP3    Integer32
                }

    sm24dp4xaQosDSCPClassificationQoSClass OBJECT-TYPE
               SYNTAX      Integer32(1..8)
               MAX-ACCESS  not-accessible
               STATUS      current
               DESCRIPTION
                  "This page allows you to configure the mapping of QoS class
                   and Drop Precedence Level to DSCP value.
                   range: 1-8}"
               ::= {     sm24dp4xaQosDSCPClassificationEntry 1 }

    sm24dp4xaQosDSCPClassificationDSCPDP0 OBJECT-TYPE
               SYNTAX      Integer32(0..63)
               MAX-ACCESS  read-write
               STATUS      current
               DESCRIPTION
                  "Select the classified DSCP value.
                   range: 0-63,
                   default: 0."
               ::= {     sm24dp4xaQosDSCPClassificationEntry 2 }

    sm24dp4xaQosDSCPClassificationDSCPDP1 OBJECT-TYPE
               SYNTAX      Integer32(0..63)
               MAX-ACCESS  read-write
               STATUS      current
               DESCRIPTION
                  "Select the classified DSCP value.
                   range: 0-63,
                   default: 0."
               ::= {     sm24dp4xaQosDSCPClassificationEntry 3 }

    sm24dp4xaQosDSCPClassificationDSCPDP2 OBJECT-TYPE
               SYNTAX      Integer32(0..63)
               MAX-ACCESS  read-write
               STATUS      current
               DESCRIPTION
                  "Select the classified DSCP value.
                   range: 0-63,
                   default: 0."
               ::= {     sm24dp4xaQosDSCPClassificationEntry 4 }

    sm24dp4xaQosDSCPClassificationDSCPDP3 OBJECT-TYPE
               SYNTAX      Integer32(0..63)
               MAX-ACCESS  read-write
               STATUS      current
               DESCRIPTION
                  "Select the classified DSCP value.
                   range: 0-63,
                   default: 0."
               ::= {     sm24dp4xaQosDSCPClassificationEntry 5 }
			   
--
-- =======================================================================================================================
-- Start sm24dp4xaQosControlList group
-- =======================================================================================================================
--sm24dp4xaQosQceTable

    sm24dp4xaQosQceTable OBJECT-TYPE
               SYNTAX      SEQUENCE OF     SM24DP4XAQosQceEntry
               MAX-ACCESS  not-accessible
               STATUS      current
               DESCRIPTION
                   "Create Qos QCE entry."
               ::= {     sm24dp4xaQosControlList 1 }

    sm24dp4xaQosQceEntry OBJECT-TYPE
               SYNTAX          SM24DP4XAQosQceEntry
               MAX-ACCESS  not-accessible
               STATUS      current
               DESCRIPTION
                   "Qos Qce Entry."
               INDEX    {     sm24dp4xaQosQceIndex  }
               ::= {     sm24dp4xaQosQceTable 1 }

    SM24DP4XAQosQceEntry             ::= SEQUENCE {
                sm24dp4xaQosQceIndex                Integer32,
                sm24dp4xaQosQceID                   Integer32,
                sm24dp4xaQosQceList                 Integer32,
                sm24dp4xaQosQcePortMembersSwitch    Integer32,
                sm24dp4xaQosQcePortMembers          DisplayString,
                sm24dp4xaQosQceTag                  DisplayString,
                sm24dp4xaQosQceVID                  DisplayString,
                sm24dp4xaQosPCP                     DisplayString,
                sm24dp4xaQosDEI                     DisplayString,
                sm24dp4xaQosSMAC                    DisplayString,
                sm24dp4xaQosDMACType                DisplayString,
                sm24dp4xaQosDMACValue               DisplayString,
                sm24dp4xaQosQceInnerTag             DisplayString,
                sm24dp4xaQosQceInnerVID             DisplayString,
                sm24dp4xaQosInnerPCP                DisplayString,
                sm24dp4xaQosInnerDEI                DisplayString,
                sm24dp4xaQosFrameType               INTEGER,
                sm24dp4xaQosMacEtherType            DisplayString,
                sm24dp4xaQosLLCSSAPAddr             DisplayString,
                sm24dp4xaQosLLCDSAPAddr             DisplayString,
                sm24dp4xaQosLLCControl              DisplayString,
                sm24dp4xaQosSNAPPID                 DisplayString,
                sm24dp4xaQosIpv4Protocol            DisplayString,
                sm24dp4xaQosIpv4ProtocolValue       Integer32,
                sm24dp4xaQosIpv4ProtocolUDPSPort    DisplayString,
                sm24dp4xaQosIpv4ProtocolUDPDPort    DisplayString,
                sm24dp4xaQosIpv4ProtocolTCPSPort    DisplayString,
                sm24dp4xaQosIpv4ProtocolTCPDPort    DisplayString,
                sm24dp4xaQosIpv4SourceIp            DisplayString,
                sm24dp4xaQosIpv4SourceMask          DisplayString,
                sm24dp4xaQosIpv4IPFragment          INTEGER,
                sm24dp4xaQosIpv4DSCP                DisplayString,
                sm24dp4xaQosIpv6Protocol            DisplayString,
                sm24dp4xaQosIpv6ProtocolValue       Integer32,
                sm24dp4xaQosIpv6ProtocolUDPSPort    DisplayString,
                sm24dp4xaQosIpv6ProtocolUDPDPort    DisplayString,
                sm24dp4xaQosIpv6ProtocolTCPSPort    DisplayString,
                sm24dp4xaQosIpv6ProtocolTCPDPort    DisplayString,
                sm24dp4xaQosIpv6SourceIp            DisplayString,
                sm24dp4xaQosIpv6SourceMask          DisplayString,
                sm24dp4xaQosIpv6DSCP                DisplayString,
                sm24dp4xaQosActionClass             Integer32,
                sm24dp4xaQosActionDPL               Integer32,
                sm24dp4xaQosActionDSCP              Integer32,
                sm24dp4xaQosActionPCP               Integer32,
                sm24dp4xaQosActionDEI               Integer32,
                sm24dp4xaQosActionPolicy            Integer32,
                sm24dp4xaQosQceRowStatus            RowStatus
                }

    sm24dp4xaQosQceIndex OBJECT-TYPE
               SYNTAX      Integer32(1..256)
               MAX-ACCESS  not-accessible
               STATUS      current
               DESCRIPTION
                   "the index to this table."
               ::= {     sm24dp4xaQosQceEntry 1 }

    sm24dp4xaQosQceID OBJECT-TYPE
               SYNTAX      Integer32(1..256)
               MAX-ACCESS  read-only
               STATUS      current
               DESCRIPTION
                   "If the QCE ID is specified and an entry with this QCE ID
                    already exists, the QCE will be modified. Otherwise, a
                    new QCE will be added.
                    range : 1 - 256."
               ::= {     sm24dp4xaQosQceEntry 2 }

    sm24dp4xaQosQceList OBJECT-TYPE
               SYNTAX      Integer32(0..256)
               MAX-ACCESS  read-create
               STATUS      current
               DESCRIPTION
                   "If the QCE List is non zero, the QCE will be placed in the list.
                    If the QCE List is zero, the QCE will be placed last in the list.
                    range : 0 - 256."
               ::= {     sm24dp4xaQosQceEntry 3 }

    sm24dp4xaQosQcePortMembersSwitch OBJECT-TYPE
               SYNTAX      Integer32
               MAX-ACCESS  read-create
               STATUS      current
               DESCRIPTION
                   "Switch number for port members.
                   -1:Any.
                   Only support stacking switch."
               ::= {     sm24dp4xaQosQceEntry 4 }

    sm24dp4xaQosQcePortMembers OBJECT-TYPE
               SYNTAX      DisplayString
               MAX-ACCESS  read-create
               STATUS      current
               DESCRIPTION
                   "Indicates the ingress port of the QCE. Possible values are:
                    All: The QCE will match all ingress port.
                    Port: The QCE will match a specific ingress port.Format: 1,3-6."
               ::= {     sm24dp4xaQosQceEntry 5 }

    sm24dp4xaQosQceTag OBJECT-TYPE
               SYNTAX      DisplayString
               MAX-ACCESS  read-create
               STATUS      current
               DESCRIPTION
                  "SERVAL:{'Any', 'Untag' or 'Tag' or 'cTag' or 'sTag'}.
                   Others:{'Any', 'Untag' or 'Tag'}."
               ::= {     sm24dp4xaQosQceEntry 6 }

    sm24dp4xaQosQceVID OBJECT-TYPE
               SYNTAX      DisplayString
               MAX-ACCESS  read-create
               STATUS      current
               DESCRIPTION
                   "Valid value of VLAN ID can be any value in
                   'Specific 1~4095' or 'range 1-4095' or 'Any'."
               ::= {     sm24dp4xaQosQceEntry 7 }

    sm24dp4xaQosPCP OBJECT-TYPE
               SYNTAX      DisplayString
               MAX-ACCESS  read-create
               STATUS      current
               DESCRIPTION
                   "Priority Code Point: Valid value PCP are
                    specific(0, 1, 2, 3, 4, 5, 6, 7)
                    or range(0-1, 2-3, 4-5, 6-7, 0-3, 4-7) or 'Any'."
               ::= {     sm24dp4xaQosQceEntry 8 }

    sm24dp4xaQosDEI OBJECT-TYPE
               SYNTAX      DisplayString
               MAX-ACCESS  read-create
               STATUS      current
               DESCRIPTION
                   "Drop Eligible Indicator: Valid value of DEI can be
                    any of values between 0, 1 or 'Any'."
               ::= {     sm24dp4xaQosQceEntry 9 }

    sm24dp4xaQosSMAC  OBJECT-TYPE
               SYNTAX      DisplayString
               MAX-ACCESS  read-create
               STATUS      current
               DESCRIPTION
                   "JAGUAR:{Source MAC address: 24 MS bits OUI(00-00-00
                    ~ FF-FF-FF) or 'Any'.}
                    Others:{Source MAC address:  xx-xx-xx-xx-xx-xx or
                    'Any'.}"
               ::= {     sm24dp4xaQosQceEntry 10 }

    sm24dp4xaQosDMACType OBJECT-TYPE
               SYNTAX      DisplayString
               MAX-ACCESS  read-create
               STATUS      current
               DESCRIPTION
                   "Destination MAC type: possible values are 'UC'(unicast),
                    'MC'(multicast), 'BC'(broadcast) or 'Any'.
                    'SP' only support SERVAL version."
               ::= {     sm24dp4xaQosQceEntry 11 }

    sm24dp4xaQosDMACValue OBJECT-TYPE
               SYNTAX      DisplayString
               MAX-ACCESS  read-create
               STATUS      current
               DESCRIPTION
                   "when sm24dp4xaQosDMACType is 'SP'(specific) can set mac address.
                    Only support SERVAL version."
               ::= {     sm24dp4xaQosQceEntry 12 }

    sm24dp4xaQosQceInnerTag OBJECT-TYPE
               SYNTAX      DisplayString
               MAX-ACCESS  read-create
               STATUS      current
               DESCRIPTION
                   "Value of Inner Tag field can be 'Any', 'Untag' or 'Tag' or
                    'cTag' or 'sTag'.
                    Only support SERVAL version."
               ::= {     sm24dp4xaQosQceEntry 13 }

    sm24dp4xaQosQceInnerVID OBJECT-TYPE
               SYNTAX      DisplayString
               MAX-ACCESS  read-create
               STATUS      current
               DESCRIPTION
                   "Valid value of Inner VLAN ID can be any value in
                    'Specific 1~4095' or 'range 1-4095' or 'Any'.
                    Only support SERVAL version."
               ::= {     sm24dp4xaQosQceEntry 14 }

    sm24dp4xaQosInnerPCP OBJECT-TYPE
               SYNTAX      DisplayString
               MAX-ACCESS  read-create
               STATUS      current
               DESCRIPTION
                   "Valid value Inner PCP are specific(0, 1, 2, 3, 4, 5, 6, 7)
                    or range(0-1, 2-3, 4-5, 6-7, 0-3, 4-7) or 'Any'.
                    Only support SERVAL version."
               ::= {     sm24dp4xaQosQceEntry 15 }

    sm24dp4xaQosInnerDEI OBJECT-TYPE
               SYNTAX      DisplayString
               MAX-ACCESS  read-create
               STATUS      current
               DESCRIPTION
                   "Valid value of Inner DEI can be any of values between
                    0, 1 or 'Any'.
                    Only support SERVAL version."
               ::= {     sm24dp4xaQosQceEntry 16 }

    sm24dp4xaQosFrameType OBJECT-TYPE
               SYNTAX      INTEGER {
                            any(1),
                            ethernet(2),
                            llc(3),
                            snap(4),
                            ipv4(5),
                            ipv6(6)
                           }
               MAX-ACCESS  read-create
               STATUS      current
               DESCRIPTION
                   "Frame Type can have any of the following values:
                    1: Any,
                    2: Ethernet,
                    3: LLC,
                    4: SNAP,
                    5: IPv4,
                    6: IPv6."
               ::= {     sm24dp4xaQosQceEntry 17 }

    sm24dp4xaQosMacEtherType OBJECT-TYPE
               SYNTAX      DisplayString
               MAX-ACCESS  read-create
               STATUS      current
               DESCRIPTION
                   "Valid ethernet type can have a value within 0x600-0xFFFF or 'Any' ,
                    but excluding 0x800(IPv4) and 0x86DD(IPv6),
                    range: 0000-FFFF,
                    default: Any."
               ::= {     sm24dp4xaQosQceEntry 18 }

    sm24dp4xaQosLLCSSAPAddr OBJECT-TYPE
               SYNTAX      DisplayString
               MAX-ACCESS  read-create
               STATUS      current
               DESCRIPTION
                   "Valid SSAP(Source Service Access Point) can vary from
                    0x00 to 0xFF or 'Any',
                    range: 00-FF,
                    default: Any."
               ::= {     sm24dp4xaQosQceEntry 19 }

    sm24dp4xaQosLLCDSAPAddr OBJECT-TYPE
               SYNTAX      DisplayString
               MAX-ACCESS  read-create
               STATUS      current
               DESCRIPTION
                   "Valid DSAP(Destination Service Access Point) can
                    vary from 0x00 to 0xFF or 'Any',
                    range: 00-FF,
                    default: Any."
               ::= {     sm24dp4xaQosQceEntry 20 }

    sm24dp4xaQosLLCControl OBJECT-TYPE
               SYNTAX      DisplayString
               MAX-ACCESS  read-create
               STATUS      current
               DESCRIPTION
                   "Valid Control field can vary from 0x00 to 0xFF or 'Any',
                    range: 00-FF,
                    default: Any."
               ::= {     sm24dp4xaQosQceEntry 21 }

    sm24dp4xaQosSNAPPID OBJECT-TYPE
               SYNTAX      DisplayString
               MAX-ACCESS  read-create
               STATUS      current
               DESCRIPTION
                   "Valid PID(a.k.a ethernet type) can have value within
                    0x00-0xFFFF or 'Any',
                    range: 0000-FFFF,
                    default: Any."
               ::= {     sm24dp4xaQosQceEntry 22 }

   sm24dp4xaQosIpv4Protocol OBJECT-TYPE
               SYNTAX      DisplayString
               MAX-ACCESS  read-create
               STATUS      current
               DESCRIPTION
                   "IP protocol number: (Other, TCP or UDP) or 'Any'."
               ::= {     sm24dp4xaQosQceEntry 23 }

    sm24dp4xaQosIpv4ProtocolValue  OBJECT-TYPE
               SYNTAX      Integer32(0..255)
               MAX-ACCESS  read-create
               STATUS      current
               DESCRIPTION
                   "Ipv4 Protocol is Other.
                    range: 0-255
                    default: 0."
               ::= {     sm24dp4xaQosQceEntry 24 }

    sm24dp4xaQosIpv4ProtocolUDPSPort OBJECT-TYPE
               SYNTAX      DisplayString
               MAX-ACCESS  read-create
               STATUS      current
               DESCRIPTION
                   "Source  TCP/UDP Port:(0-65535) or 'Any',
                    specific or port range applicable for IP protocol UDP/TCP."
               ::= {     sm24dp4xaQosQceEntry 25 }

    sm24dp4xaQosIpv4ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sm24dp4xaQosQceEntry 26 }

    sm24dp4xaQosIpv4ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sm24dp4xaQosQceEntry 27 }

    sm24dp4xaQosIpv4ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sm24dp4xaQosQceEntry 28 }

    sm24dp4xaQosIpv4SourceIp OBJECT-TYPE
               SYNTAX      DisplayString
               MAX-ACCESS  read-create
               STATUS      current
               DESCRIPTION
                   "Specific Source IP address in value format or value 0.0.0.0 is 'Any'.
                    if Ipv4 Mask value 0.0.0.0 is 'Any' ,IP address value also is 'Any'.
                    (x.y.z.w),x=0 unless y.z.w also 0,x not is 127 or greater than 223."
               ::= {     sm24dp4xaQosQceEntry 29 }

    sm24dp4xaQosIpv4SourceMask OBJECT-TYPE
               SYNTAX      DisplayString
               MAX-ACCESS  read-create
               STATUS      current
               DESCRIPTION
                   "Specific Source IP address in mask format or value 0.0.0.0 is 'Any'."
               ::= {     sm24dp4xaQosQceEntry 30 }

    sm24dp4xaQosIpv4IPFragment OBJECT-TYPE
               SYNTAX      INTEGER { any(0), no(1), yes(2) }
               MAX-ACCESS  read-create
               STATUS      current
               DESCRIPTION
                   "IPv4 frame fragmented option:
                    2: yes,
                    1: no,
                    0: any."
               ::= {     sm24dp4xaQosQceEntry 31 }

    sm24dp4xaQosIpv4DSCP OBJECT-TYPE
               SYNTAX      DisplayString
               MAX-ACCESS  read-create
               STATUS      current
               DESCRIPTION
                   "Diffserv Code Point value (DSCP): It can be a specific value,
                    range of values or 'Any'. DSCP values are in the range 0-63."
               ::= {     sm24dp4xaQosQceEntry 32 }

    sm24dp4xaQosIpv6Protocol OBJECT-TYPE
               SYNTAX      DisplayString
               MAX-ACCESS  read-create
               STATUS      current
               DESCRIPTION
                   "IP protocol number: (Other, TCP or UDP) or 'Any'."
               ::= {     sm24dp4xaQosQceEntry 33 }

    sm24dp4xaQosIpv6ProtocolValue OBJECT-TYPE
               SYNTAX      Integer32(0..255)
               MAX-ACCESS  read-create
               STATUS      current
               DESCRIPTION
                   "when IPv6 protocol is Other ,
                    range: 0-255."
               ::= {     sm24dp4xaQosQceEntry 34 }

    sm24dp4xaQosIpv6ProtocolUDPSPort OBJECT-TYPE
               SYNTAX      DisplayString
               MAX-ACCESS  read-create
               STATUS      current
               DESCRIPTION
                   "Source TCP/UDP port:(0-65535) or 'Any',
                    specific or port range applicable for IP protocol UDP/TCP."
               ::= {     sm24dp4xaQosQceEntry 35 }

    sm24dp4xaQosIpv6ProtocolUDPDPort OBJECT-TYPE
               SYNTAX      DisplayString
               MAX-ACCESS  read-create
               STATUS      current
               DESCRIPTION
                   "Destination TCP/UDP port:(0-65535) or 'Any',
                    specific or port range applicable for IP protocol UDP/TCP."
               ::= {     sm24dp4xaQosQceEntry 36 }

    sm24dp4xaQosIpv6ProtocolTCPSPort OBJECT-TYPE
               SYNTAX      DisplayString
               MAX-ACCESS  read-create
               STATUS      current
               DESCRIPTION
                   "Source TCP/UDP port:(0-65535) or 'Any',
                    specific or port range applicable for IP protocol UDP/TCP."
               ::= {     sm24dp4xaQosQceEntry 37 }


    sm24dp4xaQosIpv6ProtocolTCPDPort OBJECT-TYPE
               SYNTAX      DisplayString
               MAX-ACCESS  read-create
               STATUS      current
               DESCRIPTION
                   "Destination TCP/UDP port:(0-65535) or 'Any',
                    specific or port range applicable for IP protocol UDP/TCP."
               ::= {     sm24dp4xaQosQceEntry 38 }

    sm24dp4xaQosIpv6SourceIp OBJECT-TYPE
               SYNTAX      DisplayString
               MAX-ACCESS  read-create
               STATUS      current
               DESCRIPTION
                   "IPv6 source address: (a.b.c.d) or value 0.0.0.0 is 'Any', 32 LS bits."
               ::= {     sm24dp4xaQosQceEntry 39 }

    sm24dp4xaQosIpv6SourceMask OBJECT-TYPE
               SYNTAX      DisplayString
               MAX-ACCESS  read-create
               STATUS      current
               DESCRIPTION
                   "IPv6 mask address: (a.b.c.d) or value 0.0.0.0 is 'Any', 32 LS bits."
               ::= {     sm24dp4xaQosQceEntry 40 }

    sm24dp4xaQosIpv6DSCP OBJECT-TYPE
               SYNTAX      DisplayString
               MAX-ACCESS  read-create
               STATUS      current
               DESCRIPTION
                   "Diffserv Code Point value (DSCP): It can be a specific value,
                    range of values or 'Any'. DSCP values are in the
                    range 0-63 including BE,
                    CS1-CS7, EF or AF11-AF43."
               ::= {     sm24dp4xaQosQceEntry 41 }

    sm24dp4xaQosActionClass  OBJECT-TYPE
               SYNTAX      Integer32(0..8)
               MAX-ACCESS  read-create
               STATUS      current
               DESCRIPTION
                   "QoS class: (0-7) or 8: Default."
               ::= {     sm24dp4xaQosQceEntry 42 }

    sm24dp4xaQosActionDPL OBJECT-TYPE
               SYNTAX      Integer32 (0..4)
               MAX-ACCESS  read-create
               STATUS      current
               DESCRIPTION
                   "JAGUAR:{range:0-4. 4: Default}
                    Others:{range:0-2. 2: Default}."
               ::= {     sm24dp4xaQosQceEntry 43 }

    sm24dp4xaQosActionDSCP OBJECT-TYPE
               SYNTAX      Integer32(0..64)
               MAX-ACCESS  read-create
               STATUS      current
               DESCRIPTION
                   "Valid DSCP value can be (0-63, BE, CS1-CS7,
                    EF or AF11-AF43) or 64: Default."
               ::= {     sm24dp4xaQosQceEntry 44 }

    sm24dp4xaQosActionPCP  OBJECT-TYPE
               SYNTAX      Integer32(0..8)
               MAX-ACCESS  read-create
               STATUS      current
               DESCRIPTION
                   "pcp: (0-7) or 8: Default.
                    Only support SERVAL version."
               ::= {     sm24dp4xaQosQceEntry 45 }

    sm24dp4xaQosActionDEI OBJECT-TYPE
               SYNTAX      Integer32 (0..2)
               MAX-ACCESS  read-create
               STATUS      current
               DESCRIPTION
                   "dei: (0-1) or 2: Default.
                    Only support SERVAL version."
               ::= {     sm24dp4xaQosQceEntry 46 }

    sm24dp4xaQosActionPolicy OBJECT-TYPE
               SYNTAX      Integer32(0..64)
               MAX-ACCESS  read-create
               STATUS      current
               DESCRIPTION
                   "ACL Policy number: (0-63) or 'empty' (64 field). Default: empty.
                    Only support SERVAL version."
               ::= {     sm24dp4xaQosQceEntry 47 }

    sm24dp4xaQosQceRowStatus OBJECT-TYPE
               SYNTAX      RowStatus
               MAX-ACCESS  read-create
               STATUS      current
               DESCRIPTION
                   "This object indicates the status of this entry, and is used
                   to create/delete entries.  Any object in an entry of this table
                   may be modified while the value of the corresponding instance
                   of this object is active(1).
                   createAndGo, notReady not supported."
               ::= {     sm24dp4xaQosQceEntry 48 }

--
-- =======================================================================================================================
-- Start  sm24dp4xaQosStormControl group
-- =======================================================================================================================
--sm24dp4xaQosStormControlTable
    sm24dp4xaQosStormControlTable OBJECT-TYPE
               SYNTAX      SEQUENCE OF     SM24DP4XAQosStormControlEntry
               MAX-ACCESS  not-accessible
               STATUS      current
               DESCRIPTION
                   "The basic QoS DSCP Translation settings for all switches."
               ::= {     sm24dp4xaQosStormControl  1 }

    sm24dp4xaQosStormControlEntry OBJECT-TYPE
               SYNTAX          SM24DP4XAQosStormControlEntry
               MAX-ACCESS  not-accessible
               STATUS      current
               DESCRIPTION
                   "The Qos Storm Control Entry."
               INDEX    {     sm24dp4xaQosStormControlFrameType  }
               ::= {     sm24dp4xaQosStormControlTable 1 }

    SM24DP4XAQosStormControlEntry             ::= SEQUENCE {
                sm24dp4xaQosStormControlFrameType        INTEGER,
                sm24dp4xaQosStormControlEnabled          AdminMode,
                sm24dp4xaQosStormControlRate             Integer32,
		sm24dp4xaQosStormControlUnit             Integer32
                }

    sm24dp4xaQosStormControlFrameType OBJECT-TYPE
               SYNTAX      INTEGER { unicast(1), multicast (2), broadcast (3)}
               MAX-ACCESS  not-accessible
               STATUS      current
               DESCRIPTION
                   "The settings in a particular row apply to the frame type listed here.
                    1:Unicast,
                    2:Multicast,
                    3:Broadcast."
               ::= {     sm24dp4xaQosStormControlEntry 1 }

    sm24dp4xaQosStormControlEnabled OBJECT-TYPE
               SYNTAX      AdminMode
               MAX-ACCESS  read-write
               STATUS      current
               DESCRIPTION
                  "Enable or disable the global storm policer for the given frame type."
               ::= {     sm24dp4xaQosStormControlEntry 2 }

    sm24dp4xaQosStormControlRate OBJECT-TYPE
               SYNTAX      Integer32
               MAX-ACCESS  read-write
               STATUS      current
               DESCRIPTION
                   "Controls the rate for the global storm policer."
               ::= {     sm24dp4xaQosStormControlEntry 3 }
			   
    sm24dp4xaQosStormControlUnit OBJECT-TYPE
               SYNTAX      Integer32
               MAX-ACCESS  read-write
               STATUS      current
               DESCRIPTION
                   "Controls the unit of measure for the global storm policer rate as fps or kfps.
		   0: kbps
		   1: Mbps				   
	           2: fps
                   3: kbps"				   
               ::= {     sm24dp4xaQosStormControlEntry 4 }			   

--
-- =======================================================================================================================
-- Start  sm24dp4xaQosPortStormControl group
-- =======================================================================================================================
--sm24dp4xaQosPortStormControlTable
    sm24dp4xaQosPortStormControlTable OBJECT-TYPE
               SYNTAX      SEQUENCE OF     SM24DP4XAQosPortStormControlEntry
               MAX-ACCESS  not-accessible
               STATUS      current
               DESCRIPTION
                   "Configure the storm control settings.
                    INDEX for this table is ifIndex which is
                    equivalent to the panel port number."
               ::= {     sm24dp4xaQosPortStormControl  1 }

    sm24dp4xaQosPortStormControlEntry OBJECT-TYPE
               SYNTAX      SM24DP4XAQosPortStormControlEntry
               MAX-ACCESS  not-accessible
               STATUS      current
               DESCRIPTION
                   "The Qos Port Storm Control Entry."
               INDEX    {     ifIndex  }
               ::= {     sm24dp4xaQosPortStormControlTable 1 }

    SM24DP4XAQosPortStormControlEntry             ::= SEQUENCE {
                sm24dp4xaQosPortStormControlUnicastEnabled   AdminMode,
                sm24dp4xaQosPortStormControlUnicastRate      Integer32,
                sm24dp4xaQosPortStormControlUnicastUnit      Integer32,
                sm24dp4xaQosPortStormControlBroadcastEnabled AdminMode,
                sm24dp4xaQosPortStormControlBroadcastRate    Integer32,
                sm24dp4xaQosPortStormControlBroadcastUnit    Integer32,
                sm24dp4xaQosPortStormControlUnknownEnabled   AdminMode,
                sm24dp4xaQosPortStormControlUnknownRate      Integer32,
                sm24dp4xaQosPortStormControlUnknownUnit      Integer32
                }

     sm24dp4xaQosPortStormControlUnicastEnabled OBJECT-TYPE
               SYNTAX      AdminMode
               MAX-ACCESS  read-write
               STATUS      current
               DESCRIPTION
                  "Controls whether the storm control is enabled on this
                   switch port."
               ::= {     sm24dp4xaQosPortStormControlEntry 2 }

    sm24dp4xaQosPortStormControlUnicastRate OBJECT-TYPE
               SYNTAX      Integer32
               MAX-ACCESS  read-write
               STATUS      current
               DESCRIPTION
                   "Controls the rate for the storm control."
               ::= {     sm24dp4xaQosPortStormControlEntry 3 }

    sm24dp4xaQosPortStormControlUnicastUnit OBJECT-TYPE
               SYNTAX      Integer32
               MAX-ACCESS  read-write
               STATUS      current
               DESCRIPTION
                   "Controls the unit of measure for the storm control rate.
		   0: kbps
		   1: Mbps				   
		   2: fps
                   3: kbps"
               ::= {     sm24dp4xaQosPortStormControlEntry 4 }

     sm24dp4xaQosPortStormControlBroadcastEnabled  OBJECT-TYPE
               SYNTAX      AdminMode
               MAX-ACCESS  read-write
               STATUS      current
               DESCRIPTION
                  "Controls whether the storm control is enabled on this
                   switch port."
               ::= {     sm24dp4xaQosPortStormControlEntry 5 }

    sm24dp4xaQosPortStormControlBroadcastRate OBJECT-TYPE
               SYNTAX      Integer32
               MAX-ACCESS  read-write
               STATUS      current
               DESCRIPTION
                   "Controls the rate for the storm control."
               ::= {     sm24dp4xaQosPortStormControlEntry 6 }

    sm24dp4xaQosPortStormControlBroadcastUnit OBJECT-TYPE
               SYNTAX      Integer32
               MAX-ACCESS  read-write
               STATUS      current
               DESCRIPTION
                   "Controls the unit of measure for the storm control rate.
		   0: kbps
		   1: Mbps				   
	           2: fps
                   3: kbps"
               ::= {     sm24dp4xaQosPortStormControlEntry 7 }

    sm24dp4xaQosPortStormControlUnknownEnabled  OBJECT-TYPE
               SYNTAX      AdminMode
               MAX-ACCESS  read-write
               STATUS      current
               DESCRIPTION
                  "Controls whether the storm control is enabled on this
                   switch port."
               ::= {     sm24dp4xaQosPortStormControlEntry 8 }

    sm24dp4xaQosPortStormControlUnknownRate OBJECT-TYPE
               SYNTAX      Integer32
               MAX-ACCESS  read-write
               STATUS      current
               DESCRIPTION
                   "Controls the rate for the storm control."
               ::= {     sm24dp4xaQosPortStormControlEntry 9 }

    sm24dp4xaQosPortStormControlUnknownUnit OBJECT-TYPE
               SYNTAX      Integer32
               MAX-ACCESS  read-write
               STATUS      current
               DESCRIPTION
                   "Controls the unit of measure for the storm control rate.
		   0: kbps
		   1: Mbps				   
	           2: fps
                   3: kbps"
               ::= {     sm24dp4xaQosPortStormControlEntry 10 }

--
-- =======================================================================================================================
-- Start  sm24dp4xaQosWRED group
-- =======================================================================================================================
--sm24dp4xaQosWREDTable
    sm24dp4xaQosWREDTable OBJECT-TYPE
               SYNTAX      SEQUENCE OF     SM24DP4XAQosWREDEntry
               MAX-ACCESS  not-accessible
               STATUS      current
               DESCRIPTION
                   "The basic QoS DSCP Translation settings for all switches."
               ::= {     sm24dp4xaQosWRED  1 }

    sm24dp4xaQosWREDEntry OBJECT-TYPE
               SYNTAX          SM24DP4XAQosWREDEntry
               MAX-ACCESS  not-accessible
               STATUS      current
               DESCRIPTION
                   "The Qos WRED Entry."
               INDEX    {     sm24dp4xaQosWREDQueue  }
               ::= {     sm24dp4xaQosWREDTable 1 }

    SM24DP4XAQosWREDEntry             ::= SEQUENCE {
                sm24dp4xaQosWREDQueue           Integer32,
                sm24dp4xaQosWREDEnable          AdminMode,
                sm24dp4xaQosWREDMinThreshold    Integer32,
                sm24dp4xaQosWREDMaxDP1          Integer32,
                sm24dp4xaQosWREDMaxDP2          Integer32,
                sm24dp4xaQosWREDMaxDP3          Integer32
                }

    sm24dp4xaQosWREDQueue OBJECT-TYPE
               SYNTAX      Integer32(1..65535)
               MAX-ACCESS  not-accessible
               STATUS      current
               DESCRIPTION
                   "The queue number (QoS class) for which the configuration
                    below applies."
               ::= {     sm24dp4xaQosWREDEntry 2 }

    sm24dp4xaQosWREDEnable OBJECT-TYPE
               SYNTAX      AdminMode
               MAX-ACCESS  read-write
               STATUS      current
               DESCRIPTION
                  "Controls whether RED is enabled for this queue.
                  "
               DEFVAL  { disable }
               ::= {     sm24dp4xaQosWREDEntry 4 }

    sm24dp4xaQosWREDMinThreshold OBJECT-TYPE
               SYNTAX      Integer32(0..100)
               MAX-ACCESS  read-write
               STATUS      current
               DESCRIPTION
                   "Controls the lower RED fill level threshold. If the queue filling
                    level is below this threshold, the drop probability is zero.
                    range:0-100%,
                    default: 0.
                  "
               ::= {     sm24dp4xaQosWREDEntry 5 }

    sm24dp4xaQosWREDMaxDP1 OBJECT-TYPE
               SYNTAX      Integer32(0..100)
               MAX-ACCESS  read-write
               STATUS      current
               DESCRIPTION
                   "Controls the drop probability for frames marked with Drop
                    Precedence Level 1 when the average queue filling level is
                    100%.
                    range: 0-100."
               ::= {     sm24dp4xaQosWREDEntry 6 }

    sm24dp4xaQosWREDMaxDP2 OBJECT-TYPE
               SYNTAX      Integer32(0..100)
               MAX-ACCESS  read-write
               STATUS      current
               DESCRIPTION
                   "Controls the drop probability for frames marked with Drop
                    Precedence Level 2 when the average queue filling level is
                    100%.
                    range: 0-100."
               ::= {     sm24dp4xaQosWREDEntry 7 }

    sm24dp4xaQosWREDMaxDP3 OBJECT-TYPE
               SYNTAX      Integer32(0..100)
               MAX-ACCESS  read-write
               STATUS      current
               DESCRIPTION
                   "Controls the drop probability for frames marked with Drop
                   Precedence Level 3 when the average queue filling level is
                    100%.
                    range: 0-100."
               ::= {     sm24dp4xaQosWREDEntry 8 }

--
-- =======================================================================================================================
-- Start  sm24dp4xaQosQCLStatus
-- =======================================================================================================================

--sm24dp4xaQosQCLStatusTable
    sm24dp4xaQosQCLStatusTable OBJECT-TYPE
               SYNTAX      SEQUENCE OF     SM24DP4XAQosQCLStatusEntry
               MAX-ACCESS  not-accessible
               STATUS      current
               DESCRIPTION
                   "The basic QoS DSCP Translation settings for all switches."
               ::= {     sm24dp4xaQosQCLStatus 1 }

    sm24dp4xaQosQCLStatusEntry OBJECT-TYPE
               SYNTAX          SM24DP4XAQosQCLStatusEntry
               MAX-ACCESS  not-accessible
               STATUS      current
               DESCRIPTION
                   "The Qos QCL Status Entry."
               INDEX    {     sm24dp4xaQosQCLStatusList  }
               ::= {     sm24dp4xaQosQCLStatusTable 1 }

    SM24DP4XAQosQCLStatusEntry             ::= SEQUENCE {
                sm24dp4xaQosQCLStatusList               Integer32,
                sm24dp4xaQosQCLStatusUser               DisplayString,
                sm24dp4xaQosQCLStatusQCEId              DisplayString,
                sm24dp4xaQosQCLStatusFrameType          DisplayString,
                sm24dp4xaQosQCLStatusPortlist           DisplayString,
                sm24dp4xaQosQCLStatusActionClass        DisplayString,
                sm24dp4xaQosQCLStatusActionDPL          DisplayString,
                sm24dp4xaQosQCLStatusActionDSCP         DisplayString,
                sm24dp4xaQosQCLStatusActionPCP          DisplayString,
                sm24dp4xaQosQCLStatusActionDEL          DisplayString,
                sm24dp4xaQosQCLStatusActionPolicy       DisplayString,
                sm24dp4xaQosQCLStatusConflict           DisplayString,
		sm24dp4xaQosQCLStatusSwitch             Integer32,
		sm24dp4xaQosQCLStatusDMAC               DisplayString,
		sm24dp4xaQosQCLStatusSMAC               DisplayString,
		sm24dp4xaQosQCLStatusTag                DisplayString,
		sm24dp4xaQosQCLStatusVID                DisplayString,
		sm24dp4xaQosQCLStatusPCP                DisplayString,
		sm24dp4xaQosQCLStatusDEI                DisplayString
                }

    sm24dp4xaQosQCLStatusList OBJECT-TYPE
               SYNTAX      Integer32(1..4095)
               MAX-ACCESS  not-accessible
               STATUS      current
               DESCRIPTION
                   "QCL table index."
               ::= {     sm24dp4xaQosQCLStatusEntry 1}

    sm24dp4xaQosQCLStatusUser OBJECT-TYPE
               SYNTAX      DisplayString
               MAX-ACCESS  read-only
               STATUS      current
               DESCRIPTION
                   "Indicates the QCL user."
               ::= {     sm24dp4xaQosQCLStatusEntry 2 }

    sm24dp4xaQosQCLStatusQCEId OBJECT-TYPE
               SYNTAX      DisplayString
               MAX-ACCESS  read-only
               STATUS      current
               DESCRIPTION
                  "Indicates the index of QCE."
               ::= {     sm24dp4xaQosQCLStatusEntry 3}

    sm24dp4xaQosQCLStatusFrameType OBJECT-TYPE
               SYNTAX      DisplayString
               MAX-ACCESS  read-only
               STATUS      current
               DESCRIPTION
                   "Indicates the type of frame to look for incomming frames.
                    Any: The QCE will match all frame type.
                    Ethernet: Only Ethernet frames (with Ether Type 0x600-0xFFFF)
                    are allowed.
                    LLC: Only (LLC) frames are allowed.
                    SNAP: Only (SNAP) frames are allowed.
                    IPv4: The QCE will match only IPV4 frames.
                    IPv6: The QCE will match only IPV6 frames."
               ::= {     sm24dp4xaQosQCLStatusEntry 4}

    sm24dp4xaQosQCLStatusPortlist OBJECT-TYPE
               SYNTAX      DisplayString
               MAX-ACCESS  read-only
               STATUS      current
               DESCRIPTION
                   "Indicates the list of ports configured with the QCE."
               ::= {     sm24dp4xaQosQCLStatusEntry 5}

    sm24dp4xaQosQCLStatusActionClass OBJECT-TYPE
               SYNTAX      DisplayString
               MAX-ACCESS  read-only
               STATUS      current
               DESCRIPTION
                   "Classified QoS class; if a frame matches the
                    QCE it will be put in the  queue."
               ::= {     sm24dp4xaQosQCLStatusEntry 6}

    sm24dp4xaQosQCLStatusActionDPL OBJECT-TYPE
               SYNTAX      DisplayString
               MAX-ACCESS  read-only
               STATUS      current
               DESCRIPTION
                   "Drop Precedence Level; if a frame matches the QCE then
                    DP level will set to value displayed under DPL column."
               ::= {     sm24dp4xaQosQCLStatusEntry 7}

    sm24dp4xaQosQCLStatusActionDSCP OBJECT-TYPE
               SYNTAX      DisplayString
               MAX-ACCESS  read-only
               STATUS      current
               DESCRIPTION
                   "If a frame matches the QCE then DSCP will be
                    classified with the value
                    displayed under DSCP column."
               ::= {     sm24dp4xaQosQCLStatusEntry 8}

    sm24dp4xaQosQCLStatusActionPCP OBJECT-TYPE
               SYNTAX      DisplayString
               MAX-ACCESS  read-only
               STATUS      current
               DESCRIPTION
                   "Classify PCP value.
                    Only support SERVAL."
               ::= {     sm24dp4xaQosQCLStatusEntry 9}

    sm24dp4xaQosQCLStatusActionDEL OBJECT-TYPE
               SYNTAX      DisplayString
               MAX-ACCESS  read-only
               STATUS      current
               DESCRIPTION
                   "Classify DEI value.
                    Only support SERVAL."
               ::= {     sm24dp4xaQosQCLStatusEntry 10}

    sm24dp4xaQosQCLStatusActionPolicy OBJECT-TYPE
               SYNTAX      DisplayString
               MAX-ACCESS  read-only
               STATUS      current
               DESCRIPTION
                   "Classify ACL Policy number.
                    Only support SERVAL."
               ::= {     sm24dp4xaQosQCLStatusEntry 11}

    sm24dp4xaQosQCLStatusConflict OBJECT-TYPE
               SYNTAX      DisplayString
               MAX-ACCESS  read-only
               STATUS      current
               DESCRIPTION
                   "Displays Conflict status of QCL entries."
               ::= {     sm24dp4xaQosQCLStatusEntry 12}

    sm24dp4xaQosQCLStatusSwitch OBJECT-TYPE
               SYNTAX      Integer32
               MAX-ACCESS  read-only
               STATUS      current
               DESCRIPTION
                   "Switch number for port members. -1:Any.
                    Only support stacking switch."
               ::= {     sm24dp4xaQosQCLStatusEntry 13}
			   
    sm24dp4xaQosQCLStatusDMAC OBJECT-TYPE
               SYNTAX      DisplayString
               MAX-ACCESS  read-only
               STATUS      current
               DESCRIPTION
                   "Destination MAC address: Possible values are 'Unicast', 'Multicast', 'Broadcast' or 'Any'."
               ::= {     sm24dp4xaQosQCLStatusEntry 14}

    sm24dp4xaQosQCLStatusSMAC OBJECT-TYPE
               SYNTAX      DisplayString
               MAX-ACCESS  read-only
               STATUS      current
               DESCRIPTION
                   "Source MAC address: xx-xx-xx-xx-xx-xx or 'Any'."
               ::= {     sm24dp4xaQosQCLStatusEntry 15}

    sm24dp4xaQosQCLStatusTag OBJECT-TYPE
               SYNTAX      DisplayString
               MAX-ACCESS  read-only
               STATUS      current
               DESCRIPTION
                   "Value of Tag field can be 'Untagged', 'Tagged', 'C-Tagged', 'S-Tagged' or 'Any'."
               ::= {     sm24dp4xaQosQCLStatusEntry 16}

    sm24dp4xaQosQCLStatusVID OBJECT-TYPE
               SYNTAX      DisplayString
               MAX-ACCESS  read-only
               STATUS      current
               DESCRIPTION
                   "Valid value of VLAN ID can be any value in the range 1-4095 or 'Any'"
               ::= {     sm24dp4xaQosQCLStatusEntry 17}			   

    sm24dp4xaQosQCLStatusPCP OBJECT-TYPE
               SYNTAX      DisplayString
               MAX-ACCESS  read-only
               STATUS      current
               DESCRIPTION
                   "Valid value PCP are specific (0, 1, 2, 3, 4, 5, 6, 7) or range (0-1, 2-3, 4-5, 6-7, 0-3, 4-7) or 'Any'."
               ::= {     sm24dp4xaQosQCLStatusEntry 18}	

    sm24dp4xaQosQCLStatusDEI OBJECT-TYPE
               SYNTAX      DisplayString
               MAX-ACCESS  read-only
               STATUS      current
               DESCRIPTION
                   "Valid value of DEI can be '0', '1' or 'Any'."
               ::= {     sm24dp4xaQosQCLStatusEntry 19}				   
-- =======================================================================================================================
-- sm24dp4xaQosConformance
-- =======================================================================================================================
sm24dp4xaQosConformance OBJECT IDENTIFIER ::= { sm24dp4xaQosConf 200 }

sm24dp4xaQosCompliances OBJECT IDENTIFIER ::= { sm24dp4xaQosConformance 1 }

sm24dp4xaQosGroups      OBJECT IDENTIFIER ::= { sm24dp4xaQosConformance 2 }


sm24dp4xaQosPortClassificationGroup OBJECT-GROUP
    OBJECTS {
                --sm24dp4xaQosPortClassificationTable
                sm24dp4xaQosPortClassificationQoSClass,
                sm24dp4xaQosPortClassificationDPlevel,
                sm24dp4xaQosPortClassificationPCP,
                sm24dp4xaQosPortClassificationDEI,
                sm24dp4xaQosPortClassificationTagClass,
                sm24dp4xaQosPortClassificationDSCPBased,
                sm24dp4xaQosPortClassificationQCLAddr,
                sm24dp4xaQosPortClassificationKeyType,

                --sm24dp4xaQoSIngressPortTagClassificationTable
                sm24dp4xaQoSIngressPortTagQosClass,
                sm24dp4xaQoSIngressPortTagDPLevel
            }
    STATUS  current
    DESCRIPTION
            "The collection of objects which are used to indicate
            sm24dp4xa qos information."
    ::= { sm24dp4xaQosGroups 1}


sm24dp4xaQosPortPolicingGroup OBJECT-GROUP
    OBJECTS {
                --sm24dp4xaQosPortPolicingTable
                sm24dp4xaQosPortPolicingEnabled,
                sm24dp4xaQosPortPolicingRate,
                sm24dp4xaQosPortPolicingUnit
                --sm24dp4xaQosPortPolicingFlowControl
            }
    STATUS  current
    DESCRIPTION
            "The collection of objects which are used to indicate
            sm24dp4xa qos information."
    ::= { sm24dp4xaQosGroups 2}


sm24dp4xaQosQueuePolicingGroup OBJECT-GROUP
    OBJECTS {
                --sm24dp4xaQosPortPolicingTable
                sm24dp4xaQosQueuePolicingQueue0Enable,
                sm24dp4xaQosQueuePolicingQueue0Rate,
                sm24dp4xaQosQueuePolicingQueue1Enable,
                sm24dp4xaQosQueuePolicingQueue1Rate,
                sm24dp4xaQosQueuePolicingQueue2Enable,
                sm24dp4xaQosQueuePolicingQueue2Rate,
                sm24dp4xaQosQueuePolicingQueue3Enable,
                sm24dp4xaQosQueuePolicingQueue3Rate,
                sm24dp4xaQosQueuePolicingQueue4Enable,
                sm24dp4xaQosQueuePolicingQueue4Rate,
                sm24dp4xaQosQueuePolicingQueue5Enable,
                sm24dp4xaQosQueuePolicingQueue5Rate,
                sm24dp4xaQosQueuePolicingQueue6Enable,
                sm24dp4xaQosQueuePolicingQueue6Rate,
                sm24dp4xaQosQueuePolicingQueue7Enable,
                sm24dp4xaQosQueuePolicingQueue7Rate
            }
    STATUS  current
    DESCRIPTION
            "The collection of objects which are used to indicate
            sm24dp4xa qos information."
    ::= { sm24dp4xaQosGroups 3}

sm24dp4xaQosPortSchedulerGroup OBJECT-GROUP
    OBJECTS {
                --sm24dp4xaQosPortSchedulerModeTable
                sm24dp4xaQosSchedulerMode,
                sm24dp4xaQosSchedulerShaper,
                sm24dp4xaQosSchedulerShaperRate,

                --sm24dp4xaQosPortSchedulerTable
                 sm24dp4xaQosSchedulerPortQueueShaper,
                sm24dp4xaQosSchedulerPortQueueShaperRate,
                sm24dp4xaQosSchedulerPortQueueShaperExcess,
                sm24dp4xaQosSchedulerPortQueueSchedulerWeight,
                sm24dp4xaQosSchedulerPortQueueSchedulerPercent,

                --sm24dp4xaQosPortEgressTagRemarkingMapTable
                 sm24dp4xaQosTagRemarkingPCP,
                 sm24dp4xaQosTagRemarkingDEI
            }
    STATUS  current
    DESCRIPTION
            "The collection of objects which are used to indicate
            sm24dp4xa qos information."
    ::= { sm24dp4xaQosGroups 4}

sm24dp4xaQosPortEgressTagRemarkingGroup OBJECT-GROUP
    OBJECTS {
                --sm24dp4xaQosPortEgressTagRemarkingTable
                sm24dp4xaQosEgressTagRemarkingMode,

                --sm24dp4xaQosPortEgressTagRemarkingDefTable
               sm24dp4xaQosEgressTagRemarkingDefPCP,
               sm24dp4xaQosEgressTagRemarkingDefDEI

               --sm24dp4xaQosPortEgressTagRemarkingMapDPTable
--             sm24dp4xaQosPortEgressTagRemarkingDPLevel
            }
    STATUS  current
    DESCRIPTION
            "The collection of objects which are used to indicate
            sm24dp4xa qos information."
    ::= { sm24dp4xaQosGroups 6}


sm24dp4xaQosPortDSCPGroup OBJECT-GROUP
    OBJECTS {
                --sm24dp4xaQosPortDSCPTable
                sm24dp4xaQosPortDSCPIngressTranslate,
                sm24dp4xaQosPortDSCPIngressClassify,
                sm24dp4xaQosPortDSCPEgressRewrite
            }
    STATUS  current
    DESCRIPTION
            "The collection of objects which are used to indicate
            sm24dp4xa qos information."
    ::= { sm24dp4xaQosGroups 7}

sm24dp4xaQosDSCPGroup OBJECT-GROUP
    OBJECTS {
                --sm24dp4xaQosDSCPTable
                sm24dp4xaQosBasedDSCP,
                sm24dp4xaQosDSCPTrust,
                sm24dp4xaQosDSCPQosClass,
                sm24dp4xaQosDSCPDPL
             }
    STATUS  current
    DESCRIPTION
            "The collection of objects which are used to indicate
            sm24dp4xa qos information."
    ::= { sm24dp4xaQosGroups 8}

sm24dp4xaQosDSCPTranslationGroup OBJECT-GROUP
    OBJECTS {
                --sm24dp4xaQosDSCPTranslationTable
                sm24dp4xaQosDSCPTranslationDSCPBasedId,
                sm24dp4xaQosDSCPTranslationIngressTranslate,
                sm24dp4xaQosDSCPTranslationIngressClassify,
                sm24dp4xaQosDSCPTranslationEgressRemapDP0,
                sm24dp4xaQosDSCPTranslationEgressRemapDP1
            }
    STATUS  current
    DESCRIPTION
            "The collection of objects which are used to indicate
            sm24dp4xa qos information."
    ::= { sm24dp4xaQosGroups 9}

--sm24dp4xaQosDSCPClassificationGroup OBJECT-GROUP
--    OBJECTS {
--                sm24dp4xaQosDSCPClassificationTable
--                sm24dp4xaQosDSCPClassificationDSCP
--            }
--    STATUS  current
--    DESCRIPTION
--            "The collection of objects which are used to indicate
--            sm24dp4xa qos information."
--    ::= { sm24dp4xaQosGroups 10}

sm24dp4xaQosControlListGroup OBJECT-GROUP
    OBJECTS {
                --sm24dp4xaQosQceTable
                sm24dp4xaQosQceID,
                sm24dp4xaQosQceList,
                sm24dp4xaQosQcePortMembers,
                sm24dp4xaQosQceTag,
                sm24dp4xaQosQceVID,
                sm24dp4xaQosPCP,
                sm24dp4xaQosDEI,
                sm24dp4xaQosSMAC,
                sm24dp4xaQosDMACType,
                sm24dp4xaQosDMACValue,
                sm24dp4xaQosQceInnerTag,
                sm24dp4xaQosQceInnerVID,
                sm24dp4xaQosInnerPCP,
                sm24dp4xaQosInnerDEI,
                sm24dp4xaQosFrameType,
                sm24dp4xaQosMacEtherType,
                sm24dp4xaQosLLCSSAPAddr,
                sm24dp4xaQosLLCDSAPAddr,
                sm24dp4xaQosLLCControl,
                sm24dp4xaQosSNAPPID,
                sm24dp4xaQosIpv4Protocol,
                sm24dp4xaQosIpv4ProtocolValue,
                sm24dp4xaQosIpv4ProtocolUDPSPort,
                sm24dp4xaQosIpv4ProtocolUDPDPort,
                sm24dp4xaQosIpv4ProtocolTCPSPort,
                sm24dp4xaQosIpv4ProtocolTCPDPort,
                sm24dp4xaQosIpv4SourceIp,
                sm24dp4xaQosIpv4SourceMask,
                sm24dp4xaQosIpv4IPFragment,
                sm24dp4xaQosIpv4DSCP,
                sm24dp4xaQosIpv6Protocol,
                sm24dp4xaQosIpv6ProtocolValue,
                sm24dp4xaQosIpv6ProtocolUDPSPort,
                sm24dp4xaQosIpv6ProtocolUDPDPort,
                sm24dp4xaQosIpv6ProtocolTCPSPort,
                sm24dp4xaQosIpv6ProtocolTCPDPort,
                sm24dp4xaQosIpv6SourceIp,
                sm24dp4xaQosIpv6SourceMask,
                sm24dp4xaQosIpv6DSCP,
                sm24dp4xaQosActionClass,
                sm24dp4xaQosActionDPL,
                sm24dp4xaQosActionDSCP,
                sm24dp4xaQosActionPCP,
                sm24dp4xaQosActionDEI,
                sm24dp4xaQosActionPolicy,
                sm24dp4xaQosQceRowStatus
            }
    STATUS  current
    DESCRIPTION
            "The collection of objects which are used to indicate
             sm24dp4xa qos information."
    ::= { sm24dp4xaQosGroups 11}


sm24dp4xaQosStormControlGroup OBJECT-GROUP
    OBJECTS {
                --sm24dp4xaQosStormControlTable
                sm24dp4xaQosStormControlEnabled,
                sm24dp4xaQosStormControlRate
            }
    STATUS  current
    DESCRIPTION
            "The collection of objects which are used to indicate
            sm24dp4xa qos information."
    ::= { sm24dp4xaQosGroups 12}

sm24dp4xaQosPortStormControlGroup OBJECT-GROUP
    OBJECTS {
                --sm24dp4xaQosPortStormControlTable
                sm24dp4xaQosPortStormControlUnicastEnabled,
                sm24dp4xaQosPortStormControlUnicastRate,
                sm24dp4xaQosPortStormControlUnicastUnit,
                sm24dp4xaQosPortStormControlBroadcastEnabled,
                sm24dp4xaQosPortStormControlBroadcastRate,
                sm24dp4xaQosPortStormControlBroadcastUnit,
                sm24dp4xaQosPortStormControlUnknownEnabled,
                sm24dp4xaQosPortStormControlUnknownRate,
                sm24dp4xaQosPortStormControlUnknownUnit
            }
    STATUS  current
    DESCRIPTION
            "The collection of objects which are used to indicate
            sm24dp4xa qos information."
    ::= { sm24dp4xaQosGroups 13}

sm24dp4xaQosWREDGroup OBJECT-GROUP
    OBJECTS {
                --sm24dp4xaQosWREDTable
                sm24dp4xaQosWREDEnable,
                sm24dp4xaQosWREDMinThreshold,
                sm24dp4xaQosWREDMaxDP1,
                sm24dp4xaQosWREDMaxDP2,
                sm24dp4xaQosWREDMaxDP3 
            }
    STATUS  current
    DESCRIPTION
            "The collection of objects which are used to indicate
            sm24dp4xa qos information."
    ::= { sm24dp4xaQosGroups 14}

sm24dp4xaQosQCLStatusGroup OBJECT-GROUP
    OBJECTS {
                --sm24dp4xaQosQCLStatusTable
                sm24dp4xaQosQCLStatusUser,
                sm24dp4xaQosQCLStatusQCEId,
                sm24dp4xaQosQCLStatusFrameType,
                sm24dp4xaQosQCLStatusPortlist,
                sm24dp4xaQosQCLStatusActionClass,
                sm24dp4xaQosQCLStatusActionDPL,
                sm24dp4xaQosQCLStatusActionDSCP,
                sm24dp4xaQosQCLStatusActionPCP,
                sm24dp4xaQosQCLStatusActionDEL,
                sm24dp4xaQosQCLStatusActionPolicy,
                sm24dp4xaQosQCLStatusConflict
            }
    STATUS  current
    DESCRIPTION
            "The collection of objects which are used to indicate
            sm24dp4xa qos information."
    ::= { sm24dp4xaQosGroups 15}

-- =======================================================================================================================

sm24dp4xaLoopProtection                                                  OBJECT IDENTIFIER ::= { sm24dp4xaConfiguration 12 }

sm24dp4xaLoopProtectionConfig                                            OBJECT IDENTIFIER ::= { sm24dp4xaLoopProtection 1 }

sm24dp4xaLoopProtectionGlobalEnable OBJECT-TYPE
   SYNTAX      Integer32(0|1)
   MAX-ACCESS  read-write
   STATUS      current
   DESCRIPTION
       "Configure loop protection mode.
        0: disable,
        1: enable,
        default: disable. "
   ::= { sm24dp4xaLoopProtectionConfig 1 }

sm24dp4xaLoopProtectionTranmisstionTime OBJECT-TYPE
   SYNTAX      Integer32(1..10)
   MAX-ACCESS  read-write
   STATUS      current
   DESCRIPTION
       "Configure loop protection transmit interval.
        default: 5,
        range: 1-10. "
   ::= { sm24dp4xaLoopProtectionConfig 2 }

sm24dp4xaLoopProtectionShutdownTime OBJECT-TYPE
   SYNTAX      Integer32(0..604800)
   MAX-ACCESS  read-write
   STATUS      current
   DESCRIPTION
       "Configure loop protection shutdown time.
        default: 180,
        range: 0-604800. "
   ::= { sm24dp4xaLoopProtectionConfig 3 }

sm24dp4xaLoopProtectionConfigurationTable OBJECT-TYPE
   SYNTAX      SEQUENCE OF SM24DP4XALoopProtectionConfigurationEntry
   MAX-ACCESS  not-accessible
   STATUS      current
   DESCRIPTION
       " Show Loop Protection configurations. "
   ::= { sm24dp4xaLoopProtectionConfig 4 }

sm24dp4xaLoopProtectionConfigurationEntry OBJECT-TYPE
   SYNTAX      SM24DP4XALoopProtectionConfigurationEntry
   MAX-ACCESS  not-accessible
   STATUS      current
   DESCRIPTION
       " "
   INDEX    { sm24dp4xaLoopProtectionConfPort  }
   ::= { sm24dp4xaLoopProtectionConfigurationTable 1 }

SM24DP4XALoopProtectionConfigurationEntry ::= SEQUENCE {
   sm24dp4xaLoopProtectionConfPort	    Integer32,
   sm24dp4xaLoopProtectionConfEnable	Integer32,
   sm24dp4xaLoopProtectionConfAction	Integer32,
   sm24dp4xaLoopProtectionConfTxmode	Integer32
}

sm24dp4xaLoopProtectionConfPort OBJECT-TYPE
   SYNTAX      Integer32 (1..4095)
   MAX-ACCESS  not-accessible
   STATUS      current
   DESCRIPTION
       " port, range : 1 - port number. "
   ::= { sm24dp4xaLoopProtectionConfigurationEntry 1 }

sm24dp4xaLoopProtectionConfEnable OBJECT-TYPE
   SYNTAX      Integer32(0|1)
   MAX-ACCESS  read-write
   STATUS      current
   DESCRIPTION
       "Configure loop protection port mode.
        0: disable,
        1: enable,
        default: enable. "
   ::= { sm24dp4xaLoopProtectionConfigurationEntry 2 }

sm24dp4xaLoopProtectionConfAction OBJECT-TYPE
   SYNTAX      Integer32(0..2)
   MAX-ACCESS  read-write
   STATUS      current
   DESCRIPTION
       " Configure loop protection port action.
         0: Shutdown port,
         1: Shutdown port and Log,
         2: Log Only,
         default: Shutdown port. "
   ::= { sm24dp4xaLoopProtectionConfigurationEntry 3 }

sm24dp4xaLoopProtectionConfTxmode OBJECT-TYPE
   SYNTAX      Integer32(0|1)
   MAX-ACCESS  read-write
   STATUS      current
   DESCRIPTION
       "Configure loop protection port transmit mode.
        0: disable,
        1: enable,
        default: enable. "
   ::= { sm24dp4xaLoopProtectionConfigurationEntry 4 }

sm24dp4xaLoopProtectionStatusTable OBJECT-TYPE
   SYNTAX      SEQUENCE OF SM24DP4XALoopProtectionStatusEntry
   MAX-ACCESS  not-accessible
   STATUS      current
   DESCRIPTION
       " Show Loop Protection Status. "
   ::= { sm24dp4xaLoopProtection 2 }

sm24dp4xaLoopProtectionStatusEntry OBJECT-TYPE
   SYNTAX      SM24DP4XALoopProtectionStatusEntry
   MAX-ACCESS  not-accessible
   STATUS      current
   DESCRIPTION
       " "
   INDEX    { sm24dp4xaLoopProtectionStatusPort  }
   ::= { sm24dp4xaLoopProtectionStatusTable 1 }

SM24DP4XALoopProtectionStatusEntry ::= SEQUENCE {
   sm24dp4xaLoopProtectionStatusPort	       Integer32,
   sm24dp4xaLoopProtectionStatusAction	       DisplayString,
   sm24dp4xaLoopProtectionStatusTransmit	   DisplayString,
   sm24dp4xaLoopProtectionStatusLoops	       Integer32,
   sm24dp4xaLoopProtectionStatusStatus	       DisplayString,
   sm24dp4xaLoopProtectionStatusLoop	       DisplayString,
   sm24dp4xaLoopProtectionStatusTimeLastLoop  DisplayString
}

sm24dp4xaLoopProtectionStatusPort OBJECT-TYPE
   SYNTAX      Integer32 (1..4095)
   MAX-ACCESS  not-accessible
   STATUS      current
   DESCRIPTION
       " port, range : 1 - port number. "
   ::= { sm24dp4xaLoopProtectionStatusEntry 1 }

sm24dp4xaLoopProtectionStatusAction OBJECT-TYPE
   SYNTAX      DisplayString
   MAX-ACCESS  read-only
   STATUS      current
   DESCRIPTION
       " The currently configured port action. "
   ::= { sm24dp4xaLoopProtectionStatusEntry 2 }

sm24dp4xaLoopProtectionStatusTransmit OBJECT-TYPE
   SYNTAX      DisplayString
   MAX-ACCESS  read-only
   STATUS      current
   DESCRIPTION
       " The currently configured port transmit mode. "
   ::= { sm24dp4xaLoopProtectionStatusEntry 3 }

sm24dp4xaLoopProtectionStatusLoops OBJECT-TYPE
   SYNTAX      Integer32 (0..1000000)
   MAX-ACCESS  read-only
   STATUS      current
   DESCRIPTION
       " The number of loops detected on this port. "
   ::= { sm24dp4xaLoopProtectionStatusEntry 4 }

sm24dp4xaLoopProtectionStatusStatus OBJECT-TYPE
   SYNTAX      DisplayString
   MAX-ACCESS  read-only
   STATUS      current
   DESCRIPTION
       " The current loop protection status of the port. "
   ::= { sm24dp4xaLoopProtectionStatusEntry 5 }

sm24dp4xaLoopProtectionStatusLoop OBJECT-TYPE
   SYNTAX      DisplayString
   MAX-ACCESS  read-only
   STATUS      current
   DESCRIPTION
       " Whether a loop is currently detected on the port. "
   ::= { sm24dp4xaLoopProtectionStatusEntry 6 }

sm24dp4xaLoopProtectionStatusTimeLastLoop OBJECT-TYPE
   SYNTAX      DisplayString
   MAX-ACCESS  read-only
   STATUS      current
   DESCRIPTION
       " The time of the last loop event detected. "
   ::= { sm24dp4xaLoopProtectionStatusEntry 7 }
-- =======================================================================================================================
-- =======================================================================================================================
-- RowStatus Info:  createAndWait, notReady, notInService not supported.
-- =======================================================================================================================
-- Textual Conventions for the sm24dp4xa AAA Mib
-- =======================================================================================================================
--
sm24dp4xaAAAMIB                   OBJECT IDENTIFIER  ::= { sm24dp4xaConfiguration 15 }
    sm24dp4xaAAA                  OBJECT IDENTIFIER  ::= { sm24dp4xaAAAMIB 1 }
    sm24dp4xaRADIUS               OBJECT IDENTIFIER  ::= { sm24dp4xaAAA 1 }
    sm24dp4xaRADIUSGlobalConfig   OBJECT IDENTIFIER  ::= { sm24dp4xaRADIUS 1 }

    sm24dp4xaTACACS               OBJECT IDENTIFIER  ::= { sm24dp4xaAAA 2 }

--
-- =======================================================================================================================
-- Start sm24dp4xaRADIUS group
-- =======================================================================================================================
--sm24dp4xaRADIUSGlobalConfig

    sm24dp4xaRADIUSGlobalConfigTimeout OBJECT-TYPE
               SYNTAX      Integer32(1..1000)
               MAX-ACCESS  read-write
               STATUS      current
               DESCRIPTION
                   "Timeout is the number of seconds, to wait for a reply
                    from a RADIUS server before retransmitting the request.
                    range: 1-1000."
               ::= {     sm24dp4xaRADIUSGlobalConfig 1 }

    sm24dp4xaRADIUSGlobalConfigRetransmit OBJECT-TYPE
               SYNTAX      Integer32(1..1000)
               MAX-ACCESS  read-write
               STATUS      current
               DESCRIPTION
                   "Retransmit is the number of times,a RADIUS request is
                    retransmitted to a server that is not responding.If the
                    server has not responded after the last retransmit it is
                    considered to be dead.
                    range: 1-1000."
               ::= {     sm24dp4xaRADIUSGlobalConfig 2 }

    sm24dp4xaRADIUSGlobalConfigDeadtime OBJECT-TYPE
               SYNTAX      Integer32(0..1440)
               MAX-ACCESS  read-write
               STATUS      current
               DESCRIPTION
                   "This will stop the switch from continually trying to
                    contact a server that it has already determined as dead.
                    range: 0-1440."
               ::= {     sm24dp4xaRADIUSGlobalConfig 3 }

    sm24dp4xaRADIUSGlobalConfigKey OBJECT-TYPE
               SYNTAX      DisplayString
               MAX-ACCESS  read-write
               STATUS      current
               DESCRIPTION
                   "The secret key shared between the RADIUS server and
                    the switch."
               ::= {     sm24dp4xaRADIUSGlobalConfig 4 }

    sm24dp4xaRADIUSGlobalConfigNASIPv4 OBJECT-TYPE
               SYNTAX      IpAddress
               MAX-ACCESS  read-write
               STATUS      current
               DESCRIPTION
                   "The IPv4 address to be used as attribute 4 in RADIUS
                    Access-Request packets."
               ::= {     sm24dp4xaRADIUSGlobalConfig 5 }

    sm24dp4xaRADIUSGlobalConfigNASIPv6 OBJECT-TYPE
               SYNTAX      DisplayString
               MAX-ACCESS  read-write
               STATUS      current
               DESCRIPTION
                   "The IPv6 address to be used as attribute 95 in RADIUS
                    Access-Request packets. "
               ::= {     sm24dp4xaRADIUSGlobalConfig 6 }

    sm24dp4xaRADIUSGlobalConfigNASIdentifier OBJECT-TYPE
               SYNTAX      DisplayString
               MAX-ACCESS  read-write
               STATUS      current
               DESCRIPTION
                   "The identifier to be used as attribute 32 in RADIUS
                    Access-Request packets. "
               ::= {     sm24dp4xaRADIUSGlobalConfig 7 }

--sm24dp4xaRADIUSServerConfigTable

    sm24dp4xaRADIUSServerConfigTable OBJECT-TYPE
               SYNTAX      SEQUENCE OF     SM24DP4XARADIUSServerConfigEntry
               MAX-ACCESS  not-accessible
               STATUS      current
               DESCRIPTION
                   "The RADIUS Server Configuration Table."
               ::= {     sm24dp4xaRADIUS 2 }

    sm24dp4xaRADIUSServerConfigEntry OBJECT-TYPE
               SYNTAX          SM24DP4XARADIUSServerConfigEntry
               MAX-ACCESS  not-accessible
               STATUS      current
               DESCRIPTION
                   "The RADIUS Server Configuration Entry."
               INDEX    {    sm24dp4xaRADIUSServerConfServerNo  }
               ::= {     sm24dp4xaRADIUSServerConfigTable 1 }

    SM24DP4XARADIUSServerConfigEntry             ::= SEQUENCE {
                 sm24dp4xaRADIUSServerConfServerNo      Integer32,
                 sm24dp4xaRADIUSServerConfHostname      DisplayString,
                 sm24dp4xaRADIUSServerConfAuthPort      Integer32,
                 sm24dp4xaRADIUSServerConfAcctPort      Integer32,
                 sm24dp4xaRADIUSServerConfTimeout       Integer32,
                 sm24dp4xaRADIUSServerConfRetransmit    Integer32,
                 sm24dp4xaRADIUSServerConfKey           DisplayString,
                 sm24dp4xaRADIUSServerConfRowStatus     RowStatus
                 }

    sm24dp4xaRADIUSServerConfServerNo OBJECT-TYPE
               SYNTAX      Integer32(1..5)
               MAX-ACCESS  not-accessible
               STATUS      current
               DESCRIPTION
                   "The RADIUS server number.
                    max: 5."
               ::= {     sm24dp4xaRADIUSServerConfigEntry 1 }

    sm24dp4xaRADIUSServerConfHostname OBJECT-TYPE
               SYNTAX      DisplayString
               MAX-ACCESS  read-create
               STATUS      current
               DESCRIPTION
                   "The IP address or hostname of the RADIUS server. "
               ::= {     sm24dp4xaRADIUSServerConfigEntry 2 }

    sm24dp4xaRADIUSServerConfAuthPort OBJECT-TYPE
               SYNTAX      Integer32(0..65535)
               MAX-ACCESS  read-create
               STATUS      current
               DESCRIPTION
                   "The UDP port to use on the RADIUS server for
                    authentication.
                    range: 0-65535. "
               ::= {     sm24dp4xaRADIUSServerConfigEntry 3 }

    sm24dp4xaRADIUSServerConfAcctPort OBJECT-TYPE
               SYNTAX      Integer32(0..65535)
               MAX-ACCESS  read-create
               STATUS      current
               DESCRIPTION
                   "The UDP port to use on the RADIUS server for accounting.
                    range: 0-65535. "
               ::= {     sm24dp4xaRADIUSServerConfigEntry 4 }

    sm24dp4xaRADIUSServerConfTimeout OBJECT-TYPE
               SYNTAX      Integer32(1..1000)
               MAX-ACCESS  read-create
               STATUS      current
               DESCRIPTION
                   "This optional setting overrides the global timeout value.
                    Leaving it blank will use the global timeout value.
                    range: 1-1000. "
               ::= {     sm24dp4xaRADIUSServerConfigEntry 5 }

    sm24dp4xaRADIUSServerConfRetransmit OBJECT-TYPE
               SYNTAX      Integer32(1..1000)
               MAX-ACCESS  read-create
               STATUS      current
               DESCRIPTION
                   "This optional setting overrides the global retransmit value.
                    Leaving it blank will use the global retransmit value.
                    range: 1-1000. "
               ::= {     sm24dp4xaRADIUSServerConfigEntry 6 }

    sm24dp4xaRADIUSServerConfKey OBJECT-TYPE
               SYNTAX      DisplayString
               MAX-ACCESS  read-create
               STATUS      current
               DESCRIPTION
                   "This optional setting overrides the global key. Leaving
                    it blank will use the global key."
               ::= {     sm24dp4xaRADIUSServerConfigEntry 7 }

    sm24dp4xaRADIUSServerConfRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sm24dp4xaRADIUSServerConfigEntry 8 }

--sm24dp4xaRADIUSDetailTable

    sm24dp4xaRADIUSDetailTable OBJECT-TYPE
               SYNTAX      SEQUENCE OF     SM24DP4XARADIUSDetailEntry
               MAX-ACCESS  not-accessible
               STATUS      current
               DESCRIPTION
                   "The RADIUS Detail Table."
               ::= {     sm24dp4xaRADIUS 3 }

    sm24dp4xaRADIUSDetailEntry OBJECT-TYPE
               SYNTAX          SM24DP4XARADIUSDetailEntry
               MAX-ACCESS  not-accessible
               STATUS      current
               DESCRIPTION
                   "The RADIUS Detail Entry."
               INDEX    {    sm24dp4xaRADIUSServerConfServerNo  }
               ::= {     sm24dp4xaRADIUSDetailTable 1 }

    SM24DP4XARADIUSDetailEntry             ::= SEQUENCE {
                 sm24dp4xaRADIUSAuthIPAddress               DisplayString,
                 sm24dp4xaRADIUSAuthStatus                  DisplayString,
                 sm24dp4xaRADIUSAuthRoundTripTime           Integer32,
                 sm24dp4xaRADIUSAuthRxAccessAccept          Counter32,
                 sm24dp4xaRADIUSAuthRxAccessReject          Counter32,
                 sm24dp4xaRADIUSAuthRxAccessChallenge       Counter32,
                 sm24dp4xaRADIUSAuthRxAccessResponse        Counter32,
                 sm24dp4xaRADIUSAuthRxBadAuth               Counter32,
                 sm24dp4xaRADIUSAuthRxUnknownType           Counter32,
                 sm24dp4xaRADIUSAuthRxPacketsDropped        Counter32,
                 sm24dp4xaRADIUSAuthTxAccessRequest         Counter32,
                 sm24dp4xaRADIUSAuthTxAccessRetransmission  Counter32,
                 sm24dp4xaRADIUSAuthTxPendingRequest        Counter32,
                 sm24dp4xaRADIUSAuthTxTimeout               Counter32,
                 sm24dp4xaRADIUSAccountIPAddress            IpAddress,
                 sm24dp4xaRADIUSAccountStatus               DisplayString,
                 sm24dp4xaRADIUSAccountRoundTripTime        Integer32,
                 sm24dp4xaRADIUSAccountRxResponses          Counter32,
                 sm24dp4xaRADIUSAccountRxMalformedResponse  Counter32,
                 sm24dp4xaRADIUSAccountRxBadAuth            Counter32,
                 sm24dp4xaRADIUSAccountRxUnknownType        Counter32,
                 sm24dp4xaRADIUSAccountRxPacketsDrop        Counter32,
                 sm24dp4xaRADIUSAccountTxRequest            Counter32,
                 sm24dp4xaRADIUSAccountTxRetransmission     Counter32,
                 sm24dp4xaRADIUSAccountTxPendingRequest     Counter32,
                 sm24dp4xaRADIUSAccountTxTimeout            Counter32,
                 sm24dp4xaRADIUSDetailClearCmd              ActivateCmd
                 }

    sm24dp4xaRADIUSAuthIPAddress OBJECT-TYPE
               SYNTAX      DisplayString
               MAX-ACCESS  read-only
               STATUS      current
               DESCRIPTION
                   "IP address and UDP port for the authentication
                    server in question."
               ::= {     sm24dp4xaRADIUSDetailEntry 2 }

    sm24dp4xaRADIUSAuthStatus OBJECT-TYPE
               SYNTAX      DisplayString
               MAX-ACCESS  read-only
               STATUS      current
               DESCRIPTION
                   "Shows the state of the server."
               ::= {     sm24dp4xaRADIUSDetailEntry 3 }

    sm24dp4xaRADIUSAuthRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sm24dp4xaRADIUSDetailEntry 4 }

    sm24dp4xaRADIUSAuthRxAccessAccept OBJECT-TYPE
               SYNTAX      Counter32
               MAX-ACCESS  read-only
               STATUS      current
               DESCRIPTION
                   "The number of RADIUS Access-Accept packets
                   (valid or invalid) received from the server."
               ::= {     sm24dp4xaRADIUSDetailEntry 5 }

    sm24dp4xaRADIUSAuthRxAccessReject OBJECT-TYPE
               SYNTAX      Counter32
               MAX-ACCESS  read-only
               STATUS      current
               DESCRIPTION
                   "The number of RADIUS Access-Reject packets
                    (valid or invalid) received from the server."
               ::= {     sm24dp4xaRADIUSDetailEntry 6 }

    sm24dp4xaRADIUSAuthRxAccessChallenge OBJECT-TYPE
               SYNTAX      Counter32
               MAX-ACCESS  read-only
               STATUS      current
               DESCRIPTION
                   "The number of RADIUS Access-Challenge packets
                    (valid or invalid) received from the server."
               ::= {     sm24dp4xaRADIUSDetailEntry 7 }

    sm24dp4xaRADIUSAuthRxAccessResponse OBJECT-TYPE
               SYNTAX      Counter32
               MAX-ACCESS  read-only
               STATUS      current
               DESCRIPTION
                   "The number of malformed RADIUS Access-Response
                    packets received from the server."
               ::= {     sm24dp4xaRADIUSDetailEntry 8 }

    sm24dp4xaRADIUSAuthRxBadAuth OBJECT-TYPE
               SYNTAX      Counter32
               MAX-ACCESS  read-only
               STATUS      current
               DESCRIPTION
                   "The number of RADIUS Access-Response packets containing
                    invalid authenticators or Message Authenticator
                    attributes received from the server."
               ::= {     sm24dp4xaRADIUSDetailEntry 9 }

    sm24dp4xaRADIUSAuthRxUnknownType OBJECT-TYPE
               SYNTAX      Counter32
               MAX-ACCESS  read-only
               STATUS      current
               DESCRIPTION
                   "The number of RADIUS packets that were received with
                    unknown types from the server on the authentication
                    port and dropped."
               ::= {     sm24dp4xaRADIUSDetailEntry 10 }

    sm24dp4xaRADIUSAuthRxPacketsDropped OBJECT-TYPE
               SYNTAX      Counter32
               MAX-ACCESS  read-only
               STATUS      current
               DESCRIPTION
                   "The number of RADIUS packets that were received from
                    the server on the authentication port and dropped for
                    some other reason."
               ::= {     sm24dp4xaRADIUSDetailEntry 11 }

    sm24dp4xaRADIUSAuthTxAccessRequest OBJECT-TYPE
               SYNTAX      Counter32
               MAX-ACCESS  read-only
               STATUS      current
               DESCRIPTION
                   "The number of RADIUS Access-Request packets sent to
                    the server. This does not include retransmissions."
               ::= {     sm24dp4xaRADIUSDetailEntry 12 }

    sm24dp4xaRADIUSAuthTxAccessRetransmission OBJECT-TYPE
               SYNTAX      Counter32
               MAX-ACCESS  read-only
               STATUS      current
               DESCRIPTION
                   "The number of RADIUS Access-Request packets
                    retransmitted to the RADIUS authentication server."
               ::= {     sm24dp4xaRADIUSDetailEntry 13 }

    sm24dp4xaRADIUSAuthTxPendingRequest OBJECT-TYPE
               SYNTAX      Counter32
               MAX-ACCESS  read-only
               STATUS      current
               DESCRIPTION
                   "The number of RADIUS Access-Request packets destined
                    for the server that have not yet timed out or received
                    a response. "
               ::= {     sm24dp4xaRADIUSDetailEntry 14 }

    sm24dp4xaRADIUSAuthTxTimeout OBJECT-TYPE
               SYNTAX      Counter32
               MAX-ACCESS  read-only
               STATUS      current
               DESCRIPTION
                   "The number of authentication timeouts to the server.
                    After a timeout, the client may retry to the same server,
                    send to a different server, or give up."
               ::= {     sm24dp4xaRADIUSDetailEntry 15 }

    sm24dp4xaRADIUSAccountIPAddress OBJECT-TYPE
               SYNTAX      IpAddress
               MAX-ACCESS  read-only
               STATUS      current
               DESCRIPTION
                   "IP address and UDP port for the authentication server
                    in question."
               ::= {     sm24dp4xaRADIUSDetailEntry 16 }

    sm24dp4xaRADIUSAccountStatus OBJECT-TYPE
               SYNTAX      DisplayString
               MAX-ACCESS  read-only
               STATUS      current
               DESCRIPTION
                   "Shows the state of the server. "
               ::= {     sm24dp4xaRADIUSDetailEntry 17 }

    sm24dp4xaRADIUSAccountRoundTripTime OBJECT-TYPE
               SYNTAX      Integer32(0..100000000)
               MAX-ACCESS  read-only
               STATUS      current
               DESCRIPTION
                   "The time interval (measured in milliseconds) between
                    the most recent Access-Reply/Access-Challenge and the
                    Access-Request that matched it from the RADIUS
                    authentication server."
               ::= {     sm24dp4xaRADIUSDetailEntry 18 }

    sm24dp4xaRADIUSAccountRxResponses OBJECT-TYPE
               SYNTAX      Counter32
               MAX-ACCESS  read-only
               STATUS      current
               DESCRIPTION
                   "The number of RADIUS packets (valid or invalid)
                    received from the server."
               ::= {     sm24dp4xaRADIUSDetailEntry 19 }

    sm24dp4xaRADIUSAccountRxMalformedResponse OBJECT-TYPE
               SYNTAX      Counter32
               MAX-ACCESS  read-only
               STATUS      current
               DESCRIPTION
                   "The number of malformed RADIUS packets received from
                    the server. "
               ::= {     sm24dp4xaRADIUSDetailEntry 20 }

    sm24dp4xaRADIUSAccountRxBadAuth OBJECT-TYPE
               SYNTAX      Counter32
               MAX-ACCESS  read-only
               STATUS      current
               DESCRIPTION
                   "The number of RADIUS packets containing invalid
                    authenticators received from the server."
               ::= {     sm24dp4xaRADIUSDetailEntry 21 }

    sm24dp4xaRADIUSAccountRxUnknownType OBJECT-TYPE
               SYNTAX      Counter32
               MAX-ACCESS  read-only
               STATUS      current
               DESCRIPTION
                   "The number of RADIUS packets of unknown types that were
                    received from the server on the accounting port. "
               ::= {     sm24dp4xaRADIUSDetailEntry 22 }

    sm24dp4xaRADIUSAccountRxPacketsDrop OBJECT-TYPE
               SYNTAX      Counter32
               MAX-ACCESS  read-only
               STATUS      current
               DESCRIPTION
                   "The number of RADIUS packets that were received from
                    the server on the accounting port and dropped for some
                    other reason."
               ::= {     sm24dp4xaRADIUSDetailEntry 23 }

    sm24dp4xaRADIUSAccountTxRequest OBJECT-TYPE
               SYNTAX      Counter32
               MAX-ACCESS  read-only
               STATUS      current
               DESCRIPTION
                   "The number of RADIUS packets sent to the server.
                    This does not include retransmissions."
               ::= {     sm24dp4xaRADIUSDetailEntry 24 }

    sm24dp4xaRADIUSAccountTxRetransmission OBJECT-TYPE
               SYNTAX      Counter32
               MAX-ACCESS  read-only
               STATUS      current
               DESCRIPTION
                   "The number of RADIUS packets retransmitted to the RADIUS
                    accounting server."
               ::= {     sm24dp4xaRADIUSDetailEntry 25 }

    sm24dp4xaRADIUSAccountTxPendingRequest OBJECT-TYPE
               SYNTAX      Counter32
               MAX-ACCESS  read-only
               STATUS      current
               DESCRIPTION
                   "The number of RADIUS packets destined for the server
                    that have not yet timed out or received a response."
               ::= {     sm24dp4xaRADIUSDetailEntry 26 }

    sm24dp4xaRADIUSAccountTxTimeout OBJECT-TYPE
               SYNTAX      Counter32
               MAX-ACCESS  read-only
               STATUS      current
               DESCRIPTION
                   "The number of accounting timeouts to the server.
                    After a timeout, the client may retry to the same
                    server, send to a different server, or give up."
               ::= {     sm24dp4xaRADIUSDetailEntry 27 }

    sm24dp4xaRADIUSDetailClearCmd OBJECT-TYPE
               SYNTAX      ActivateCmd
               MAX-ACCESS  read-only
               STATUS      current
               DESCRIPTION
                   "Clears the counters for the selected server."
               ::= {     sm24dp4xaRADIUSDetailEntry 28 }

--
-- =======================================================================================================================
-- Start sm24dp4xaTACACS group
-- =======================================================================================================================
--sm24dp4xaTACACSGlobalConfig

    sm24dp4xaTACACSGlobalConfigTimeout OBJECT-TYPE
               SYNTAX      Integer32(1..1000)
               MAX-ACCESS  read-write
               STATUS      current
               DESCRIPTION
                   "Timeout is the number of seconds,to wait for a reply
                    from a TACACS+ server before it is considered to be dead.
                    range: 1-1000 seconds,
                    default: 5 seconds."
               ::= {     sm24dp4xaTACACS 1 }

    sm24dp4xaTACACSGlobalConfigDeadtime OBJECT-TYPE
               SYNTAX      Integer32(0..1440)
               MAX-ACCESS  read-write
               STATUS      current
               DESCRIPTION
                   "The period during which the switch will not send new
                    requests to a server that has failed to respond to a
                    previous request. This will stop the switch from
                    continually trying to contact a server that it has
                    already determined as dead.
                    range: 0-1440 minutes,
                    default: 0 minutes."
               ::= {     sm24dp4xaTACACS 2 }

    sm24dp4xaTACACSGlobalConfigKey OBJECT-TYPE
               SYNTAX      DisplayString
               MAX-ACCESS  read-write
               STATUS      current
               DESCRIPTION
                   "The secret key shared between the TACACS+ server and
                    the switch."
               ::= {     sm24dp4xaTACACS 3 }

--sm24dp4xaTACACSServerConfigTable

    sm24dp4xaTACACSServerConfigTable OBJECT-TYPE
               SYNTAX      SEQUENCE OF     SM24DP4XATACACSServerConfigEntry
               MAX-ACCESS  not-accessible
               STATUS      current
               DESCRIPTION
                   "The TACACS Server configuration Table."
               ::= {     sm24dp4xaTACACS 4 }

    sm24dp4xaTACACSServerConfigEntry OBJECT-TYPE
               SYNTAX          SM24DP4XATACACSServerConfigEntry
               MAX-ACCESS  not-accessible
               STATUS      current
               DESCRIPTION
                   "The TACACS Server configuration Entry."
               INDEX    {    sm24dp4xaTACACSServerConfigServerNo  }
               ::= {     sm24dp4xaTACACSServerConfigTable 1 }

    SM24DP4XATACACSServerConfigEntry             ::= SEQUENCE {
                 sm24dp4xaTACACSServerConfigServerNo        Integer32,
                 sm24dp4xaTACACSServerConfigHostname        DisplayString,
                 sm24dp4xaTACACSServerConfigPort            Integer32,
                 sm24dp4xaTACACSServerConfigTimeout         Integer32,
                 sm24dp4xaTACACSServerConfigKey             DisplayString,
                 sm24dp4xaTACACSServerConfigRowStatus       RowStatus
                 }

    sm24dp4xaTACACSServerConfigServerNo OBJECT-TYPE
               SYNTAX      Integer32(1..5)
               MAX-ACCESS  not-accessible
               STATUS      current
               DESCRIPTION
                   "The TACACS server number.
                    max: 5."
               ::= {     sm24dp4xaTACACSServerConfigEntry 1 }

    sm24dp4xaTACACSServerConfigHostname OBJECT-TYPE
               SYNTAX      DisplayString
               MAX-ACCESS  read-create
               STATUS      current
               DESCRIPTION
                   "The IP address or hostname of the TACACS+ server."
               ::= {     sm24dp4xaTACACSServerConfigEntry 2 }

    sm24dp4xaTACACSServerConfigPort OBJECT-TYPE
               SYNTAX      Integer32(0..65535)
               MAX-ACCESS  read-create
               STATUS      current
               DESCRIPTION
                   "The TCP port to use on the TACACS+ server for
                    authentication."
               ::= {     sm24dp4xaTACACSServerConfigEntry 3 }

    sm24dp4xaTACACSServerConfigTimeout OBJECT-TYPE
               SYNTAX      Integer32(1..1000)
               MAX-ACCESS  read-create
               STATUS      current
               DESCRIPTION
                   "This optional setting overrides the global timeout
                    value. Leaving it blank will use the global timeout
                    value.
                    range: 1-1000."
               ::= {     sm24dp4xaTACACSServerConfigEntry 4 }

    sm24dp4xaTACACSServerConfigKey OBJECT-TYPE
               SYNTAX      DisplayString
               MAX-ACCESS  read-create
               STATUS      current
               DESCRIPTION
                   "This optional setting overrides the global key.
                    Leaving it blank will use the global key. "
               ::= {     sm24dp4xaTACACSServerConfigEntry 5 }

    sm24dp4xaTACACSServerConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sm24dp4xaTACACSServerConfigEntry 6 }

-- =======================================================================================================================
--
-- =======================================================================================================================
-- Textual Conventions for the sm24dp4xa Nas Mib
-- =======================================================================================================================
--
sm24dp4xaNasMIB                   OBJECT IDENTIFIER  ::= { sm24dp4xaConfiguration 16 }
    sm24dp4xaNAS                  OBJECT IDENTIFIER  ::= { sm24dp4xaNasMIB 1 }
    sm24dp4xaNASConf              OBJECT IDENTIFIER  ::= { sm24dp4xaNAS 1 }
    sm24dp4xaNASStatus            OBJECT IDENTIFIER  ::= { sm24dp4xaNAS 2 }

--
-- =======================================================================================================================
-- Start sm24dp4xaNAS group
-- =======================================================================================================================
--sm24dp4xaNASConf

    sm24dp4xaNASConfMode OBJECT-TYPE
               SYNTAX      AdminMode
               MAX-ACCESS  read-write
               STATUS      current
               DESCRIPTION
                   "Indicates if NAS is globally enabled or disabled on
                    the switch."
               DEFVAL  { disable }
               ::= {     sm24dp4xaNASConf 1 }

    sm24dp4xaNASConfReauthenticationEnabled OBJECT-TYPE
               SYNTAX      AdminMode
               MAX-ACCESS  read-write
               STATUS      current
               DESCRIPTION
                   "If enable, successfully authenticated supplicants/clients
                    are reauthenticated after the interval specified by the
                    Reauthentication Period."
               DEFVAL  { disable }
               ::= {     sm24dp4xaNASConf 2 }

    sm24dp4xaNASConfReauthenticationPeriod OBJECT-TYPE
               SYNTAX      Integer32(1..3600)
               MAX-ACCESS  read-write
               STATUS      current
               DESCRIPTION
                   "Determines the period, in seconds, after which a
                    connected client must be reauthenticated.
                    default: 3600 sec,
                    range: 1-3600 sec."
               ::= {     sm24dp4xaNASConf 3 }

    sm24dp4xaNASConfEAPOLTimeout OBJECT-TYPE
               SYNTAX      Integer32(1..65535)
               MAX-ACCESS  read-write
               STATUS      current
               DESCRIPTION
                   "Determines the time for retransmission of Request
                    Identity EAPOL frames.
                    default: 30 sec,
                    range: 1-65535 sec."
               ::= {     sm24dp4xaNASConf 4 }

    sm24dp4xaNASConfAgingPeriod OBJECT-TYPE
               SYNTAX      Integer32(0|10..1000000)
               MAX-ACCESS  read-write
               STATUS      current
               DESCRIPTION
                   "When the NAS module uses the Port Security module to
                    secure MAC addresses, the Port Security module needs to
                    check for activity on the MAC address in question at regular
                    intervals and free resources if no activity is seen within
                    a given period of time.
                    default: 300 sec,
                    0: no support.
                    range: 0,10-1000000 sec."
               ::= {     sm24dp4xaNASConf 5 }

    sm24dp4xaNASConfHoldTime OBJECT-TYPE
               SYNTAX      Integer32(0|10..1000000)
               MAX-ACCESS  read-write
               STATUS      current
               DESCRIPTION
                   "If a client is denied access - either because the RADIUS
                    server denies the client access or because the RADIUS server
                    request times out - the client is put on hold in the
                    Unauthorized state.
                    default: 10 sec,
                    0: no support.
                    range: 0,10-1000000 sec."
               ::= {     sm24dp4xaNASConf 6 }

    sm24dp4xaNASConfRADIUSQoSEnabled OBJECT-TYPE
               SYNTAX      AdminMode
               MAX-ACCESS  read-write
               STATUS      current
               DESCRIPTION
                   "RADIUS-assigned QoS provides a means to centrally control
                    the traffic class to which traffic coming from a successfully
                    authenticated supplicant is assigned on the switch."
               DEFVAL  { disable }
               ::= {     sm24dp4xaNASConf 7 }

    sm24dp4xaNASConfRADIUSVLANEnabled OBJECT-TYPE
               SYNTAX      AdminMode
               MAX-ACCESS  read-write
               STATUS      current
               DESCRIPTION
                   "RADIUS-assigned VLAN provides a means to centrally control
                    the VLAN on which a successfully authenticated supplicant
                    is placed on the switch."
               DEFVAL  { disable }
               ::= {     sm24dp4xaNASConf 8 }

    sm24dp4xaNASConfGuestVLANEnabled OBJECT-TYPE
               SYNTAX      AdminMode
               MAX-ACCESS  read-write
               STATUS      current
               DESCRIPTION
                   "A Guest VLAN is a special VLAN - typically with limited
                    network access - on which 802.1X-unaware clients are placed
                    after a network administrator-defined timeout."
               DEFVAL  { disable }
               ::= {     sm24dp4xaNASConf 9 }

    sm24dp4xaNASConfGuestVLANID OBJECT-TYPE
               SYNTAX      Integer32(1..4095)
               MAX-ACCESS  read-write
               STATUS      current
               DESCRIPTION
                   "This is the value that a port's Port VLAN ID is set to if
                    a port is moved into the Guest VLAN.
                    default: 1,
                    range: 1-4095."
               ::= {     sm24dp4xaNASConf 10 }

    sm24dp4xaNASConfMaxReauthCount OBJECT-TYPE
               SYNTAX      Integer32(1..255)
               MAX-ACCESS  read-write
               STATUS      current
               DESCRIPTION
                   "The number of times the switch transmits an EAPOL Request
                    Identity frame without response before considering entering
                    the Guest VLAN is adjusted with this setting.
                    default: 2,
                    range: 1-255."
               ::= {     sm24dp4xaNASConf 11 }

    sm24dp4xaNASConfAllowGuestVLAN OBJECT-TYPE
               SYNTAX      AdminMode
               MAX-ACCESS  read-write
               STATUS      current
               DESCRIPTION
                   "The switch remembers if an EAPOL frame has been received
                    on the port for the life-time of the port."
               DEFVAL  { disable }
               ::= {     sm24dp4xaNASConf 12 }

--sm24dp4xaNASPortConfTable

    sm24dp4xaNASPortConfTable OBJECT-TYPE
               SYNTAX      SEQUENCE OF     SM24DP4XANASPortConfEntry
               MAX-ACCESS  not-accessible
               STATUS      current
               DESCRIPTION
                   "The NAS Port Configuration Table.
                    INDEX for this table is ifIndex which is
                    equivalent to the panel port number."
               ::= {     sm24dp4xaNASConf 13 }

    sm24dp4xaNASPortConfEntry OBJECT-TYPE
               SYNTAX          SM24DP4XANASPortConfEntry
               MAX-ACCESS  not-accessible
               STATUS      current
               DESCRIPTION
                   "The NAS Port Configuration Entry."
               INDEX    {    ifIndex  }
               ::= {     sm24dp4xaNASPortConfTable 1 }

    SM24DP4XANASPortConfEntry             ::= SEQUENCE {
                 sm24dp4xaNASPortConfAdminState         Integer32,
                 sm24dp4xaNASPortConfRADIUSQoSEnabled   AdminMode,
                 sm24dp4xaNASPortConfRADIUSVLANEnabled  AdminMode,
                 sm24dp4xaNASPortConfGuestVLANEnabled   AdminMode,
                 sm24dp4xaNASPortConfPortState          DisplayString,
                 sm24dp4xaNASPortConfReauthenticateCmd  INTEGER,
                 sm24dp4xaNASPortConfReinitializeCmd    INTEGER
                 }

    sm24dp4xaNASPortConfAdminState OBJECT-TYPE
               SYNTAX      Integer32(0..5)
               MAX-ACCESS  read-write
               STATUS      current
               DESCRIPTION
                   "This selection controls the port's authentication mode.
                    0: Force Authorized,
                    1: Force Unauthorized,
                    2: Port-based 802.1X,
                    3: Single 802.1X,
                    4: Multi 802.1X,
                    5: MAC-based Auth,
                    range: 0-5."
               ::= {     sm24dp4xaNASPortConfEntry 2 }

    sm24dp4xaNASPortConfRADIUSQoSEnabled OBJECT-TYPE
               SYNTAX      AdminMode
               MAX-ACCESS  read-write
               STATUS      current
               DESCRIPTION
                   "When RADIUS-Assigned QoS is both globally enabled and
                    enabled on a given port, the switch reacts to QoS Class
                    information carried in the RADIUS Access-Accept packet
                    transmitted by the RADIUS server when a supplicant is
                    successfully authenticated."
               ::= {     sm24dp4xaNASPortConfEntry 3 }

    sm24dp4xaNASPortConfRADIUSVLANEnabled OBJECT-TYPE
               SYNTAX      AdminMode
               MAX-ACCESS  read-write
               STATUS      current
               DESCRIPTION
                   "When RADIUS-Assigned VLAN is both globally enabled and
                    enabled for a given port, the switch reacts to VLAN ID
                    information carried in the RADIUS Access-Accept packet
                    transmitted by the RADIUS server when a supplicant is
                    successfully authenticated."
               ::= {     sm24dp4xaNASPortConfEntry 4 }

    sm24dp4xaNASPortConfGuestVLANEnabled OBJECT-TYPE
               SYNTAX      AdminMode
               MAX-ACCESS  read-write
               STATUS      current
               DESCRIPTION
                   "When Guest VLAN is both globally enabled and enabled for
                    a given port, the switch considers moving the port into
                    the Guest VLAN according to the rules."
               ::= {     sm24dp4xaNASPortConfEntry 5 }

    sm24dp4xaNASPortConfPortState OBJECT-TYPE
               SYNTAX      DisplayString
               MAX-ACCESS  read-only
               STATUS      current
               DESCRIPTION
                   "The current state of the port."
               ::= {     sm24dp4xaNASPortConfEntry 6 }

    sm24dp4xaNASPortConfReauthenticateCmd OBJECT-TYPE
               SYNTAX      ActivateCmd
               MAX-ACCESS  read-write
               STATUS      current
               DESCRIPTION
                   "Schedules a reauthentication whenever the quiet-period of
                    the port runs out (EAPOL-based authentication). For
                    MAC-based authentication, reauthentication will be attempted
                    immediately.The button only has effect for successfully
                    authenticated clients on the port and will not cause the
                    clients to get temporarily unauthorized."
               DEFVAL  { noAction }
               ::= {     sm24dp4xaNASPortConfEntry 7 }

    sm24dp4xaNASPortConfReinitializeCmd OBJECT-TYPE
               SYNTAX      ActivateCmd
               MAX-ACCESS  read-write
               STATUS      current
               DESCRIPTION
                   "Forces a reinitialization of the clients on the port and
                    thereby a reauthentication immediately. The clients will
                    transfer to the unauthorized state while the
                    reauthentication is in progress."
               DEFVAL  { noAction }
               ::= {     sm24dp4xaNASPortConfEntry 8 }

--sm24dp4xaNASSwitchStatusTable

    sm24dp4xaNASSwitchStatusTable OBJECT-TYPE
               SYNTAX      SEQUENCE OF     SM24DP4XANASSwitchStatusEntry
               MAX-ACCESS  not-accessible
               STATUS      current
               DESCRIPTION
                   "The NAS Switch Status Table.
                    INDEX for this table is ifIndex which is
                    equivalent to the panel port number."
               ::= {     sm24dp4xaNASStatus 1 }

    sm24dp4xaNASSwitchStatusEntry OBJECT-TYPE
               SYNTAX          SM24DP4XANASSwitchStatusEntry
               MAX-ACCESS  not-accessible
               STATUS      current
               DESCRIPTION
                   "The NAS Switch Status Entry."
               INDEX    {    ifIndex  }
               ::= {     sm24dp4xaNASSwitchStatusTable 1 }

    SM24DP4XANASSwitchStatusEntry             ::= SEQUENCE {
                 sm24dp4xaNASSwitchStatusAdminState   DisplayString,
                 sm24dp4xaNASSwitchStatusPortState    DisplayString,
                 sm24dp4xaNASSwitchStatusLastSource   DisplayString,
                 sm24dp4xaNASSwitchStatusLastID       DisplayString,
                 sm24dp4xaNASSwitchStatusQoSClass     DisplayString,
                 sm24dp4xaNASSwitchStatusPortVLANID   DisplayString
                 }

    sm24dp4xaNASSwitchStatusAdminState OBJECT-TYPE
               SYNTAX      DisplayString
               MAX-ACCESS  read-only
               STATUS      current
               DESCRIPTION
                   "The port's current administrative state."
               ::= {     sm24dp4xaNASSwitchStatusEntry 2 }

    sm24dp4xaNASSwitchStatusPortState OBJECT-TYPE
               SYNTAX      DisplayString
               MAX-ACCESS  read-only
               STATUS      current
               DESCRIPTION
                   "The current state of the port."
               ::= {     sm24dp4xaNASSwitchStatusEntry 3 }

    sm24dp4xaNASSwitchStatusLastSource OBJECT-TYPE
               SYNTAX      DisplayString
               MAX-ACCESS  read-only
               STATUS      current
               DESCRIPTION
                   "The source MAC address carried in the most recently
                    received EAPOL frame for EAPOL-based authentication,
                    and the most recently received frame from a new client
                    for MAC-based authentication."
               ::= {     sm24dp4xaNASSwitchStatusEntry 4 }

    sm24dp4xaNASSwitchStatusLastID OBJECT-TYPE
               SYNTAX      DisplayString
               MAX-ACCESS  read-only
               STATUS      current
               DESCRIPTION
                   "The user name (supplicant identity) carried in the most
                    recently received Response Identity EAPOL frame for
                    EAPOL-based authentication, and the source MAC address
                    from the most recently received frame from a new client
                    for MAC-based authentication."
               ::= {     sm24dp4xaNASSwitchStatusEntry 5 }

    sm24dp4xaNASSwitchStatusQoSClass OBJECT-TYPE
               SYNTAX      DisplayString
               MAX-ACCESS  read-only
               STATUS      current
               DESCRIPTION
                   "QoS Class assigned to the port by the RADIUS server
                    if enabled."
               ::= {     sm24dp4xaNASSwitchStatusEntry 6 }

    sm24dp4xaNASSwitchStatusPortVLANID OBJECT-TYPE
               SYNTAX      DisplayString
               MAX-ACCESS  read-only
               STATUS      current
               DESCRIPTION
                   "The VLAN ID that NAS has put the port in."
               ::= {     sm24dp4xaNASSwitchStatusEntry 7 }

--sm24dp4xaNASPortCounterTable

    sm24dp4xaNASPortCounterTable OBJECT-TYPE
               SYNTAX      SEQUENCE OF     SM24DP4XANASPortCounterEntry
               MAX-ACCESS  not-accessible
               STATUS      current
               DESCRIPTION
                   "The NAS Port Counter Table.
                    INDEX for this table is ifIndex which is
                    equivalent to the panel port number."
               ::= {     sm24dp4xaNASStatus 2 }

    sm24dp4xaNASPortCounterEntry OBJECT-TYPE
               SYNTAX          SM24DP4XANASPortCounterEntry
               MAX-ACCESS  not-accessible
               STATUS      current
               DESCRIPTION
                   "The NAS Port Counter Entry."
               INDEX    {    ifIndex  }
               ::= {     sm24dp4xaNASPortCounterTable 1 }

    SM24DP4XANASPortCounterEntry             ::= SEQUENCE {
                 sm24dp4xaNASReceiveEAPOLTotal          Integer32,
                 sm24dp4xaNASReceiveEAPOLResponseID     Integer32,
                 sm24dp4xaNASReceiveEAPOLResponses      Integer32,
                 sm24dp4xaNASReceiveEAPOLStart          Integer32,
                 sm24dp4xaNASReceiveEAPOLLogoff         Integer32,
                 sm24dp4xaNASReceiveEAPOLInvalidType    Integer32,
                 sm24dp4xaNASReceiveEAPOLInvalidLength  Integer32,
                 sm24dp4xaNASTransmitEAPOLTotal         Integer32,
                 sm24dp4xaNASTransmitEAPOLRequestID     Integer32,
                 sm24dp4xaNASTransmitEAPOLRequests      Integer32,
                 sm24dp4xaNASPortReceiveBackendServerAccessChallenges    Integer32,
                 sm24dp4xaNASPortReceiveBackendServerOtherRequests       Integer32,
                 sm24dp4xaNASPortReceiveBackendServerAuthSuccesses       Integer32,
                 sm24dp4xaNASPortReceiveBackendServerAuthFailures        Integer32,
                 sm24dp4xaNASPortTransmitBackendServerResponses          Integer32,
                 sm24dp4xaNASSupplicantInfoMAC          DisplayString,
                 sm24dp4xaNASSupplicantInfoVlanID       Integer32,
                 sm24dp4xaNASSupplicantInfoVersion      Integer32,
                 sm24dp4xaNASSupplicantInfoIdentity     DisplayString,
                 sm24dp4xaNASPortCounterClearCmd        ActivateCmd
                 }

    sm24dp4xaNASReceiveEAPOLTotal OBJECT-TYPE
               SYNTAX      Integer32(-1..1000000)
               MAX-ACCESS  read-only
               STATUS      current
               DESCRIPTION
                   "The number of valid EAPOL frames of any type that have
                    been received by the switch.
                    -1: no support."
               ::= {     sm24dp4xaNASPortCounterEntry 2 }

    sm24dp4xaNASReceiveEAPOLResponseID OBJECT-TYPE
               SYNTAX      Integer32(-1..1000000)
               MAX-ACCESS  read-only
               STATUS      current
               DESCRIPTION
                   "The number of valid EAPOL Response Identity frames that
                    have been received by the switch.
                    -1: no support."
               ::= {     sm24dp4xaNASPortCounterEntry 3 }

    sm24dp4xaNASReceiveEAPOLResponses OBJECT-TYPE
               SYNTAX      Integer32(-1..1000000)
               MAX-ACCESS  read-only
               STATUS      current
               DESCRIPTION
                   "The number of valid EAPOL response frames (other than
                    Response Identity frames) that have been received by
                    the switch.
                    -1: no support."
               ::= {     sm24dp4xaNASPortCounterEntry 4 }

    sm24dp4xaNASReceiveEAPOLStart OBJECT-TYPE
               SYNTAX      Integer32(-1..1000000)
               MAX-ACCESS  read-only
               STATUS      current
               DESCRIPTION
                   "The number of EAPOL Start frames that have been received
                    by the switch.
                    -1: no support."
               ::= {     sm24dp4xaNASPortCounterEntry 5 }

    sm24dp4xaNASReceiveEAPOLLogoff OBJECT-TYPE
               SYNTAX      Integer32(-1..1000000)
               MAX-ACCESS  read-only
               STATUS      current
               DESCRIPTION
                   "The number of valid EAPOL Logoff frames that have been
                    received by the switch.
                    -1: no support."
               ::= {     sm24dp4xaNASPortCounterEntry 6 }

    sm24dp4xaNASReceiveEAPOLInvalidType OBJECT-TYPE
               SYNTAX      Integer32(-1..1000000)
               MAX-ACCESS  read-only
               STATUS      current
               DESCRIPTION
                   "The number of EAPOL frames that have been received by
                    the switch in which the frame type is not recognized.
                    -1: no support."
               ::= {     sm24dp4xaNASPortCounterEntry 7 }

    sm24dp4xaNASReceiveEAPOLInvalidLength OBJECT-TYPE
               SYNTAX      Integer32(-1..1000000)
               MAX-ACCESS  read-only
               STATUS      current
               DESCRIPTION
                   "The number of EAPOL frames that have been received
                    by the switch in which the Packet Body Length field
                    is invalid.
                    -1: no support."
               ::= {     sm24dp4xaNASPortCounterEntry 8 }

    sm24dp4xaNASTransmitEAPOLTotal OBJECT-TYPE
               SYNTAX      Integer32(-1..1000000)
               MAX-ACCESS  read-only
               STATUS      current
               DESCRIPTION
                   "The number of EAPOL frames of any type that have been
                    transmitted by the switch.
                    -1: no support."
               ::= {     sm24dp4xaNASPortCounterEntry 9 }

    sm24dp4xaNASTransmitEAPOLRequestID OBJECT-TYPE
               SYNTAX      Integer32(-1..1000000)
               MAX-ACCESS  read-only
               STATUS      current
               DESCRIPTION
                   "The number of EAPOL Request Identity frames that have
                    been transmitted by the switch.
                    -1: no support."
               ::= {     sm24dp4xaNASPortCounterEntry 10 }

    sm24dp4xaNASTransmitEAPOLRequests OBJECT-TYPE
               SYNTAX      Integer32(-1..1000000)
               MAX-ACCESS  read-only
               STATUS      current
               DESCRIPTION
                   "The number of valid EAPOL Request frames (other than
                    Request Identity frames) that have been transmitted
                    by the switch.
                    -1: no support."
               ::= {     sm24dp4xaNASPortCounterEntry 11 }

    sm24dp4xaNASPortReceiveBackendServerAccessChallenges OBJECT-TYPE
               SYNTAX      Integer32(-1..1000000)
               MAX-ACCESS  read-only
               STATUS      current
               DESCRIPTION
                   "802.1X-based: Counts the number of times that the switch
                    receives the first request from the backend server following
                    the first response from the supplicant. Indicates that the
                    backend server has communication with the switch.
                    MAC-based:Counts all Access Challenges received from the
                    backend server for this port (left-most table).
                    -1: no support."
               ::= {     sm24dp4xaNASPortCounterEntry 12 }

    sm24dp4xaNASPortReceiveBackendServerOtherRequests OBJECT-TYPE
               SYNTAX      Integer32(-1..1000000)
               MAX-ACCESS  read-only
               STATUS      current
               DESCRIPTION
                   "802.1X-based: Counts the number of times that the switch
                    sends an EAP Request packet following the first to the
                    supplicant. Indicates that the backend server chose an
                    EAP-method.
                    MAC-based: Not applicable.
                    -1: no support."
               ::= {     sm24dp4xaNASPortCounterEntry 13 }

    sm24dp4xaNASPortReceiveBackendServerAuthSuccesses OBJECT-TYPE
               SYNTAX      Integer32(-1..1000000)
               MAX-ACCESS  read-only
               STATUS      current
               DESCRIPTION
                   "802.1X- and MAC-based: Counts the number of times that
                    the switch receives a success indication.Indicates that
                    the supplicant has successfully authenticated to
                    the backend server.
                    -1: no support."
               ::= {     sm24dp4xaNASPortCounterEntry 14 }

    sm24dp4xaNASPortReceiveBackendServerAuthFailures OBJECT-TYPE
               SYNTAX      Integer32(-1..1000000)
               MAX-ACCESS  read-only
               STATUS      current
               DESCRIPTION
                   "802.1X- and MAC-based:Counts the number of times that the
                    switch receives a failure message.This indicates that the
                    supplicant has not authenticated to the backend
                    server.
                    -1: no support."
               ::= {     sm24dp4xaNASPortCounterEntry 15 }

    sm24dp4xaNASPortTransmitBackendServerResponses OBJECT-TYPE
               SYNTAX      Integer32(-1..1000000)
               MAX-ACCESS  read-only
               STATUS      current
               DESCRIPTION
                   "802.1X-based:Counts the number of times that the switch
                    attempts to send a supplicant's first response packet to
                    the backend server. Indicates the switch attempted
                    communication with the backend server. Possible
                    retransmissions are not counted.
                    MAC-based: Counts all the backend server packets sent from
                    the switch towards the backend server for a given port
                    (left-most table). Possible retransmissions are not
                    counted.
                    -1: no support."
               ::= {     sm24dp4xaNASPortCounterEntry 16 }

    sm24dp4xaNASSupplicantInfoMAC OBJECT-TYPE
               SYNTAX      DisplayString
               MAX-ACCESS  read-only
               STATUS      current
               DESCRIPTION
                   "The MAC address of the last supplicant. "
               ::= {     sm24dp4xaNASPortCounterEntry 17 }

    sm24dp4xaNASSupplicantInfoVlanID OBJECT-TYPE
               SYNTAX      Integer32(-1..1000000)
               MAX-ACCESS  read-only
               STATUS      current
               DESCRIPTION
                   "The VLAN ID on which the last frame from the last
                    supplicant was received.
                    -1: no support."
               ::= {     sm24dp4xaNASPortCounterEntry 18 }

    sm24dp4xaNASSupplicantInfoVersion OBJECT-TYPE
               SYNTAX      Integer32(-1..1000000)
               MAX-ACCESS  read-only
               STATUS      current
               DESCRIPTION
                   "802.1X-based:The protocol version number carried in
                    the most recently received EAPOL frame.
                    MAC-based: Not applicable.
                    -1: no support."
               ::= {     sm24dp4xaNASPortCounterEntry 19 }

    sm24dp4xaNASSupplicantInfoIdentity OBJECT-TYPE
               SYNTAX      DisplayString
               MAX-ACCESS  read-only
               STATUS      current
               DESCRIPTION
                   "802.1X-based:The user name (supplicant identity) carried
                    in the most recently received Response Identity EAPOL frame.
                    MAC-based: Not applicable. "
               ::= {     sm24dp4xaNASPortCounterEntry 20 }

    sm24dp4xaNASPortCounterClearCmd OBJECT-TYPE
               SYNTAX      ActivateCmd
               MAX-ACCESS  read-write
               STATUS      current
               DESCRIPTION
                   "Clear the counters for the selected port."
               ::= {     sm24dp4xaNASPortCounterEntry 21 }


-- =======================================================================================================================
sm24dp4xaMACConf 						OBJECT IDENTIFIER ::= { sm24dp4xaConfiguration 17 }

    sm24dp4xaMAC                                                    OBJECT IDENTIFIER   ::= { sm24dp4xaMACConf 1 }

--
-- =======================================================================================================================
-- Start sm24dp4xaMAC group
-- =======================================================================================================================
    sm24dp4xaMACDisableAutomaticAging   OBJECT-TYPE
               SYNTAX       AdminMode
               MAX-ACCESS   read-write
               STATUS       current
               DESCRIPTION
                   "Disable the automatic aging of dynamic entries."
                ::= {     sm24dp4xaMAC 1 }

    sm24dp4xaMACAgingTime  OBJECT-TYPE
               SYNTAX       Integer32 (-1 | 10..1000000)
               MAX-ACCESS   read-write
               STATUS       current
               DESCRIPTION
                   "Configure aging time by entering a value here in seconds.
                   range: 10-1000000 seconds.
                   -1: Automatic Aging is disable."
                ::= {     sm24dp4xaMAC 2 }

--sm24dp4xaMACLearningTable
    sm24dp4xaMACLearningTable OBJECT-TYPE
               SYNTAX      SEQUENCE OF     SM24DP4XAMACLearningEntry
               MAX-ACCESS  not-accessible
               STATUS      current
               DESCRIPTION
                   "The mac learning table.
                    INDEX for this table is ifIndex which is
                    equivalent to the panel port number."
               ::= {     sm24dp4xaMAC 3 }

    sm24dp4xaMACLearningEntry OBJECT-TYPE
               SYNTAX          SM24DP4XAMACLearningEntry
               MAX-ACCESS  not-accessible
               STATUS      current
               DESCRIPTION
                   "The mac learning entry."
               INDEX    {     ifIndex  }
               ::= {     sm24dp4xaMACLearningTable 1 }

    SM24DP4XAMACLearningEntry             ::= SEQUENCE {
                sm24dp4xaMACTableLearning     INTEGER
                }

    sm24dp4xaMACTableLearning OBJECT-TYPE
               SYNTAX      INTEGER{ auto(0), disable(1), secure(2)}
               MAX-ACCESS  read-write
               STATUS      current
               DESCRIPTION
                   "auto(0)   : Learning is done automatically as soon as a
                                frame with unknown SMAC is received.
                    disable(1): Disable, No learning is done.
                    secure(2) : Secure, Only static MAC entries are learned,
                                all other frames are dropped."
               ::= {     sm24dp4xaMACLearningEntry 2 }

--sm24dp4xaMACStaticConfigTable
    sm24dp4xaMACStaticConfigTable OBJECT-TYPE
               SYNTAX      SEQUENCE OF     SM24DP4XAMACStaticConfigEntry
               MAX-ACCESS  not-accessible
               STATUS      current
               DESCRIPTION
                   "The static Mac config table."
               ::= {     sm24dp4xaMAC 4 }

    sm24dp4xaMACStaticConfigEntry OBJECT-TYPE
               SYNTAX          SM24DP4XAMACStaticConfigEntry
               MAX-ACCESS  not-accessible
               STATUS      current
               DESCRIPTION
                   "The static Mac config entry."
               INDEX    {     sm24dp4xaMACStaticConfigIndex  }
               ::= {     sm24dp4xaMACStaticConfigTable 1 }

    SM24DP4XAMACStaticConfigEntry             ::= SEQUENCE {
                sm24dp4xaMACStaticConfigSwitchIndex Integer32,
                sm24dp4xaMACStaticConfigIndex       Integer32,
                sm24dp4xaMACStaticConfigVID         Integer32,
                sm24dp4xaMACStaticConfigMACaddress  DisplayString,
                sm24dp4xaMACStaticConfigPortList    DisplayString,
                sm24dp4xaMACStaticConfigRowStatus   RowStatus
                }

    sm24dp4xaMACStaticConfigSwitchIndex OBJECT-TYPE
               SYNTAX      Integer32(1..16)
               MAX-ACCESS  not-accessible
               STATUS      current
               DESCRIPTION
                   "Switch Index."
               ::= {     sm24dp4xaMACStaticConfigEntry 1 }



    sm24dp4xaMACStaticConfigIndex OBJECT-TYPE
               SYNTAX      Integer32(1..64)
               MAX-ACCESS  not-accessible
               STATUS      current
               DESCRIPTION
                   "The static entries in the MAC table are shown in this table.
                    The static MAC table can contain 64 entries."
               ::= {     sm24dp4xaMACStaticConfigEntry 2 }

    sm24dp4xaMACStaticConfigVID OBJECT-TYPE
               SYNTAX      Integer32(1..4095)
               MAX-ACCESS  read-create
               STATUS      current
               DESCRIPTION
                   "The VLAN ID of the entry.
                    range: 1-4095."
               ::= {     sm24dp4xaMACStaticConfigEntry 3 }

    sm24dp4xaMACStaticConfigMACaddress OBJECT-TYPE
               SYNTAX      DisplayString
               MAX-ACCESS  read-create
               STATUS      current
               DESCRIPTION
                   "The MAC address of the entry."
               ::= {     sm24dp4xaMACStaticConfigEntry 4 }

    sm24dp4xaMACStaticConfigPortList OBJECT-TYPE
               SYNTAX      DisplayString
               MAX-ACCESS  read-create
               STATUS      current
               DESCRIPTION
                   "Checkmarks indicate which ports are members of the entry.
                    Check or uncheck as needed to
                    modify the entry."
               ::= {     sm24dp4xaMACStaticConfigEntry 5 }

    sm24dp4xaMACStaticConfigRowStatus OBJECT-TYPE
               SYNTAX      RowStatus
               MAX-ACCESS  read-create
               STATUS      current
               DESCRIPTION
                   "This object indicates the status of this entry,
                    and is used to create/delete entries. Any
                    object in an entry of this table may be modified
                    while the value of the corresponding instance
                    of this object is active(1).
                    createAndGo, notReady not supported."
               ::= {     sm24dp4xaMACStaticConfigEntry 6 }


-- =======================================================================================================================
sm24dp4xaSpanningTree 						OBJECT IDENTIFIER ::= { sm24dp4xaConfiguration 18 }

sm24dp4xaBridgeSettings                     OBJECT IDENTIFIER ::= { sm24dp4xaSpanningTree 1 }

sm24dp4xaSTPProtocolVersion    OBJECT-TYPE
               SYNTAX      Integer32
               MAX-ACCESS  read-write
               STATUS      current
               DESCRIPTION
                   "0:STP
				    2:RSTP
					3:MSTP"
               ::= {     sm24dp4xaBridgeSettings 1 }

sm24dp4xaBridgePriority    OBJECT-TYPE
               SYNTAX      Integer32
               MAX-ACCESS  read-write
               STATUS      current
               DESCRIPTION
                   "Bridge Priority, range: 0-61440, multiple of 4096."
               ::= {     sm24dp4xaBridgeSettings 2 }

sm24dp4xaBridgeForwardDelay    OBJECT-TYPE
               SYNTAX      Integer32
               MAX-ACCESS  read-write
               STATUS      current
               DESCRIPTION
                   "Bridge Forward Delay, range: 4-30 seconds."
               ::= {     sm24dp4xaBridgeSettings 3 }

sm24dp4xaBridgeMaxAge    OBJECT-TYPE
               SYNTAX      Integer32
               MAX-ACCESS  read-write
               STATUS      current
               DESCRIPTION
                   "Bridge MaxAge, range:6-40 seconds."
               ::= {     sm24dp4xaBridgeSettings 4 }

sm24dp4xaBridgeMaxHops    OBJECT-TYPE
               SYNTAX      Integer32
               MAX-ACCESS  read-write
               STATUS      current
               DESCRIPTION
                   "Bridge Max Hops, range:6-40 hops."
               ::= {     sm24dp4xaBridgeSettings 5 }

sm24dp4xaBridgetxHoldCount    OBJECT-TYPE
               SYNTAX      Integer32
               MAX-ACCESS  read-write
               STATUS      current
               DESCRIPTION
                   "Bridge Transmit Hold Count,range: 1-10 bpdu's per second. "
               ::= {     sm24dp4xaBridgeSettings 6 }

sm24dp4xaBridgeBPDUFilter    OBJECT-TYPE
               SYNTAX      Integer32
               MAX-ACCESS  read-write
               STATUS      current
               DESCRIPTION
                   "Bridge BPD UFilter
              		0:disable
                    1:enable					"
               ::= {     sm24dp4xaBridgeSettings 7 }

sm24dp4xaBridgeBPDUGuard    OBJECT-TYPE
               SYNTAX      Integer32
               MAX-ACCESS  read-write
               STATUS      current
               DESCRIPTION
                   "Bridge BPDU Guard
              		0:disable
                    1:enable					   "
               ::= {     sm24dp4xaBridgeSettings 8 }

sm24dp4xaBridgeerrorRecoveryDelay    OBJECT-TYPE
               SYNTAX      Integer32
               MAX-ACCESS  read-write
               STATUS      current
               DESCRIPTION
                   "Bridge error Recovery Delay
				   range:30-86400 seconds
				   0:disable
				   "
               ::= {     sm24dp4xaBridgeSettings 9 }

sm24dp4xaBridgeHelloTime    OBJECT-TYPE
               SYNTAX      Integer32
               MAX-ACCESS  read-write
               STATUS      current
               DESCRIPTION
                   "The interval between sending STP BPDU's. Valid values are in the range 1 to 10 seconds, 
				   default:2 seconds."
               ::= {     sm24dp4xaBridgeSettings 10 }			   

sm24dp4xaMSTIMapping                        OBJECT IDENTIFIER ::= { sm24dp4xaSpanningTree 2 }
sm24dp4xaConfigName    OBJECT-TYPE
               SYNTAX      DisplayString
               MAX-ACCESS  read-write
               STATUS      current
               DESCRIPTION
                   "Configuration Name, identify the VLAN to MSTI mapping"
               ::= {     sm24dp4xaMSTIMapping 1 }

sm24dp4xaConfigRevision    OBJECT-TYPE
               SYNTAX      Integer32
               MAX-ACCESS  read-write
               STATUS      current
               DESCRIPTION
                   "Configuration Revision. range:0-65535 "
               ::= {     sm24dp4xaMSTIMapping 2 }

sm24dp4xaMSTIMappingVLAN                    OBJECT IDENTIFIER ::= { sm24dp4xaSpanningTree 3 }
sm24dp4xaConfigMstiName1    OBJECT-TYPE
               SYNTAX      DisplayString
               MAX-ACCESS  read-write
               STATUS      current
               DESCRIPTION
                   "The list of VLANs mapped to the MSTI1.
				    The VLANs can be given as a single (xx, xx being between 1 and 4094) VLAN, or a range (xx-yy), each of which must be separated with comma and/or space. "
               ::= {     sm24dp4xaMSTIMappingVLAN 1 }

sm24dp4xaConfigMstiName2    OBJECT-TYPE
               SYNTAX      DisplayString
               MAX-ACCESS  read-write
               STATUS      current
               DESCRIPTION
                   "The list of VLANs mapped to the MSTI2.
				    The VLANs can be given as a single (xx, xx being between 1 and 4094) VLAN, or a range (xx-yy), each of which must be separated with comma and/or space.  "
               ::= {     sm24dp4xaMSTIMappingVLAN 2 }

sm24dp4xaConfigMstiName3    OBJECT-TYPE
               SYNTAX      DisplayString
               MAX-ACCESS  read-write
               STATUS      current
               DESCRIPTION
                   "The list of VLANs mapped to the MSTI3.
				    The VLANs can be given as a single (xx, xx being between 1 and 4094) VLAN, or a range (xx-yy), each of which must be separated with comma and/or space. "
               ::= {     sm24dp4xaMSTIMappingVLAN 3 }

sm24dp4xaConfigMstiName4    OBJECT-TYPE
               SYNTAX      DisplayString
               MAX-ACCESS  read-write
               STATUS      current
               DESCRIPTION
                   "The list of VLANs mapped to the MSTI4.
				    The VLANs can be given as a single (xx, xx being between 1 and 4094) VLAN, or a range (xx-yy), each of which must be separated with comma and/or space. "
               ::= {     sm24dp4xaMSTIMappingVLAN 4 }

sm24dp4xaConfigMstiName5    OBJECT-TYPE
               SYNTAX      DisplayString
               MAX-ACCESS  read-write
               STATUS      current
               DESCRIPTION
                   "The list of VLANs mapped to the MSTI5.
				    The VLANs can be given as a single (xx, xx being between 1 and 4094) VLAN, or a range (xx-yy), each of which must be separated with comma and/or space. "
               ::= {     sm24dp4xaMSTIMappingVLAN 5 }

sm24dp4xaConfigMstiName6    OBJECT-TYPE
               SYNTAX      DisplayString
               MAX-ACCESS  read-write
               STATUS      current
               DESCRIPTION
                   "The list of VLANs mapped to the MSTI6.
				    The VLANs can be given as a single (xx, xx being between 1 and 4094) VLAN, or a range (xx-yy), each of which must be separated with comma and/or space. "
               ::= {     sm24dp4xaMSTIMappingVLAN 6 }

sm24dp4xaConfigMstiName7    OBJECT-TYPE
               SYNTAX      DisplayString
               MAX-ACCESS  read-write
               STATUS      current
               DESCRIPTION
                   "The list of VLANs mapped to the MSTI7.
				    The VLANs can be given as a single (xx, xx being between 1 and 4094) VLAN, or a range (xx-yy), each of which must be separated with comma and/or space. "
               ::= {     sm24dp4xaMSTIMappingVLAN 7 }

sm24dp4xaMSTIPriorities                     OBJECT IDENTIFIER ::= { sm24dp4xaSpanningTree 4 }

sm24dp4xaCSTIPriority   OBJECT-TYPE
               SYNTAX      Integer32
               MAX-ACCESS  read-write
               STATUS      current
               DESCRIPTION
                   "CSTI Priority. range: 0-61440, multiple of 4096. Lower numeric values have better priority."
               ::= {     sm24dp4xaMSTIPriorities 1 }

sm24dp4xaMSTI1Priority   OBJECT-TYPE
               SYNTAX      Integer32
               MAX-ACCESS  read-write
               STATUS      current
               DESCRIPTION
                   "MSTI1 Priority. range: 0-61440, multiple of 4096. Lower numeric values have better priority."
               ::= {     sm24dp4xaMSTIPriorities 2 }

sm24dp4xaMSTI2Priority   OBJECT-TYPE
               SYNTAX      Integer32
               MAX-ACCESS  read-write
               STATUS      current
               DESCRIPTION
                   "MSTI2 Priority. range: 0-61440, multiple of 4096. Lower numeric values have better priority."
               ::= {     sm24dp4xaMSTIPriorities 3 }

sm24dp4xaMSTI3Priority   OBJECT-TYPE
               SYNTAX      Integer32
               MAX-ACCESS  read-write
               STATUS      current
               DESCRIPTION
                   "MSTI3 Priority. range: 0-61440, multiple of 4096. Lower numeric values have better priority."
               ::= {     sm24dp4xaMSTIPriorities 4 }
sm24dp4xaMSTI4Priority   OBJECT-TYPE
               SYNTAX      Integer32
               MAX-ACCESS  read-write
               STATUS      current
               DESCRIPTION
                   "MSTI4 Priority. range: 0-61440, multiple of 4096. Lower numeric values have better priority."
               ::= {     sm24dp4xaMSTIPriorities 5 }
sm24dp4xaMSTI5Priority   OBJECT-TYPE
               SYNTAX      Integer32
               MAX-ACCESS  read-write
               STATUS      current
               DESCRIPTION
                   "MSTI5 Priority. range: 0-61440, multiple of 4096. Lower numeric values have better priority."
               ::= {     sm24dp4xaMSTIPriorities 6 }

sm24dp4xaMSTI6Priority   OBJECT-TYPE
               SYNTAX      Integer32
               MAX-ACCESS  read-write
               STATUS      current
               DESCRIPTION
                   "MSTI6 Priority. range: 0-61440, multiple of 4096. Lower numeric values have better priority."
               ::= {     sm24dp4xaMSTIPriorities 7 }
sm24dp4xaMSTI7Priority   OBJECT-TYPE
               SYNTAX      Integer32
               MAX-ACCESS  read-write
               STATUS      current
               DESCRIPTION
                   "MSTI7 Priority. range: 0-61440, multiple of 4096. Lower numeric values have better priority."
               ::= {     sm24dp4xaMSTIPriorities 8 }


sm24dp4xaCISTPorts                          OBJECT IDENTIFIER ::= { sm24dp4xaSpanningTree 5 }

sm24dp4xaCISTAggregatedEnable   OBJECT-TYPE
               SYNTAX      Integer32 (0|1)
               MAX-ACCESS  read-write
               STATUS      current
               DESCRIPTION
                   "CIST Port Enable. range: 0-1.
				   0:disable
				   1:enable."
               ::= {     sm24dp4xaCISTPorts 1 }

sm24dp4xaCISTAggregatedPathCost   OBJECT-TYPE
               SYNTAX      Integer32 (0..200000000)
               MAX-ACCESS  read-write
               STATUS      current
               DESCRIPTION
                   "CIST Port Path Cost. range: 0-200000000. 0 is Auto."
               ::= {     sm24dp4xaCISTPorts 2 }

sm24dp4xaCISTAggregatedPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sm24dp4xaCISTPorts 3 }

sm24dp4xaCISTAggregatedAdminEdge   OBJECT-TYPE
               SYNTAX      Integer32 (0|1)
               MAX-ACCESS  read-write
               STATUS      current
               DESCRIPTION
                   "CIST Port Admin Edge. range: 0-1.
				   0:Non-Edge
				   1:Edge."
               ::= {     sm24dp4xaCISTPorts 4 }

sm24dp4xaCISTAggregatedAutoEdge   OBJECT-TYPE
               SYNTAX      Integer32 (0|1)
               MAX-ACCESS  read-write
               STATUS      current
               DESCRIPTION
                   "CIST Port Auto Edge. range: 0-1.
				   0:disable
				   1:enable."
               ::= {     sm24dp4xaCISTPorts 5 }

sm24dp4xaCISTAggregatedrestrictedRole   OBJECT-TYPE
               SYNTAX      Integer32 (0|1)
               MAX-ACCESS  read-write
               STATUS      current
               DESCRIPTION
                   "CIST Port restricted Role. range: 0-1.
				   0:disable
				   1:enable."
               ::= {     sm24dp4xaCISTPorts 6 }

sm24dp4xaCISTAggregatedrestrictedTcn   OBJECT-TYPE
               SYNTAX      Integer32 (0|1)
               MAX-ACCESS  read-write
               STATUS      current
               DESCRIPTION
                   "CIST Port restricted Tcn. range: 0-1.
				   0:disable
				   1:enable."
               ::= {     sm24dp4xaCISTPorts 7 }

sm24dp4xaCISTAggregatedbpduGuard   OBJECT-TYPE
               SYNTAX      Integer32 (0|1)
               MAX-ACCESS  read-write
               STATUS      current
               DESCRIPTION
                   "CIST Port bpdu Guard. range: 0-1.
				   0:disable
				   1:enable."
               ::= {     sm24dp4xaCISTPorts 8 }

sm24dp4xaCISTAggregatedPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sm24dp4xaCISTPorts 9 }


sm24dp4xaCISTPortsTable OBJECT-TYPE
   SYNTAX      SEQUENCE OF SM24DP4XACISTPortsEntry
   MAX-ACCESS  not-accessible
   STATUS      current
   DESCRIPTION
        "CIST port table."
    ::= { sm24dp4xaCISTPorts 10 }

sm24dp4xaCISTPortsEntry OBJECT-TYPE
    SYNTAX        SM24DP4XACISTPortsEntry
    MAX-ACCESS    not-accessible
    STATUS        current
    DESCRIPTION
        "An entry in the CIST Ports Table."
    INDEX        { sm24dp4xaCISTPortIndex }
    ::= { sm24dp4xaCISTPortsTable 1 }

SM24DP4XACISTPortsEntry ::=
    SEQUENCE {
        sm24dp4xaCISTPortIndex                 Integer32,
        sm24dp4xaCISTPortEnable                Integer32,
        sm24dp4xaCISTPortPathCost              Integer32,
        sm24dp4xaCISTPortPortPriority          Integer32,
        sm24dp4xaCISTPortAdminEdge             Integer32,
        sm24dp4xaCISTPortAutoEdge              Integer32,
        sm24dp4xaCISTPortrestrictedRole        Integer32,
        sm24dp4xaCISTPortrestrictedTcn         Integer32,
        sm24dp4xaCISTPortbpduGuard             Integer32,
        sm24dp4xaCISTPortPointToPoint          Integer32
    }

sm24dp4xaCISTPortIndex   OBJECT-TYPE
               SYNTAX      Integer32 (1..53)
               MAX-ACCESS  not-accessible
               STATUS      current
               DESCRIPTION
                   "CIST Port Index. range: 1-53. 53 is Aggregated Port Configuration."
               ::= {     sm24dp4xaCISTPortsEntry 1 }

sm24dp4xaCISTPortEnable   OBJECT-TYPE
               SYNTAX      Integer32 (0|1)
               MAX-ACCESS  read-write
               STATUS      current
               DESCRIPTION
                   "CIST Port Enable. range: 0-1.
				   0:disable
				   1:enable."
               ::= {     sm24dp4xaCISTPortsEntry 2 }

sm24dp4xaCISTPortPathCost   OBJECT-TYPE
               SYNTAX      Integer32 (0..200000000)
               MAX-ACCESS  read-write
               STATUS      current
               DESCRIPTION
                   "CIST Port Path Cost. range: 0-200000000. 0 is Auto."
               ::= {     sm24dp4xaCISTPortsEntry 3 }

sm24dp4xaCISTPortPortPriority   OBJECT-TYPE
               SYNTAX      Integer32 (0|16|32|48|64|80|96|112|128|144|160|176|192|208|224|240)
               MAX-ACCESS  read-write
               STATUS      current
               DESCRIPTION
                   "CIST Port Priority. range: 0-240, multiple of 16."
               ::= {     sm24dp4xaCISTPortsEntry 4 }

sm24dp4xaCISTPortAdminEdge   OBJECT-TYPE
               SYNTAX      Integer32 (0|1)
               MAX-ACCESS  read-write
               STATUS      current
               DESCRIPTION
                   "CIST Port Admin Edge. range: 0-1.
				   0:Non-Edge
				   1:Edge."
               ::= {     sm24dp4xaCISTPortsEntry 5 }

sm24dp4xaCISTPortAutoEdge   OBJECT-TYPE
               SYNTAX      Integer32 (0|1)
               MAX-ACCESS  read-write
               STATUS      current
               DESCRIPTION
                   "CIST Port Auto Edge. range: 0-1.
				   0:disable
				   1:enable."
               ::= {     sm24dp4xaCISTPortsEntry 6 }

sm24dp4xaCISTPortrestrictedRole   OBJECT-TYPE
               SYNTAX      Integer32 (0|1)
               MAX-ACCESS  read-write
               STATUS      current
               DESCRIPTION
                   "CIST Port restricted Role. range: 0-1.
				   0:disable
				   1:enable."
               ::= {     sm24dp4xaCISTPortsEntry 7 }

sm24dp4xaCISTPortrestrictedTcn   OBJECT-TYPE
               SYNTAX      Integer32 (0|1)
               MAX-ACCESS  read-write
               STATUS      current
               DESCRIPTION
                   "CIST Port restricted Tcn. range: 0-1.
				   0:disable
				   1:enable."
               ::= {     sm24dp4xaCISTPortsEntry 8 }

sm24dp4xaCISTPortbpduGuard   OBJECT-TYPE
               SYNTAX      Integer32 (0|1)
               MAX-ACCESS  read-write
               STATUS      current
               DESCRIPTION
                   "CIST Port bpdu Guard. range: 0-1.
				   0:disable
				   1:enable."
               ::= {     sm24dp4xaCISTPortsEntry 9 }

sm24dp4xaCISTPortPointToPoint   OBJECT-TYPE
               SYNTAX      Integer32 (0..2)
               MAX-ACCESS  read-write
               STATUS      current
               DESCRIPTION
                   "CIST Port Point To Point. range: 0-2.
				   0:Forced True
				   1:Forced False.
				   2:Auto"
               ::= {     sm24dp4xaCISTPortsEntry 10 }

sm24dp4xaMSTIPorts                          OBJECT IDENTIFIER ::= { sm24dp4xaSpanningTree 6 }


sm24dp4xaMSTIAggregatedPortsTable OBJECT-TYPE
   SYNTAX      SEQUENCE OF SM24DP4XAMSTIAggregatedPortsEntry
   MAX-ACCESS  not-accessible
   STATUS      current
   DESCRIPTION
       "A table of MSTI ports."
    ::= { sm24dp4xaMSTIPorts 1 }

sm24dp4xaMSTIAggregatedPortsEntry OBJECT-TYPE
    SYNTAX        SM24DP4XAMSTIAggregatedPortsEntry
    MAX-ACCESS    not-accessible
    STATUS        current
    DESCRIPTION
        "An entry in the MSTI ports Table."
    INDEX        { sm24dp4xaMSTIAggregatedPortsMSTIndex }
    ::= { sm24dp4xaMSTIAggregatedPortsTable 1 }

SM24DP4XAMSTIAggregatedPortsEntry ::=
    SEQUENCE {
        sm24dp4xaMSTIAggregatedPortsMSTIndex                        Integer32,
        sm24dp4xaMSTIAggregatedPortsPathCost                        Integer32,
        sm24dp4xaMSTIAggregatedPortsPortPriority                    Integer32
    }

sm24dp4xaMSTIAggregatedPortsMSTIndex OBJECT-TYPE
   SYNTAX      Integer32 (1..7)
   MAX-ACCESS  not-accessible
   STATUS      current
   DESCRIPTION
       "MST index, range:1-7"
   ::= {sm24dp4xaMSTIAggregatedPortsEntry 1 }

sm24dp4xaMSTIAggregatedPortsPathCost   OBJECT-TYPE
   SYNTAX      Integer32 (0..200000000)
   MAX-ACCESS  read-write
   STATUS      current
   DESCRIPTION
       "MST Path Cost. range: 0-200000000. 0 is Auto."
   ::= {sm24dp4xaMSTIAggregatedPortsEntry 3 }

sm24dp4xaMSTIAggregatedPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sm24dp4xaMSTIAggregatedPortsEntry 4 }


sm24dp4xaMSTIPortsTable OBJECT-TYPE
   SYNTAX      SEQUENCE OF SM24DP4XAMSTIPortsEntry
   MAX-ACCESS  not-accessible
   STATUS      current
   DESCRIPTION
       "A table of MSTI ports."
    ::= { sm24dp4xaMSTIPorts 2 }

sm24dp4xaMSTIPortsEntry OBJECT-TYPE
    SYNTAX        SM24DP4XAMSTIPortsEntry
    MAX-ACCESS    not-accessible
    STATUS        current
    DESCRIPTION
        "An entry in the MSTI ports Table."
    INDEX        { sm24dp4xaMSTIPortsMSTIndex, sm24dp4xaMSTIPortsPortIndex }
    ::= { sm24dp4xaMSTIPortsTable 1 }

SM24DP4XAMSTIPortsEntry ::=
    SEQUENCE {
        sm24dp4xaMSTIPortsMSTIndex                        Integer32,
        sm24dp4xaMSTIPortsPortIndex                       Integer32,
        sm24dp4xaMSTIPortsPathCost                        Integer32,
        sm24dp4xaMSTIPortsPortPriority                    Integer32
    }

sm24dp4xaMSTIPortsMSTIndex OBJECT-TYPE
   SYNTAX      Integer32 (1..7)
   MAX-ACCESS  not-accessible
   STATUS      current
   DESCRIPTION
       "MST index, range:1-7"
   ::= {sm24dp4xaMSTIPortsEntry 1 }

sm24dp4xaMSTIPortsPortIndex OBJECT-TYPE
   SYNTAX      Integer32 (1..53)
   MAX-ACCESS  not-accessible
   STATUS      current
   DESCRIPTION
       "Port index, range 1-53, 53 is Aggregated Ports Configuration."
   ::= {sm24dp4xaMSTIPortsEntry 2 }

sm24dp4xaMSTIPortsPathCost   OBJECT-TYPE
   SYNTAX      Integer32 (0..200000000)
   MAX-ACCESS  read-write
   STATUS      current
   DESCRIPTION
       "MST Path Cost. range: 0-200000000. 0 is Auto."
   ::= {sm24dp4xaMSTIPortsEntry 3 }

sm24dp4xaMSTIPortsPortPriority   OBJECT-TYPE
   SYNTAX      Integer32 (0|16|32|48|64|80|96|112|128|144|160|176|192|208|224|240)
   MAX-ACCESS  read-write
   STATUS      current
   DESCRIPTION
       "MST Port Priority. range: 0-240, multiple of 16."
   ::= {sm24dp4xaMSTIPortsEntry 4 }

-- =======================================================================================================================
sm24dp4xaPrivateVLANs 						OBJECT IDENTIFIER ::= { sm24dp4xaConfiguration 19 }

sm24dp4xaPVLANMembershipTable  OBJECT-TYPE
   SYNTAX      SEQUENCE OF SM24DP4XAPVLANMembershipEntry
   MAX-ACCESS  not-accessible
   STATUS      current
   DESCRIPTION
       "A table of Private VLAN Membership."
 ::= { sm24dp4xaPrivateVLANs 1 }

sm24dp4xaPVLANMembershipEntry OBJECT-TYPE
    SYNTAX        SM24DP4XAPVLANMembershipEntry
    MAX-ACCESS    not-accessible
    STATUS        current
    DESCRIPTION
        "An entry in the private VLAN table."
    INDEX        { sm24dp4xaPVLANMembershipIndex }
    ::= { sm24dp4xaPVLANMembershipTable 1 }

SM24DP4XAPVLANMembershipEntry ::=
    SEQUENCE {
        sm24dp4xaPVLANMembershipIndex                    Integer32,
        sm24dp4xaPVLANID                                 Integer32,
        sm24dp4xaPVLANMembers                            DisplayString,
        sm24dp4xaPVLANRowStatus                          RowStatus
    }

sm24dp4xaPVLANMembershipIndex OBJECT-TYPE
   SYNTAX      Integer32 (1..28)
   MAX-ACCESS  not-accessible
   STATUS      current
   DESCRIPTION
       "PVLAN membership index. Range:1-28."
   ::= {sm24dp4xaPVLANMembershipEntry 1 }

sm24dp4xaPVLANID OBJECT-TYPE
   SYNTAX      Integer32 (1..28)
   MAX-ACCESS  read-create
   STATUS      current
   DESCRIPTION
       "PVLAN ID. Range:1-28."
   ::= {sm24dp4xaPVLANMembershipEntry 2 }

sm24dp4xaPVLANMembers OBJECT-TYPE
   SYNTAX      DisplayString
   MAX-ACCESS  read-create
   STATUS      current
   DESCRIPTION
       "PVLAN Members. Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1',
        then that port is included in the set of ports; the port
        is not included if its bit has a value of '0'."
   ::= {sm24dp4xaPVLANMembershipEntry 3 }

sm24dp4xaPVLANRowStatus OBJECT-TYPE
   SYNTAX      RowStatus
   MAX-ACCESS  read-create
   STATUS      current
   DESCRIPTION
       "PVLAN Row Status."
   ::= {sm24dp4xaPVLANMembershipEntry 4 }

sm24dp4xaPVLANPortIsolationTable  OBJECT-TYPE
   SYNTAX      SEQUENCE OF SM24DP4XAPVLANPortIsolationEntry
   MAX-ACCESS  not-accessible
   STATUS      current
   DESCRIPTION
       "A table of Private VLAN Port Isolation."
 ::= { sm24dp4xaPrivateVLANs 2 }

sm24dp4xaPVLANPortIsolationEntry OBJECT-TYPE
    SYNTAX        SM24DP4XAPVLANPortIsolationEntry
    MAX-ACCESS    not-accessible
    STATUS        current
    DESCRIPTION
        "An entry in the private VLAN table."
    INDEX        { sm24dp4xaPVLANPortIsolationIndex }
    ::= { sm24dp4xaPVLANPortIsolationTable 1 }

SM24DP4XAPVLANPortIsolationEntry ::=
    SEQUENCE {
        sm24dp4xaPVLANPortIsolationIndex                 Integer32,
        sm24dp4xaPVLANPortIsolationPortMembers           Integer32
    }

sm24dp4xaPVLANPortIsolationIndex OBJECT-TYPE
   SYNTAX      Integer32 (1..28)
   MAX-ACCESS  not-accessible
   STATUS      current
   DESCRIPTION
       "PVLAN Port Isolation Index. Range:1-28."
   ::= {sm24dp4xaPVLANPortIsolationEntry 1 }

sm24dp4xaPVLANPortIsolationPortMembers OBJECT-TYPE
   SYNTAX      Integer32 (0|1)
   MAX-ACCESS  read-write
   STATUS      current
   DESCRIPTION
       "PVLAN Port Isolation Port Members enable/disable. Range:0-1.
	   1:Port Isolation enable  on that port.
	   0:Port Isolation disable on that port."
   ::= {sm24dp4xaPVLANPortIsolationEntry 2 }

-- =======================================================================================================================


sm24dp4xasFlow 						OBJECT IDENTIFIER ::= { sm24dp4xaConfiguration 20 }

      sm24dp4xasFlowVersion OBJECT-TYPE
              SYNTAX      SnmpAdminString
              MAX-ACCESS  read-only
              STATUS      current
              DESCRIPTION "Uniquely identifies the version and implementation of this MIB. The version string must have the following structure: <MIB Version>;<Organization>;<Software Revision> where: <MIB Version>  must be '1.3', the version of this MIB.
                    <Organization> the name of the organization responsible for the agent implementation. <Revision>     the specific software build of this agent.
                 As an example, the string '1.3;InMon Corp.;2.1.1' indicates that this agent implements version '1.2' of the SFLOW MIB, that
                 it was developed by 'InMon Corp.' and that the software build is '2.1.1'.
                 The MIB Version will change with each revision of the SFLOW MIB.
                 Management entities must check the MIB Version and not attempt to manage agents with MIB Versions greater than that for which
                 they were designed.
                 Note: The sFlow Datagram Format has an independent version number which may change independently from <MIB Version>.
                       <MIB Version> applies to the structure and semantics of the SFLOW MIB only." DEFVAL { "1.3;;" }
              ::= { sm24dp4xasFlow 1 }

      sm24dp4xasFlowAgentAddressType OBJECT-TYPE
              SYNTAX      InetAddressType
              MAX-ACCESS  read-only
              STATUS      current
              DESCRIPTION "The address type of the address associated with this agent. Only ipv4 and ipv6 types are supported. ipv4:1, ipv6:2."
              ::= { sm24dp4xasFlow 2 }

      sm24dp4xasFlowAgentAddress OBJECT-TYPE
              SYNTAX      IpAddress
              MAX-ACCESS  read-write
              STATUS      current
              DESCRIPTION "The IP address associated with this agent. In the case of a multi-homed agent, this should be the loopback address of the
                 agent. The sFlowAgent address must provide SNMP connectivity to the agent. The address should be an invariant that does not
                 change as interfaces are reconfigured, enabled, disabled, added or removed. A manager should be able to use the
                 sFlowAgentAddress as a unique key that will identify this agent over extended periods of time so that a history can
                 be maintained."
              ::= { sm24dp4xasFlow 3 }
      --
      -- Receiver Table
      --
      sm24dp4xasFlowRcvrTable OBJECT-TYPE
              SYNTAX      SEQUENCE OF SM24DP4XASFlowRcvrEntry
              MAX-ACCESS  not-accessible
              STATUS      current
              DESCRIPTION "A table of the receivers of sFlow information."
              ::= { sm24dp4xasFlow 4 }

      sm24dp4xasFlowRcvrEntry OBJECT-TYPE
              SYNTAX SM24DP4XASFlowRcvrEntry
              MAX-ACCESS  not-accessible
              STATUS      current
              DESCRIPTION "Attributes of an sFlow Receiver."
              INDEX { sm24dp4xasFlowRcvrIndex }
              ::= { sm24dp4xasFlowRcvrTable 1 }

      SM24DP4XASFlowRcvrEntry ::= SEQUENCE {
              sm24dp4xasFlowRcvrIndex                    Integer32,
              sm24dp4xasFlowRcvrOwner                    OwnerString,
              sm24dp4xasFlowRcvrTimeout                  Integer32,
              sm24dp4xasFlowRcvrMaximumDatagramSize      Integer32,
              sm24dp4xasFlowRcvrAddressType              InetAddressType,
              sm24dp4xasFlowRcvrAddress                  IpAddress,
              sm24dp4xasFlowRcvrPort                     Integer32,
              sm24dp4xasFlowRcvrDatagramVersion          Integer32 }

      sm24dp4xasFlowRcvrIndex OBJECT-TYPE
              SYNTAX      Integer32 (1..65535)
              MAX-ACCESS  not-accessible
              STATUS      current
              DESCRIPTION "Index into sFlowReceiverTable."
              ::= { sm24dp4xasFlowRcvrEntry 1 }

      sm24dp4xasFlowRcvrOwner OBJECT-TYPE
              SYNTAX      OwnerString
              MAX-ACCESS  read-write
              STATUS      current
              DESCRIPTION "The entity making use of this sFlowRcvrTable entry. The empty string indicates that the entry is currently unclaimed.
                 An entity wishing to claim an sFlowRcvrTable entry must ensure that the entry is unclaimed before trying to claim it.
                 The entry is claimed by setting the owner string. The entry must be claimed before any changes can be made to other sampler
                 objects.
                 In order to avoid a race condition, the entity taking control of the sampler must set both the owner and a value for
                 sFlowRcvrTimeout in the same SNMP set request.
                 When a management entity is finished using the sampler, it should set the value of sFlowRcvrOwner back to unclaimed.
                 The agent must restore all other entities this row to their default values when the owner is set to unclaimed. It must
                 also free all other resources associated with this sFlowRcvrTable entry.
                 This mechanism provides no enforcement and relies on the cooperation of management entities in order to ensure that
                 competition for a receiver entry is fairly resolved." DEFVAL { "" }
              ::= { sm24dp4xasFlowRcvrEntry 2 }

      sm24dp4xasFlowRcvrTimeout OBJECT-TYPE
              SYNTAX      Integer32
              MAX-ACCESS  read-write
              STATUS      current
              DESCRIPTION "The time (in seconds) remaining before the sampler is released and stops sampling. When set, the owner establishes control
                 for the specified period. When read, the remaining time in the interval is returned.
                 A management entity wanting to maintain control of the sampler is responsible for setting a new value before the old one
                 expires.
                 When the interval expires, the agent is responsible for restoring all other entities in this row to their default
                 values. It must also free all other resources associated with this sFlowRcvrTable entry." DEFVAL { 0 }
              ::= { sm24dp4xasFlowRcvrEntry 3 }

      sm24dp4xasFlowRcvrMaximumDatagramSize OBJECT-TYPE
              SYNTAX      Integer32
              MAX-ACCESS  read-write
              STATUS      current
              DESCRIPTION "The maximum number of data bytes that can be sent in a single sample datagram. The manager should set this value to avoid fragmentation of the sFlow datagrams." DEFVAL { 1400 }
              ::= { sm24dp4xasFlowRcvrEntry 4 }

      sm24dp4xasFlowRcvrAddressType OBJECT-TYPE
              SYNTAX      InetAddressType
              MAX-ACCESS  read-write
              STATUS      current
              DESCRIPTION "The type of sFlowRcvrCollectorAddress." DEFVAL { ipv4 }
              ::= { sm24dp4xasFlowRcvrEntry 5 }

      sm24dp4xasFlowRcvrAddress OBJECT-TYPE
              SYNTAX      IpAddress
              MAX-ACCESS  read-write
              STATUS      current
              DESCRIPTION "The IP address of the sFlow collector. If set to 0.0.0.0 not sFlow datagrams will be sent." DEFVAL { '00000000'h }  -- 0.0.0.0
              ::= { sm24dp4xasFlowRcvrEntry 6 }

      sm24dp4xasFlowRcvrPort OBJECT-TYPE
              SYNTAX      Integer32
              MAX-ACCESS  read-write
              STATUS      current
              DESCRIPTION "The destination port for sFlow datagrams." DEFVAL { 6343 }
              ::= { sm24dp4xasFlowRcvrEntry 7 }

      sm24dp4xasFlowRcvrDatagramVersion OBJECT-TYPE
              SYNTAX      Integer32
              MAX-ACCESS  read-write
              STATUS      current
              DESCRIPTION "The version of sFlow datagrams that should be sent.
                 When set to a value not support by the agent, the agent should adjust the value to the highest supported value less than the
                 requested value, or return an SNMP bad value error if no such value exists." DEFVAL { 5 }
              ::= { sm24dp4xasFlowRcvrEntry 8 }

      --
      -- Flow Sampling Table
      --
      sm24dp4xasFlowFsTable OBJECT-TYPE
              SYNTAX      SEQUENCE OF SM24DP4XASFlowFsEntry
              MAX-ACCESS  not-accessible
              STATUS      current
              DESCRIPTION "A table of the flow samplers within a device."
              ::= { sm24dp4xasFlow 5 }

      sm24dp4xasFlowFsEntry OBJECT-TYPE
              SYNTAX      SM24DP4XASFlowFsEntry
              MAX-ACCESS  not-accessible
              STATUS      current
              DESCRIPTION "Attributes of a flow sampler."
              INDEX { sm24dp4xasFlowFsDataSource, sm24dp4xasFlowFsInstance }
              ::= { sm24dp4xasFlowFsTable 1 }

      SM24DP4XASFlowFsEntry ::= SEQUENCE {
              sm24dp4xasFlowFsDataSource               Integer32,
              sm24dp4xasFlowFsInstance                 Integer32,
              sm24dp4xasFlowFsReceiver                 Integer32,
              sm24dp4xasFlowFsPacketSamplingRate       Integer32,
              sm24dp4xasFlowFsMaximumHeaderSize        Integer32,
              sm24dp4xasFlowFsType                     Integer32
              }

      sm24dp4xasFlowFsDataSource OBJECT-TYPE
              SYNTAX      Integer32 (1..65535)
              MAX-ACCESS  not-accessible
              STATUS      current
              DESCRIPTION "sFlowDataSource for this flow sampler."
              ::= { sm24dp4xasFlowFsEntry 1 }

      sm24dp4xasFlowFsInstance OBJECT-TYPE
              SYNTAX      Integer32 (1..65535)
              MAX-ACCESS  not-accessible
              STATUS      current
              DESCRIPTION "The sFlow instance for this flow sampler."
              ::= { sm24dp4xasFlowFsEntry 2 }

      sm24dp4xasFlowFsReceiver OBJECT-TYPE
              SYNTAX      Integer32
              MAX-ACCESS  read-write
              STATUS      current
              DESCRIPTION "The SFlowReceiver for this flow sampler." DEFVAL { 0 }
              ::= { sm24dp4xasFlowFsEntry 3 }

      sm24dp4xasFlowFsPacketSamplingRate OBJECT-TYPE
              SYNTAX      Integer32
              MAX-ACCESS  read-write
              STATUS      current
              DESCRIPTION "The statistical sampling rate for packet sampling from this source.
                 Set to N to sample 1/Nth of the packets in the monitored flows. An agent should choose its own algorithm to introduce variance
                 into the sampling so that exactly every Nth packet is not counted. A sampling rate of 1 counts all packets. A sampling
                 rate of 0 disables sampling.
                 The agent is permitted to have minimum and maximum allowable values for the sampling rate. A minimum rate lets the agent
                 designer set an upper bound on the overhead associated with sampling, and a maximum rate may be the result of hardware
                 restrictions (such as counter size). In addition not all values between the maximum and minimum may be realizable as the
                 sampling rate (again because of implementation considerations).
                 When the sampling rate is set the agent is free to adjust the value so that it lies between the maximum and minimum values
                 and has the closest achievable value.
                 When read, the agent must return the actual sampling rate it will be using (after the adjustments previously described). The
                 sampling algorithm must converge so that over time the number of packets sampled approaches 1/Nth of the total number of
                 packets in the monitored flows." DEFVAL { 0 }
              ::= { sm24dp4xasFlowFsEntry 4 }

      sm24dp4xasFlowFsMaximumHeaderSize OBJECT-TYPE
              SYNTAX      Integer32
              MAX-ACCESS  read-write
              STATUS      current
              DESCRIPTION "The maximum number of bytes that should be copied from a sampled packet. The agent may have an internal maximum and
                 minimum permissible sizes. If an attempt is made to set this value outside the permissible range then the agent should
                 adjust the value to the closest permissible value." DEFVAL { 128 }
              ::= { sm24dp4xasFlowFsEntry 5 }

      sm24dp4xasFlowFsType OBJECT-TYPE
              SYNTAX      Integer32
              MAX-ACCESS  read-write
              STATUS      current
              DESCRIPTION "Flow Sample Type.
			  1:Rx
			  2:Tx
			  3:All."
			  DEFVAL { 2 }
              ::= { sm24dp4xasFlowFsEntry 6 }
      --
      -- Counter Polling Table
      --
      sm24dp4xasFlowCpTable OBJECT-TYPE
              SYNTAX      SEQUENCE OF SM24DP4XASFlowCpEntry
              MAX-ACCESS  not-accessible
              STATUS      current
              DESCRIPTION "A table of the counter pollers within a device."
              ::= { sm24dp4xasFlow 6 }

      sm24dp4xasFlowCpEntry OBJECT-TYPE
              SYNTAX      SM24DP4XASFlowCpEntry
              MAX-ACCESS  not-accessible
              STATUS      current
              DESCRIPTION "Attributes of a counter poller."
              INDEX { sm24dp4xasFlowCpDataSource, sm24dp4xasFlowCpInstance }
              ::= { sm24dp4xasFlowCpTable 1 }

      SM24DP4XASFlowCpEntry ::= SEQUENCE {
              sm24dp4xasFlowCpDataSource               Integer32,
              sm24dp4xasFlowCpInstance                 Integer32,
              sm24dp4xasFlowCpReceiver                 Integer32,
              sm24dp4xasFlowCpInterval                 Integer32
              }

      sm24dp4xasFlowCpDataSource OBJECT-TYPE
              SYNTAX      Integer32 (1..65535)
              MAX-ACCESS  not-accessible
              STATUS      current
              DESCRIPTION "Identifies the source of the data for the counter poller."
              ::= { sm24dp4xasFlowCpEntry 1 }

      sm24dp4xasFlowCpInstance OBJECT-TYPE
              SYNTAX      Integer32 (1..65535)
              MAX-ACCESS  not-accessible
              STATUS      current
              DESCRIPTION "The sFlowInstance for this counter poller."
              ::= { sm24dp4xasFlowCpEntry 2 }

      sm24dp4xasFlowCpReceiver OBJECT-TYPE
              SYNTAX      Integer32
              MAX-ACCESS  read-write
              STATUS      current
              DESCRIPTION "The SFlowReciever associated with this counter poller." DEFVAL { 0 }
              ::= { sm24dp4xasFlowCpEntry 3 }

      sm24dp4xasFlowCpInterval OBJECT-TYPE
              SYNTAX      Integer32
              MAX-ACCESS  read-write
              STATUS      current
              DESCRIPTION "The maximum number of seconds between successive samples of the counters associated with this data source. A sampling interval
                 of 0 disables counter sampling.
                 The agent is permitted to have minimum and maximum allowable values for the counter polling interval. A minimum interval
                 lets the agent designer set an upper bound on the overhead associated with polling, and a maximum interval may be the
                 result of implementation restrictions (such as counter size). In addition not all values between the maximum and minimum may
                 be realizable as the sampling interval (again because of implementation considerations).
                 When the sampling rate is set the agent is free to adjust the value so that it lies between the maximum and minimum values
                 and has the closest achievable value.
                 When read, the agent must return the actual sampling interval it will be using (after the adjustments previously described).
                 The sampling algorithm must converge so that over time the number of packets sampled approaches 1/Nth of the total number
                 of packets in the monitored flows." DEFVAL { 0 }
              ::= { sm24dp4xasFlowCpEntry 4 }

sm24dp4xaLLDP                  OBJECT IDENTIFIER ::= { sm24dp4xaConfiguration 21 }

    sm24dp4xaLLDPConfTable OBJECT-TYPE
               SYNTAX      SEQUENCE OF     SM24DP4XALLDPConfEntry
               MAX-ACCESS  not-accessible
               STATUS      current
               DESCRIPTION
                   " "
               ::= {     sm24dp4xaLLDP 1 }

    sm24dp4xaLLDPConfEntry OBJECT-TYPE
               SYNTAX          SM24DP4XALLDPConfEntry
               MAX-ACCESS  not-accessible
               STATUS      current
               DESCRIPTION
                   " "
               INDEX    {    sm24dp4xaLLDPIndex  }
               ::= {     sm24dp4xaLLDPConfTable 1 }

    SM24DP4XALLDPConfEntry             ::= SEQUENCE {
                 sm24dp4xaLLDPIndex        Integer32,
                 sm24dp4xaLLDPMode         Integer32,
                 sm24dp4xaLLDPCDPAware     Integer32,
                 sm24dp4xaLLDPPortDescr    Integer32,
		 sm24dp4xaLLDPSysName      Integer32,
		 sm24dp4xaLLDPSysDescr     Integer32,
		 sm24dp4xaLLDPSysCapa      Integer32,
		 sm24dp4xaLLDPMgmtAddr     Integer32
    }

    sm24dp4xaLLDPIndex OBJECT-TYPE
               SYNTAX      Integer32 (1..65535)
               MAX-ACCESS  read-write
               STATUS      current
               DESCRIPTION
                   "LLDP configuration index."
               ::= {     sm24dp4xaLLDPConfEntry 1 }

    sm24dp4xaLLDPMode OBJECT-TYPE
               SYNTAX      Integer32
               MAX-ACCESS  read-write
               STATUS      current
               DESCRIPTION
                   "0:Disable
		   1:Tx only
		   2:Rx only
		   3:Enabled"
               ::= {     sm24dp4xaLLDPConfEntry 2 }

    sm24dp4xaLLDPCDPAware OBJECT-TYPE
               SYNTAX      Integer32
               MAX-ACCESS  read-write
               STATUS      current
               DESCRIPTION
                   "0:Disable
		   1:Enable"
               ::= {     sm24dp4xaLLDPConfEntry 3 }

    sm24dp4xaLLDPPortDescr OBJECT-TYPE
               SYNTAX      Integer32
               MAX-ACCESS  read-write
               STATUS      current
               DESCRIPTION
                   "0:Disable
		   1:Enable"
               ::= {     sm24dp4xaLLDPConfEntry 4 }

    sm24dp4xaLLDPSysName OBJECT-TYPE
               SYNTAX      Integer32
               MAX-ACCESS  read-write
               STATUS      current
               DESCRIPTION
                   "0:Disable
		   1:Enable"
               ::= {     sm24dp4xaLLDPConfEntry 5 }

    sm24dp4xaLLDPSysDescr OBJECT-TYPE
               SYNTAX      Integer32
               MAX-ACCESS  read-write
               STATUS      current
               DESCRIPTION
                   "0:Disable
		   1:Enable"
               ::= {     sm24dp4xaLLDPConfEntry 6 }

    sm24dp4xaLLDPSysCapa OBJECT-TYPE
               SYNTAX      Integer32
               MAX-ACCESS  read-write
               STATUS      current
               DESCRIPTION
                   "0:Disable
		   1:Enable"
               ::= {     sm24dp4xaLLDPConfEntry 7 }

    sm24dp4xaLLDPMgmtAddr OBJECT-TYPE
               SYNTAX      Integer32
               MAX-ACCESS  read-write
               STATUS      current
               DESCRIPTION
                   "0:Disable
		   1:Enable"
               ::= {     sm24dp4xaLLDPConfEntry 8 }

sm24dp4xaLLDPMEDCoordinatesLocation                          OBJECT IDENTIFIER ::= { sm24dp4xaLLDP 2 }   
			   
sm24dp4xaLLDPMEDLatitude   OBJECT-TYPE
   SYNTAX      DisplayString
   MAX-ACCESS  read-write
   STATUS      current
   DESCRIPTION
	   "Latitude SHOULD be normalized to within 0-90 degrees with a maximum of 4 digits."
   ::= { sm24dp4xaLLDPMEDCoordinatesLocation 2 }
			   
sm24dp4xaLLDPMEDLatitudeDirection OBJECT-TYPE
   SYNTAX      Integer32(0|1)
   MAX-ACCESS  read-write
   STATUS      current
   DESCRIPTION
       "0:North 
	    1:South"
   ::= { sm24dp4xaLLDPMEDCoordinatesLocation 3 }
			  
sm24dp4xaLLDPMEDLongitude   OBJECT-TYPE
   SYNTAX      DisplayString
   MAX-ACCESS  read-write
   STATUS      current
   DESCRIPTION
	   "Longitude SHOULD be normalized to within 0-180 degrees with a maximum of 4 digits."
   ::= { sm24dp4xaLLDPMEDCoordinatesLocation 4 }
			   
sm24dp4xaLLDPMEDLongitudeDirection OBJECT-TYPE
   SYNTAX      Integer32(0|1)
   MAX-ACCESS  read-write
   STATUS      current
   DESCRIPTION
       "0:East 
	    1:West"
   ::= { sm24dp4xaLLDPMEDCoordinatesLocation 5 }
			  
sm24dp4xaLLDPMEDAltitude   OBJECT-TYPE
   SYNTAX      DisplayString
   MAX-ACCESS  read-write
   STATUS      current
   DESCRIPTION
	   "Altitude SHOULD be normalized to within -2097151.9 to 2097151.9 with a maximum of 1 digits."
   ::= { sm24dp4xaLLDPMEDCoordinatesLocation 6 }
			   
sm24dp4xaLLDPMEDAltitudeType OBJECT-TYPE
   SYNTAX      Integer32(1|2)
   MAX-ACCESS  read-write
   STATUS      current
   DESCRIPTION
       "1:Meters 
	    2:Floors"
   ::= { sm24dp4xaLLDPMEDCoordinatesLocation 7 } 
   
sm24dp4xaLLDPMEDMapDatum OBJECT-TYPE
   SYNTAX      Integer32(0..2)
   MAX-ACCESS  read-write
   STATUS      current
   DESCRIPTION
       "The Map Datum is used for the coordinates given in these options:
	    1:WGS84
	    2:NAD83/NAVD88 
	    3:NAD83/MLLW
		"
   ::= { sm24dp4xaLLDPMEDCoordinatesLocation 8 }    

   
sm24dp4xaLLDPMEDTransmitTLVsTable OBJECT-TYPE
   SYNTAX      SEQUENCE OF SM24DP4XALLDPMEDTransmitTLVsEntry
   MAX-ACCESS  not-accessible
   STATUS      current
   DESCRIPTION
       " "
   ::= { sm24dp4xaLLDP 3 }

sm24dp4xaLLDPMEDTransmitTLVsEntry OBJECT-TYPE
   SYNTAX      SM24DP4XALLDPMEDTransmitTLVsEntry
   MAX-ACCESS  not-accessible
   STATUS      current
   DESCRIPTION
       " "
   INDEX    { sm24dp4xaLLDPMEDTransmitTLVsPort  }
   ::= { sm24dp4xaLLDPMEDTransmitTLVsTable 1 }
  
SM24DP4XALLDPMEDTransmitTLVsEntry ::= SEQUENCE {
   sm24dp4xaLLDPMEDTransmitTLVsPort          Integer32,
   sm24dp4xaLLDPMEDTransmitTLVsCapabilities  Integer32,
   sm24dp4xaLLDPMEDTransmitTLVsPolicies      Integer32,
   sm24dp4xaLLDPMEDTransmitTLVsLocation      Integer32,
   sm24dp4xaLLDPMEDTransmitTLVsPoE           Integer32
}

sm24dp4xaLLDPMEDTransmitTLVsPort OBJECT-TYPE
   SYNTAX      Integer32 (1..65535)
   MAX-ACCESS  not-accessible
   STATUS      current
   DESCRIPTION
       "Index"
   ::= { sm24dp4xaLLDPMEDTransmitTLVsEntry 1 }

sm24dp4xaLLDPMEDTransmitTLVsCapabilities OBJECT-TYPE
   SYNTAX      Integer32 (0|1)
   MAX-ACCESS  read-write
   STATUS      current
   DESCRIPTION
       "0:Disable
	    1:Enable"
   ::= { sm24dp4xaLLDPMEDTransmitTLVsEntry 2 }
			   
sm24dp4xaLLDPMEDTransmitTLVsPolicies OBJECT-TYPE
   SYNTAX      Integer32 (0|1)
   MAX-ACCESS  read-write
   STATUS      current
   DESCRIPTION
       "0:Disable
	    1:Enable"
   ::= { sm24dp4xaLLDPMEDTransmitTLVsEntry 3 }
   
sm24dp4xaLLDPMEDTransmitTLVsLocation OBJECT-TYPE
   SYNTAX      Integer32 (0|1)
   MAX-ACCESS  read-write
   STATUS      current
   DESCRIPTION
       "0:Disable
	    1:Enable"
   ::= { sm24dp4xaLLDPMEDTransmitTLVsEntry 4 }

sm24dp4xaLLDPMEDTransmitTLVsPoE OBJECT-TYPE
   SYNTAX      Integer32 (0|1)
   MAX-ACCESS  read-write
   STATUS      current
   DESCRIPTION
       "0:Disable
	    1:Enable"
   ::= { sm24dp4xaLLDPMEDTransmitTLVsEntry 5 }

sm24dp4xaLLDPMEDCivicAddressLocation                          OBJECT IDENTIFIER ::= { sm24dp4xaLLDP 4 }

sm24dp4xaLLDPMEDCivicAddrLocatCountryCode   OBJECT-TYPE
   SYNTAX      DisplayString
   MAX-ACCESS  read-write
   STATUS      current
   DESCRIPTION
	   " "
   ::= { sm24dp4xaLLDPMEDCivicAddressLocation 2 }

sm24dp4xaLLDPMEDCivicAddrLocatStateProvince   OBJECT-TYPE
   SYNTAX      DisplayString
   MAX-ACCESS  read-write
   STATUS      current
   DESCRIPTION
	   " "
   ::= { sm24dp4xaLLDPMEDCivicAddressLocation 3 }

sm24dp4xaLLDPMEDCivicAddrLocatCounty   OBJECT-TYPE
   SYNTAX      DisplayString
   MAX-ACCESS  read-write
   STATUS      current
   DESCRIPTION
	   " "
   ::= { sm24dp4xaLLDPMEDCivicAddressLocation 4 }

sm24dp4xaLLDPMEDCivicAddrLocatCity   OBJECT-TYPE
   SYNTAX      DisplayString
   MAX-ACCESS  read-write
   STATUS      current
   DESCRIPTION
	   " "
   ::= { sm24dp4xaLLDPMEDCivicAddressLocation 5 }

sm24dp4xaLLDPMEDCivicAddrLocatCityDistrict   OBJECT-TYPE
   SYNTAX      DisplayString
   MAX-ACCESS  read-write
   STATUS      current
   DESCRIPTION
	   " "
   ::= { sm24dp4xaLLDPMEDCivicAddressLocation 6 }

sm24dp4xaLLDPMEDCivicAddrLocatBlockNeighborhood   OBJECT-TYPE
   SYNTAX      DisplayString
   MAX-ACCESS  read-write
   STATUS      current
   DESCRIPTION
	   " "
   ::= { sm24dp4xaLLDPMEDCivicAddressLocation 7 }

sm24dp4xaLLDPMEDCivicAddrLocatStreet   OBJECT-TYPE
   SYNTAX      DisplayString
   MAX-ACCESS  read-write
   STATUS      current
   DESCRIPTION
	   " "
   ::= { sm24dp4xaLLDPMEDCivicAddressLocation 8 }

sm24dp4xaLLDPMEDCivicAddrLocatLeadingStreetDirect   OBJECT-TYPE
   SYNTAX      DisplayString
   MAX-ACCESS  read-write
   STATUS      current
   DESCRIPTION
	   " "
   ::= { sm24dp4xaLLDPMEDCivicAddressLocation 9 }

sm24dp4xaLLDPMEDCivicAddrLocatTrailingStreetSuffix   OBJECT-TYPE
   SYNTAX      DisplayString
   MAX-ACCESS  read-write
   STATUS      current
   DESCRIPTION
	   " "
   ::= { sm24dp4xaLLDPMEDCivicAddressLocation 10 }

sm24dp4xaLLDPMEDCivicAddrLocatStreetSuffix   OBJECT-TYPE
   SYNTAX      DisplayString
   MAX-ACCESS  read-write
   STATUS      current
   DESCRIPTION
	   " "
   ::= { sm24dp4xaLLDPMEDCivicAddressLocation 11 }

sm24dp4xaLLDPMEDCivicAddrLocatHouseNo   OBJECT-TYPE
   SYNTAX      DisplayString
   MAX-ACCESS  read-write
   STATUS      current
   DESCRIPTION
	   " "
   ::= { sm24dp4xaLLDPMEDCivicAddressLocation 12 }

sm24dp4xaLLDPMEDCivicAddrLocatHouseNoSuffix   OBJECT-TYPE
   SYNTAX      DisplayString
   MAX-ACCESS  read-write
   STATUS      current
   DESCRIPTION
	   " "
   ::= { sm24dp4xaLLDPMEDCivicAddressLocation 13 }

sm24dp4xaLLDPMEDCivicAddrLocatLandmark   OBJECT-TYPE
   SYNTAX      DisplayString
   MAX-ACCESS  read-write
   STATUS      current
   DESCRIPTION
	   " "
   ::= { sm24dp4xaLLDPMEDCivicAddressLocation 14 }

sm24dp4xaLLDPMEDCivicAddrLocatAdditionalLocatInfo   OBJECT-TYPE
   SYNTAX      DisplayString
   MAX-ACCESS  read-write
   STATUS      current
   DESCRIPTION
	   " "
   ::= { sm24dp4xaLLDPMEDCivicAddressLocation 15 }

sm24dp4xaLLDPMEDCivicAddrLocatName   OBJECT-TYPE
   SYNTAX      DisplayString
   MAX-ACCESS  read-write
   STATUS      current
   DESCRIPTION
	   " "
   ::= { sm24dp4xaLLDPMEDCivicAddressLocation 16 }

sm24dp4xaLLDPMEDCivicAddrLocatZipCode   OBJECT-TYPE
   SYNTAX      DisplayString
   MAX-ACCESS  read-write
   STATUS      current
   DESCRIPTION
	   " "
   ::= { sm24dp4xaLLDPMEDCivicAddressLocation 17 }

sm24dp4xaLLDPMEDCivicAddrLocatBuilding   OBJECT-TYPE
   SYNTAX      DisplayString
   MAX-ACCESS  read-write
   STATUS      current
   DESCRIPTION
	   " "
   ::= { sm24dp4xaLLDPMEDCivicAddressLocation 18 }

sm24dp4xaLLDPMEDCivicAddrLocatApartment   OBJECT-TYPE
   SYNTAX      DisplayString
   MAX-ACCESS  read-write
   STATUS      current
   DESCRIPTION
	   " "
   ::= { sm24dp4xaLLDPMEDCivicAddressLocation 19 }

sm24dp4xaLLDPMEDCivicAddrLocatFloor   OBJECT-TYPE
   SYNTAX      DisplayString
   MAX-ACCESS  read-write
   STATUS      current
   DESCRIPTION
	   " "
   ::= { sm24dp4xaLLDPMEDCivicAddressLocation 20 }

sm24dp4xaLLDPMEDCivicAddrLocatRoomNo   OBJECT-TYPE
   SYNTAX      DisplayString
   MAX-ACCESS  read-write
   STATUS      current
   DESCRIPTION
	   " "
   ::= { sm24dp4xaLLDPMEDCivicAddressLocation 21 }

sm24dp4xaLLDPMEDCivicAddrLocatPlaceType   OBJECT-TYPE
   SYNTAX      DisplayString
   MAX-ACCESS  read-write
   STATUS      current
   DESCRIPTION
	   " "
   ::= { sm24dp4xaLLDPMEDCivicAddressLocation 22 }

sm24dp4xaLLDPMEDCivicAddrLocatPostalCommunityName   OBJECT-TYPE
   SYNTAX      DisplayString
   MAX-ACCESS  read-write
   STATUS      current
   DESCRIPTION
	   " "
   ::= { sm24dp4xaLLDPMEDCivicAddressLocation 23 }

sm24dp4xaLLDPMEDCivicAddrLocatPOBox   OBJECT-TYPE
   SYNTAX      DisplayString
   MAX-ACCESS  read-write
   STATUS      current
   DESCRIPTION
	   " "
   ::= { sm24dp4xaLLDPMEDCivicAddressLocation 24 }

sm24dp4xaLLDPMEDCivicAddrLocatAdditionalCode   OBJECT-TYPE
   SYNTAX      DisplayString
   MAX-ACCESS  read-write
   STATUS      current
   DESCRIPTION
	   " "
   ::= { sm24dp4xaLLDPMEDCivicAddressLocation 25 }


sm24dp4xaLLDPMEDPoliciesTable OBJECT-TYPE
   SYNTAX      SEQUENCE OF SM24DP4XALLDPMEDPoliciesEntry
   MAX-ACCESS  not-accessible
   STATUS      current
   DESCRIPTION
       " "
   ::= { sm24dp4xaLLDP 5 }

sm24dp4xaLLDPMEDPoliciesEntry OBJECT-TYPE
   SYNTAX      SM24DP4XALLDPMEDPoliciesEntry
   MAX-ACCESS  not-accessible
   STATUS      current
   DESCRIPTION
       " "
   INDEX    { sm24dp4xaLLDPMEDPoliciesIndex  }
   ::= { sm24dp4xaLLDPMEDPoliciesTable 1 }

SM24DP4XALLDPMEDPoliciesEntry ::= SEQUENCE {
   sm24dp4xaLLDPMEDPoliciesIndex            Integer32,
   sm24dp4xaLLDPMEDPoliciesPolicyID         Integer32,
   sm24dp4xaLLDPMEDPoliciesApplicationType  Integer32,
   sm24dp4xaLLDPMEDPoliciesTag              Integer32,
   sm24dp4xaLLDPMEDPoliciesVLANID           Integer32,
   sm24dp4xaLLDPMEDPoliciesL2Priority       Integer32,
   sm24dp4xaLLDPMEDPoliciesDSCP             Integer32,
   sm24dp4xaLLDPMEDPoliciesRowStatus        RowStatus
}

sm24dp4xaLLDPMEDPoliciesIndex OBJECT-TYPE
   SYNTAX      Integer32 (1..65535)
   MAX-ACCESS  not-accessible
   STATUS      current
   DESCRIPTION
       "Index"
   ::= { sm24dp4xaLLDPMEDPoliciesEntry 1 }

sm24dp4xaLLDPMEDPoliciesPolicyID OBJECT-TYPE
   SYNTAX      Integer32
   MAX-ACCESS  read-only
   STATUS      current
   DESCRIPTION
       " "
   ::= { sm24dp4xaLLDPMEDPoliciesEntry 2 }
			   
sm24dp4xaLLDPMEDPoliciesApplicationType OBJECT-TYPE
   SYNTAX      Integer32 (1..8)
   MAX-ACCESS  read-write
   STATUS      current
   DESCRIPTION
       "1:Voice
		2:Voice Signalling
		3:Guest Voice
		4:Guest Voice Signalling
		5:Softphone Voice
		6:Video Conferencing
		7:Streaming Video 
		8:Video Signalling"
   ::= { sm24dp4xaLLDPMEDPoliciesEntry 3 }
   
sm24dp4xaLLDPMEDPoliciesTag OBJECT-TYPE
   SYNTAX      Integer32 (0|1)
   MAX-ACCESS  read-write
   STATUS      current
   DESCRIPTION
       "0:Untagged
	    1:Tagged"
   ::= { sm24dp4xaLLDPMEDPoliciesEntry 4 }
   
sm24dp4xaLLDPMEDPoliciesVLANID OBJECT-TYPE
   SYNTAX      Integer32 (1..4095)
   MAX-ACCESS  read-write
   STATUS      current
   DESCRIPTION
       "Range:1-4095"
   ::= { sm24dp4xaLLDPMEDPoliciesEntry 5 }

sm24dp4xaLLDPMEDPoliciesL2Priority OBJECT-TYPE
   SYNTAX      Integer32 (0..7)
   MAX-ACCESS  read-write
   STATUS      current
   DESCRIPTION
       "Range:0-7"
   ::= { sm24dp4xaLLDPMEDPoliciesEntry 6 }
   
sm24dp4xaLLDPMEDPoliciesDSCP OBJECT-TYPE
   SYNTAX      Integer32 (0..63)
   MAX-ACCESS  read-write
   STATUS      current
   DESCRIPTION
       "Range:0-63"
   ::= { sm24dp4xaLLDPMEDPoliciesEntry 7 }	
   
sm24dp4xaLLDPMEDPoliciesRowStatus OBJECT-TYPE
   SYNTAX      RowStatus
   MAX-ACCESS  read-create
   STATUS      current
   DESCRIPTION
       "Row Status."
   ::= { sm24dp4xaLLDPMEDPoliciesEntry 8 }
	
sm24dp4xaLLDPMEDPolicyPortConfTable OBJECT-TYPE
   SYNTAX      SEQUENCE OF SM24DP4XALLDPMEDPolicyPortConfEntry
   MAX-ACCESS  not-accessible
   STATUS      current
   DESCRIPTION
       " "
   ::= { sm24dp4xaLLDP 6 }

sm24dp4xaLLDPMEDPolicyPortConfEntry OBJECT-TYPE
   SYNTAX      SM24DP4XALLDPMEDPolicyPortConfEntry
   MAX-ACCESS  not-accessible
   STATUS      current
   DESCRIPTION
       " "
   INDEX    { sm24dp4xaLLDPMEDPolicyPortConfPort  }
   ::= { sm24dp4xaLLDPMEDPolicyPortConfTable 1 }

SM24DP4XALLDPMEDPolicyPortConfEntry ::= SEQUENCE {
   sm24dp4xaLLDPMEDPolicyPortConfPort        Integer32,
   sm24dp4xaLLDPMEDPolicyPortConf            Integer32
}
	
sm24dp4xaLLDPMEDPolicyPortConfPort OBJECT-TYPE
   SYNTAX      Integer32 (1..65535)
   MAX-ACCESS  not-accessible
   STATUS      current
   DESCRIPTION
       "Index"
   ::= { sm24dp4xaLLDPMEDPolicyPortConfEntry 1 }

sm24dp4xaLLDPMEDPolicyPortConf OBJECT-TYPE
   SYNTAX      Integer32 (0|1)
   MAX-ACCESS  read-write
   STATUS      current
   DESCRIPTION
       "0:Disable
	    1:Enable"
   ::= { sm24dp4xaLLDPMEDPolicyPortConfEntry 2 }
	
sm24dp4xaLLDPMEDFastStartRepeatCount OBJECT-TYPE
   SYNTAX      Integer32 (1..10)
   MAX-ACCESS  read-write
   STATUS      current
   DESCRIPTION
       "Range:1-10"
   ::= { sm24dp4xaLLDP 7 }
	
sm24dp4xaLLDPMEDEmergencyCallService OBJECT-TYPE
   SYNTAX      DisplayString
   MAX-ACCESS  read-write
   STATUS      current
   DESCRIPTION
       " "
   ::= { sm24dp4xaLLDP 8 }
			   
sm24dp4xaUDLD    OBJECT IDENTIFIER ::= { sm24dp4xaConfiguration 22 }

sm24dp4xaUDLDPortConfigTable OBJECT-TYPE
   SYNTAX      SEQUENCE OF SM24DP4XAUDLDPortConfigEntry
   MAX-ACCESS  not-accessible
   STATUS      current
   DESCRIPTION
       " "
   ::= { sm24dp4xaUDLD 1 }

sm24dp4xaUDLDPortConfigEntry OBJECT-TYPE
   SYNTAX      SM24DP4XAUDLDPortConfigEntry
   MAX-ACCESS  not-accessible
   STATUS      current
   DESCRIPTION
       " "
   INDEX    { sm24dp4xaUDLDPort  }
   ::= { sm24dp4xaUDLDPortConfigTable 1 }

SM24DP4XAUDLDPortConfigEntry ::= SEQUENCE {
   sm24dp4xaUDLDPort                       Integer32,
   sm24dp4xaUDLDPortMode                   Integer32,
   sm24dp4xaUDLDPortMessageInterval        Integer32
}

sm24dp4xaUDLDPort OBJECT-TYPE
   SYNTAX      Integer32 (1..65535)
   MAX-ACCESS  not-accessible
   STATUS      current
   DESCRIPTION
       " "
   ::= { sm24dp4xaUDLDPortConfigEntry 1 }

sm24dp4xaUDLDPortMode OBJECT-TYPE
   SYNTAX      Integer32 (0|1|2)
   MAX-ACCESS  read-write
   STATUS      current
   DESCRIPTION
       "default: 0
       0: disable
       1: Normal
	   2: Aggressive"
   ::= { sm24dp4xaUDLDPortConfigEntry 2 }

sm24dp4xaUDLDPortMessageInterval OBJECT-TYPE
   SYNTAX      Integer32(7..90)
   MAX-ACCESS  read-write
   STATUS      current
   DESCRIPTION
       "default: 7, range: 7-90"
   ::= { sm24dp4xaUDLDPortConfigEntry 3 }


sm24dp4xaUDLDPortStatusTable OBJECT-TYPE
   SYNTAX      SEQUENCE OF SM24DP4XAUDLDPortStatusEntry
   MAX-ACCESS  not-accessible
   STATUS      current
   DESCRIPTION
       " "
   ::= { sm24dp4xaUDLD 2 }

sm24dp4xaUDLDPortStatusEntry OBJECT-TYPE
   SYNTAX      SM24DP4XAUDLDPortStatusEntry
   MAX-ACCESS  not-accessible
   STATUS      current
   DESCRIPTION
       " "
   INDEX    { sm24dp4xaUDLDPortStatusPort  }
   ::= { sm24dp4xaUDLDPortStatusTable 1 }

SM24DP4XAUDLDPortStatusEntry ::= SEQUENCE {
   sm24dp4xaUDLDPortStatusPort                   Integer32,
   sm24dp4xaUDLDStatusAdminState                 Integer32,
   sm24dp4xaUDLDStatusDeviceIDLocal          DisplayString,
   sm24dp4xaUDLDStatusDeviceNameLocal        DisplayString,
   sm24dp4xaUDLDStatusBidirectionalState     DisplayString
}

sm24dp4xaUDLDPortStatusPort OBJECT-TYPE
   SYNTAX      Integer32 (1..65535)
   MAX-ACCESS  not-accessible
   STATUS      current
   DESCRIPTION
       "Port index"
   ::= { sm24dp4xaUDLDPortStatusEntry 1 }

sm24dp4xaUDLDStatusAdminState OBJECT-TYPE
   SYNTAX      Integer32
   MAX-ACCESS  read-only
   STATUS      current
   DESCRIPTION
       "0:disable
	   1:enable"
   ::= { sm24dp4xaUDLDPortStatusEntry 2 }

sm24dp4xaUDLDStatusDeviceIDLocal OBJECT-TYPE
   SYNTAX      DisplayString
   MAX-ACCESS  read-only
   STATUS      current
   DESCRIPTION
       " "
   ::= { sm24dp4xaUDLDPortStatusEntry 3 }

sm24dp4xaUDLDStatusDeviceNameLocal OBJECT-TYPE
   SYNTAX      DisplayString
   MAX-ACCESS  read-only
   STATUS      current
   DESCRIPTION
       " "
   ::= { sm24dp4xaUDLDPortStatusEntry 4 }

sm24dp4xaUDLDStatusBidirectionalState OBJECT-TYPE
   SYNTAX      DisplayString
   MAX-ACCESS  read-only
   STATUS      current
   DESCRIPTION
       " "
   ::= { sm24dp4xaUDLDPortStatusEntry 5 }


sm24dp4xaUDLDStatusPort OBJECT-TYPE
   SYNTAX      Integer32
   MAX-ACCESS  read-write
   STATUS      current
   DESCRIPTION
       "Specify port number for check neighbour status"
   ::= { sm24dp4xaUDLD 3 }

sm24dp4xaUDLDPortNeighbourStatusTable OBJECT-TYPE
   SYNTAX      SEQUENCE OF SM24DP4XAUDLDPortNeighbourStatusEntry
   MAX-ACCESS  not-accessible
   STATUS      current
   DESCRIPTION
       " "
   ::= { sm24dp4xaUDLD 4 }

sm24dp4xaUDLDPortNeighbourStatusEntry OBJECT-TYPE
   SYNTAX      SM24DP4XAUDLDPortNeighbourStatusEntry
   MAX-ACCESS  not-accessible
   STATUS      current
   DESCRIPTION
       " "
   INDEX    { sm24dp4xaUDLDNeighbourPort  }
   ::= { sm24dp4xaUDLDPortNeighbourStatusTable 1 }

SM24DP4XAUDLDPortNeighbourStatusEntry ::= SEQUENCE {
   sm24dp4xaUDLDNeighbourPort                 Integer32,
   sm24dp4xaUDLDNeighbourStatusPort           DisplayString,
   sm24dp4xaUDLDNeighbourStatusDeviceId       DisplayString,
   sm24dp4xaUDLDNeighbourStatusLinkStatus     DisplayString,
   sm24dp4xaUDLDNeighbourStatusDeviceName     DisplayString
}

sm24dp4xaUDLDNeighbourPort OBJECT-TYPE
   SYNTAX      Integer32 (1..65535)
   MAX-ACCESS  not-accessible
   STATUS      current
   DESCRIPTION
       "Index"
   ::= { sm24dp4xaUDLDPortNeighbourStatusEntry 1 }

sm24dp4xaUDLDNeighbourStatusPort OBJECT-TYPE
   SYNTAX      DisplayString
   MAX-ACCESS  read-only
   STATUS      current
   DESCRIPTION
       " "
   ::= { sm24dp4xaUDLDPortNeighbourStatusEntry 2 }

sm24dp4xaUDLDNeighbourStatusDeviceId OBJECT-TYPE
   SYNTAX      DisplayString
   MAX-ACCESS  read-only
   STATUS      current
   DESCRIPTION
       " "
   ::= { sm24dp4xaUDLDPortNeighbourStatusEntry 3 }

sm24dp4xaUDLDNeighbourStatusLinkStatus OBJECT-TYPE
   SYNTAX      DisplayString
   MAX-ACCESS  read-only
   STATUS      current
   DESCRIPTION
       " "
   ::= { sm24dp4xaUDLDPortNeighbourStatusEntry 4 }

sm24dp4xaUDLDNeighbourStatusDeviceName OBJECT-TYPE
   SYNTAX      DisplayString
   MAX-ACCESS  read-only
   STATUS      current
   DESCRIPTION
       " "
   ::= { sm24dp4xaUDLDPortNeighbourStatusEntry 5 }
-- =======================================================================================================================
sm24dp4xaEPS    OBJECT IDENTIFIER ::= { sm24dp4xaConfiguration 23 }

sm24dp4xaEPSTable  OBJECT-TYPE
   SYNTAX      SEQUENCE OF SM24DP4XAEPSEntry
   MAX-ACCESS  not-accessible
   STATUS      current
   DESCRIPTION
       "A table of EPS."
 ::= { sm24dp4xaEPS 1 }

sm24dp4xaEPSEntry OBJECT-TYPE
    SYNTAX        SM24DP4XAEPSEntry
    MAX-ACCESS    not-accessible
    STATUS        current
    DESCRIPTION
        ""
    INDEX        { sm24dp4xaEPSIndex }
    ::= { sm24dp4xaEPSTable 1 }

SM24DP4XAEPSEntry ::=
    SEQUENCE {
        sm24dp4xaEPSIndex                                Integer32,
        sm24dp4xaEpsID                                   Integer32,
		sm24dp4xaEpsDomain                               Integer32,
        sm24dp4xaEpsArchitecture                         Integer32,
        sm24dp4xaEpsWFlow                                Integer32,
        sm24dp4xaEpsPFlow                                Integer32,	
        sm24dp4xaEpsWSFMEP                               Integer32,		
        sm24dp4xaEpsPSFMEP                               Integer32,		
        sm24dp4xaEpsAPSMEP                               Integer32,		
        sm24dp4xaEpsAlarm                                Integer32,		
        sm24dp4xaEpsRowStatus                            RowStatus
    }

sm24dp4xaEPSIndex OBJECT-TYPE
   SYNTAX      Integer32 (1..65535)
   MAX-ACCESS  not-accessible
   STATUS      current
   DESCRIPTION
       "Index"
   ::= { sm24dp4xaEPSEntry 1 }

sm24dp4xaEpsID OBJECT-TYPE
   SYNTAX      Integer32 (1..100)
   MAX-ACCESS  read-create
   STATUS      current
   DESCRIPTION
       "EPS ID. Range:1-100."
   ::= {sm24dp4xaEPSEntry 2 }

sm24dp4xaEpsDomain OBJECT-TYPE
   SYNTAX      Integer32
   MAX-ACCESS  read-create
   STATUS      current
   DESCRIPTION
       "EPS Domain. Range:0.
	   0:Domain is Port"
   ::= {sm24dp4xaEPSEntry 3 }   
   
sm24dp4xaEpsArchitecture OBJECT-TYPE
   SYNTAX      Integer32
   MAX-ACCESS  read-create
   STATUS      current
   DESCRIPTION
       "EPS Architecture. Range:0-1.
	   0:Architecture is 1+1
	   1:Architecture is 1:1"
   ::= {sm24dp4xaEPSEntry 4 }   
   
sm24dp4xaEpsWFlow OBJECT-TYPE
   SYNTAX      Integer32
   MAX-ACCESS  read-create
   STATUS      current
   DESCRIPTION
       "The working flow for the EPS."
   ::= {sm24dp4xaEPSEntry 5 }  

sm24dp4xaEpsPFlow OBJECT-TYPE
   SYNTAX      Integer32
   MAX-ACCESS  read-create
   STATUS      current
   DESCRIPTION
       "The protecting flow for the EPS"
   ::= {sm24dp4xaEPSEntry 6 }    
   
sm24dp4xaEpsWSFMEP OBJECT-TYPE
   SYNTAX      Integer32
   MAX-ACCESS  read-create
   STATUS      current
   DESCRIPTION
       "The working Signal Fail reporting MEP."
   ::= {sm24dp4xaEPSEntry 7 }     
   
sm24dp4xaEpsPSFMEP OBJECT-TYPE
   SYNTAX      Integer32
   MAX-ACCESS  read-create
   STATUS      current
   DESCRIPTION
       "The protecting Signal Fail reporting MEP."
   ::= {sm24dp4xaEPSEntry 8 }        
   
sm24dp4xaEpsAPSMEP OBJECT-TYPE
   SYNTAX      Integer32
   MAX-ACCESS  read-create
   STATUS      current
   DESCRIPTION
       "The APS PDU handling MEP."
   ::= {sm24dp4xaEPSEntry 9 }
   
sm24dp4xaEpsAlarm OBJECT-TYPE
   SYNTAX      Integer32
   MAX-ACCESS  read-only
   STATUS      current
   DESCRIPTION
       "There is an active alarm on the EPS."
   ::= {sm24dp4xaEPSEntry 10 }  
   
sm24dp4xaEpsRowStatus OBJECT-TYPE
   SYNTAX      RowStatus
   MAX-ACCESS  read-create
   STATUS      current
   DESCRIPTION
       "EPS Row Status."
   ::= {sm24dp4xaEPSEntry 11 }
   
sm24dp4xaEpsConfigInstanceEpsID   OBJECT-TYPE
   SYNTAX      Integer32
   MAX-ACCESS  read-write
   STATUS      current
   DESCRIPTION
	   "Specify EPS ID for table uesd."
   ::= {sm24dp4xaEPS 2 }
   
   
sm24dp4xaEPSConfigInstanceEntry    OBJECT IDENTIFIER ::= { sm24dp4xaEPS 3 } 

sm24dp4xaEpsConfigInstanceProtectionType OBJECT-TYPE
   SYNTAX      Integer32
   MAX-ACCESS  read-write
   STATUS      current
   DESCRIPTION
       "Range:0-1.
	   0:Unidirectional: EPS in the two ends can select traffic from different working/protecting flow. This is only possible in case of 1+1.
       1:Bidirectional: EPS in the two ends is selecting traffic from the same working/protecting flow. This requires APS enabled. This is mandatory for 1:1"
   ::= { sm24dp4xaEPSConfigInstanceEntry 2 }

sm24dp4xaEpsConfigInstanceAPS OBJECT-TYPE
   SYNTAX      Integer32
   MAX-ACCESS  read-write
   STATUS      current
   DESCRIPTION
       "Range:0-1.
	    0:disable
	    1:enable
	    The Automatic Protection Switching protocol can be enabled/disabled. This is mandatory for 1:1."
   ::= { sm24dp4xaEPSConfigInstanceEntry 3 }

sm24dp4xaEpsConfigInstanceRevertive OBJECT-TYPE
   SYNTAX      Integer32
   MAX-ACCESS  read-write
   STATUS      current
   DESCRIPTION
       "Range:0-1.
	    0:disable
	    1:enable
		The revertive switching to working flow can be enabled/disabled.
		"
   ::= { sm24dp4xaEPSConfigInstanceEntry 4 }   
   
sm24dp4xaEpsConfigInstanceWTRTime OBJECT-TYPE
   SYNTAX      Integer32
   MAX-ACCESS  read-write
   STATUS      current
   DESCRIPTION
       "The Wait To Restore timing value to be used in revertive switching. Range is 1 to 720 seconds.
		"
   ::= { sm24dp4xaEPSConfigInstanceEntry 5 }      
   
sm24dp4xaEpsConfigInstanceHoldOffTime OBJECT-TYPE
   SYNTAX      Integer32
   MAX-ACCESS  read-write
   STATUS      current
   DESCRIPTION
       "The timing value to be used to make persistent check on Signal Fail before switching. This is in 100 ms. and the max value is 100 (10 sec)."
   ::= { sm24dp4xaEPSConfigInstanceEntry 6 }     
   
sm24dp4xaEpsConfigInstanceCommand OBJECT-TYPE
   SYNTAX      Integer32
   MAX-ACCESS  read-write
   STATUS      current
   DESCRIPTION
       "0:None
	    1:Clear
		2:Lock Out
		3:Forced switch
		4:Manual switch P
		5:Manual switch W
		6:Exercise
		7:Freeze
		8:Lock Out Local
	   "
   ::= { sm24dp4xaEPSConfigInstanceEntry 7 }     

sm24dp4xaEpsStatusProtectionState OBJECT-TYPE
   SYNTAX      DisplayString
   MAX-ACCESS  read-only
   STATUS      current
   DESCRIPTION
       "EPS state according to State Transition Tables in G.8031.
	   "
   ::= { sm24dp4xaEPSConfigInstanceEntry 8 }
   
sm24dp4xaEpsStatusWorkingFlowState OBJECT-TYPE
   SYNTAX      DisplayString
   MAX-ACCESS  read-only
   STATUS      current
   DESCRIPTION
       "OK: State of working flow is ok
        SF: State of working flow is Signal Fail
		SD: State of working flow is Signal Degrade (for future use)
	   "
   ::= { sm24dp4xaEPSConfigInstanceEntry 9 }   
   
sm24dp4xaEpsStatusProtectingFlowState OBJECT-TYPE
   SYNTAX      DisplayString
   MAX-ACCESS  read-only
   STATUS      current
   DESCRIPTION
       "OK: State of protecting flow is ok
        SF: State of protecting flow is Signal Fail
        SD: State of protecting flow is Signal Degrade (for future use)
	   "
   ::= { sm24dp4xaEPSConfigInstanceEntry 10 }     
   
sm24dp4xaEpsStatusTransmittedApsRequest OBJECT-TYPE
   SYNTAX      DisplayString
   MAX-ACCESS  read-only
   STATUS      current
   DESCRIPTION
       "The transmitted APS according to State Transition Tables in G.8031.
	   "
   ::= { sm24dp4xaEPSConfigInstanceEntry 11 }     
   
sm24dp4xaEpsStatusTransmittedApsReSignal OBJECT-TYPE
   SYNTAX      Integer32
   MAX-ACCESS  read-only
   STATUS      current
   DESCRIPTION
       "The transmitted APS according to State Transition Tables in G.8031.
	   "
   ::= { sm24dp4xaEPSConfigInstanceEntry 12 }    
   
sm24dp4xaEpsStatusTransmittedApsBrSignal OBJECT-TYPE
   SYNTAX      Integer32
   MAX-ACCESS  read-only
   STATUS      current
   DESCRIPTION
       "The transmitted APS according to State Transition Tables in G.8031.
	   "
   ::= { sm24dp4xaEPSConfigInstanceEntry 13 }
   
sm24dp4xaEpsStatusReceivedApsRequest OBJECT-TYPE
   SYNTAX      DisplayString
   MAX-ACCESS  read-only
   STATUS      current
   DESCRIPTION
       "The received APS according to State Transition Tables in G.8031.
	   "
   ::= { sm24dp4xaEPSConfigInstanceEntry 14 }   
   
sm24dp4xaEpsStatusReceivedApsReSignal OBJECT-TYPE
   SYNTAX      Integer32
   MAX-ACCESS  read-only
   STATUS      current
   DESCRIPTION
       "The received APS according to State Transition Tables in G.8031.
	   "
   ::= { sm24dp4xaEPSConfigInstanceEntry 15 }      
   
sm24dp4xaEpsStatusReceivedApsBrSignal OBJECT-TYPE
   SYNTAX      Integer32
   MAX-ACCESS  read-only
   STATUS      current
   DESCRIPTION
       "The received APS according to State Transition Tables in G.8031.
	   "
   ::= { sm24dp4xaEPSConfigInstanceEntry 16 }    

sm24dp4xaEpsStatusArchitectureMismatch OBJECT-TYPE
   SYNTAX      DisplayString
   MAX-ACCESS  read-only
   STATUS      current
   DESCRIPTION
       "The architecture indicated in the received APS does not match the locally configured.
	   "
   ::= { sm24dp4xaEPSConfigInstanceEntry 17 }    

sm24dp4xaEpsStatusAPSOnWorking OBJECT-TYPE
   SYNTAX      DisplayString
   MAX-ACCESS  read-only
   STATUS      current
   DESCRIPTION
       "APS is received on the working flow.
	   "
   ::= { sm24dp4xaEPSConfigInstanceEntry 18 }     
   
sm24dp4xaEpsStatusSwitchingIncomplete OBJECT-TYPE
   SYNTAX      DisplayString
   MAX-ACCESS  read-only
   STATUS      current
   DESCRIPTION
       "Traffic is not selected from the same flow instance in the two ends.
	   "
   ::= { sm24dp4xaEPSConfigInstanceEntry 19 }     
   
sm24dp4xaEpsStatusNoApsReceived OBJECT-TYPE
   SYNTAX      DisplayString
   MAX-ACCESS  read-only
   STATUS      current
   DESCRIPTION
       "APS PDU is not received from the other end.
	   "
   ::= { sm24dp4xaEPSConfigInstanceEntry 20 }      
   
-- =======================================================================================================================
 
sm24dp4xaERPS    OBJECT IDENTIFIER ::= { sm24dp4xaConfiguration 24 }

sm24dp4xaERPSTable  OBJECT-TYPE
   SYNTAX      SEQUENCE OF SM24DP4XAERPSEntry
   MAX-ACCESS  not-accessible
   STATUS      current
   DESCRIPTION
       "A table of ERPS."
 ::= { sm24dp4xaERPS 1 }

sm24dp4xaERPSEntry OBJECT-TYPE
    SYNTAX        SM24DP4XAERPSEntry
    MAX-ACCESS    not-accessible
    STATUS        current
    DESCRIPTION
        ""
    INDEX        { sm24dp4xaErpsIndex }
    ::= { sm24dp4xaERPSTable 1 }

SM24DP4XAERPSEntry ::=
    SEQUENCE {
        sm24dp4xaErpsIndex                                Integer32,
        sm24dp4xaErpsID                                   Integer32,
		sm24dp4xaErpsPort0                                Integer32,
		sm24dp4xaErpsPort1                                Integer32,
		sm24dp4xaErpsPort0APSMEP                          Integer32,		
        sm24dp4xaErpsPort1APSMEP                          Integer32,
        sm24dp4xaErpsPort0SFMEP                           Integer32,
        sm24dp4xaErpsPort1SFMEP                           Integer32,	
        sm24dp4xaErpsRingType                             Integer32,		
        sm24dp4xaErpsInterconnectedNode                   Integer32,		
        sm24dp4xaErpsVirtualChannel                       Integer32,		
        sm24dp4xaErpsMajorRingID                          Integer32,	
        sm24dp4xaErpsAlarm		                          Integer32,
        sm24dp4xaErpsRowStatus                            RowStatus
    }

sm24dp4xaErpsIndex OBJECT-TYPE
   SYNTAX      Integer32 (1..65535)
   MAX-ACCESS  not-accessible
   STATUS      current
   DESCRIPTION
       "Index"
   ::= { sm24dp4xaERPSEntry 1 }

sm24dp4xaErpsID OBJECT-TYPE
   SYNTAX      Integer32 (1..64)
   MAX-ACCESS  read-create
   STATUS      current
   DESCRIPTION
       "ERPS ID. Range:1-64."
   ::= {sm24dp4xaERPSEntry 2 }

sm24dp4xaErpsPort0 OBJECT-TYPE
   SYNTAX      Integer32
   MAX-ACCESS  read-create
   STATUS      current
   DESCRIPTION
       "This will create a Port 0 of the switch in the ring."
   ::= {sm24dp4xaERPSEntry 3 }   
   
sm24dp4xaErpsPort1 OBJECT-TYPE
   SYNTAX      Integer32
   MAX-ACCESS  read-create
   STATUS      current
   DESCRIPTION
       "This will create Port 1 of the switch in the Ring. 
	   As interconnected sub-ring will have only one ring port, Port 1 is configured as 0 for interconnected sub-ring.
	   0 in this field indicates that no Port 1 is associated with this instance"
   ::= {sm24dp4xaERPSEntry 4 }   
   
sm24dp4xaErpsPort0APSMEP OBJECT-TYPE
   SYNTAX      Integer32
   MAX-ACCESS  read-create
   STATUS      current
   DESCRIPTION
       "The Port 0 APS PDU handling MEP.
	   Range: 1-100."
   ::= {sm24dp4xaERPSEntry 5 }  
   
sm24dp4xaErpsPort1APSMEP OBJECT-TYPE
   SYNTAX      Integer32
   MAX-ACCESS  read-create
   STATUS      current
   DESCRIPTION
       "The Port 1 APS PDU handling MEP.
	   Range: 1-100."
   ::= {sm24dp4xaERPSEntry 6 }     

sm24dp4xaErpsPort0SFMEP OBJECT-TYPE
   SYNTAX      Integer32
   MAX-ACCESS  read-create
   STATUS      current
   DESCRIPTION
       "The Port 0 Signal Fail reporting MEP.
	   Range: 1-100."
   ::= {sm24dp4xaERPSEntry 7 }      
   
 sm24dp4xaErpsPort1SFMEP OBJECT-TYPE
   SYNTAX      Integer32
   MAX-ACCESS  read-create
   STATUS      current
   DESCRIPTION
       "The Port 1 Signal Fail reporting MEP.
	   Range: 1-100."
   ::= {sm24dp4xaERPSEntry 8 }      
   
sm24dp4xaErpsRingType OBJECT-TYPE
   SYNTAX      Integer32
   MAX-ACCESS  read-create
   STATUS      current
   DESCRIPTION
       "Type of Protecting ring. It can be either major ring or sub-ring.
	   0:Major
	   1:Sub"
   ::= {sm24dp4xaERPSEntry 9 }
   
sm24dp4xaErpsInterconnectedNode OBJECT-TYPE
   SYNTAX      Integer32
   MAX-ACCESS  read-create
   STATUS      current
   DESCRIPTION
       "Interconnected Node indicates that the ring instance is interconnected. 
	   0: not interconnected
	   1: interconnected"
   ::= {sm24dp4xaERPSEntry 10 }  
   
sm24dp4xaErpsVirtualChannel OBJECT-TYPE
   SYNTAX      Integer32
   MAX-ACCESS  read-create
   STATUS      current
   DESCRIPTION
       "1: indicates it is a sub-ring with virtual channel. 
	    0: indicates, sub-ring doesn't have virtual channel."
   ::= {sm24dp4xaERPSEntry 11 }
   
sm24dp4xaErpsMajorRingID OBJECT-TYPE
   SYNTAX      Integer32
   MAX-ACCESS  read-create
   STATUS      current
   DESCRIPTION
       "Major ring group ID for the interconnected sub-ring.
	   Range:1-64"
   ::= {sm24dp4xaERPSEntry 12 }   

sm24dp4xaErpsAlarm OBJECT-TYPE
   SYNTAX      Integer32
   MAX-ACCESS  read-create
   STATUS      current
   DESCRIPTION
       "There is an active alarm on the ERPS."
   ::= {sm24dp4xaERPSEntry 13 }  
   
sm24dp4xaErpsRowStatus OBJECT-TYPE
   SYNTAX      RowStatus
   MAX-ACCESS  read-create
   STATUS      current
   DESCRIPTION
       "ERPS Row Status."
   ::= {sm24dp4xaERPSEntry 14 }      
  
   
sm24dp4xaErpsConfigInstanceErpsID   OBJECT-TYPE
   SYNTAX      Integer32
   MAX-ACCESS  read-write
   STATUS      current
   DESCRIPTION
	   "Specify ERPS ID for ERPSConfigInstanceEntry and ErpsConfigInstanceVLANConfigTable uesd."
   ::= {sm24dp4xaERPS 2 }
   

sm24dp4xaERPSConfigInstanceEntry    OBJECT IDENTIFIER ::= { sm24dp4xaERPS 3 } 

sm24dp4xaErpsConfigInstanceConfigured OBJECT-TYPE
   SYNTAX      DisplayString
   MAX-ACCESS  read-only
   STATUS      current
   DESCRIPTION
       "Down: This ERPS is only created and has not yet been configured - is not active.
        Up: This ERPS is configured - is active."
   ::= { sm24dp4xaERPSConfigInstanceEntry 2 }

sm24dp4xaErpsConfigInstanceGuardTime OBJECT-TYPE
   SYNTAX      Integer32
   MAX-ACCESS  read-write
   STATUS      current
   DESCRIPTION
       "The period of the guard timer can be configured in 10 ms steps between 10 ms and 2 seconds, with a default value of 500 ms.
	    Guard timeout value to be used to prevent ring nodes from receiving outdated R-APS messages."
   ::= { sm24dp4xaERPSConfigInstanceEntry 3 }

sm24dp4xaErpsConfigInstanceWTRTime OBJECT-TYPE
   SYNTAX      Integer32
   MAX-ACCESS  read-write
   STATUS      current
   DESCRIPTION
       "The Wait To Restore timing value to be used in revertive switching.
        The period of the WTR time can be configured by the operator in 1 minute steps between 5 and 12 minutes with a default value of 5 minutes.
		"
   ::= { sm24dp4xaERPSConfigInstanceEntry 4 }   
   
sm24dp4xaErpsConfigInstanceHoldOffTime OBJECT-TYPE
   SYNTAX      Integer32
   MAX-ACCESS  read-write
   STATUS      current
   DESCRIPTION
       "The timing value to be used to make persistent check on Signal Fail before switching.
        The range of the hold off timer is 0 to 10 seconds in steps of 100 ms
		"
   ::= { sm24dp4xaERPSConfigInstanceEntry 5 }      
   
sm24dp4xaErpsConfigInstanceVersion OBJECT-TYPE
   SYNTAX      Integer32
   MAX-ACCESS  read-write
   STATUS      current
   DESCRIPTION
       "ERPS Protocol Version - v1 or v2
	   1:v1
	   2:v2"
   ::= { sm24dp4xaERPSConfigInstanceEntry 6 }     
   
sm24dp4xaErpsConfigInstanceRevertive OBJECT-TYPE
   SYNTAX      Integer32
   MAX-ACCESS  read-write
   STATUS      current
   DESCRIPTION
       "1:Revertive mode
	    0:Non-Revertive mode"
   ::= { sm24dp4xaERPSConfigInstanceEntry 7 }     

sm24dp4xaErpsConfigInstanceRPLRole OBJECT-TYPE
   SYNTAX      Integer32
   MAX-ACCESS  read-write
   STATUS      current
   DESCRIPTION
       "It can be either RPL owner or RPL Neighbor.
	   0:None 
	   1:RPL owner
	   2:RPL Neighbor
	   Please set RPLPort first.
	   "
   ::= { sm24dp4xaERPSConfigInstanceEntry 8 }
   
sm24dp4xaErpsConfigInstanceRPLPort OBJECT-TYPE
   SYNTAX      Integer32
   MAX-ACCESS  read-write
   STATUS      current
   DESCRIPTION
       "This allows to select the east port or west port as the RPL block.
	   0:None
	   1:Port0
	   2:Port1
	   Please set RPLRole after specify RPLPort.
	   "
   ::= { sm24dp4xaERPSConfigInstanceEntry 9 }   
   
sm24dp4xaErpsConfigInstanceClear OBJECT-TYPE
   SYNTAX      Integer32
   MAX-ACCESS  read-write
   STATUS      current
   DESCRIPTION
       "If the owner has to be changed, then the clear check box allows to clear the RPL owner for that ERPS ring.
	   0: no clear
	   1: clear
	   "
   ::= { sm24dp4xaERPSConfigInstanceEntry 10 }     
   
sm24dp4xaErpsConfigInstanceTopologyChange OBJECT-TYPE
   SYNTAX      Integer32
   MAX-ACCESS  read-write
   STATUS      current
   DESCRIPTION
       "1: indicates that the topology changes in the sub-ring are propagated in the major ring.
	    0: indicates that the topology changes in the sub-ring are not propagated in the major ring.
	   "
   ::= { sm24dp4xaERPSConfigInstanceEntry 11 }     
 
sm24dp4xaErpsConfigInstanceCommand OBJECT-TYPE
   SYNTAX      Integer32
   MAX-ACCESS  read-write
   STATUS      current
   DESCRIPTION
       "0:None
	    1:Manual Switch
		2:Forced Switch
		3:Clear
		Please set InstancePort first.
	   "
   ::= { sm24dp4xaERPSConfigInstanceEntry 12 }  
 
sm24dp4xaErpsConfigInstancePort OBJECT-TYPE
   SYNTAX      Integer32
   MAX-ACCESS  read-write
   STATUS      current
   DESCRIPTION
       "0:None
	   1:Port0
	   2:Port1
	   Please set InstanceCommand after specify InstancePort.
	   "
   ::= { sm24dp4xaERPSConfigInstanceEntry 13 }     
   
sm24dp4xaErpsStatusProtectionState OBJECT-TYPE
   SYNTAX      DisplayString
   MAX-ACCESS  read-only
   STATUS      current
   DESCRIPTION
       "ERPS state according to State Transition Tables in G.8032.
	   "
   ::= { sm24dp4xaERPSConfigInstanceEntry 14 }        
   
sm24dp4xaErpsStatusPort0 OBJECT-TYPE
   SYNTAX      DisplayString
   MAX-ACCESS  read-only
   STATUS      current
   DESCRIPTION
       "OK: State of East port is ok
        SF: State of East port is Signal Fail
	   "
   ::= { sm24dp4xaERPSConfigInstanceEntry 15 }        
   
sm24dp4xaErpsStatusPort1 OBJECT-TYPE
   SYNTAX      DisplayString
   MAX-ACCESS  read-only
   STATUS      current
   DESCRIPTION
       "OK: State of West port is ok
        SF: State of West port is Signal Fail
	   "
   ::= { sm24dp4xaERPSConfigInstanceEntry 16 }    
   
sm24dp4xaErpsStatusTransmitAPS OBJECT-TYPE
   SYNTAX      DisplayString
   MAX-ACCESS  read-only
   STATUS      current
   DESCRIPTION
       "The transmitted APS according to State Transition Tables in G.8032.
	   "
   ::= { sm24dp4xaERPSConfigInstanceEntry 17 }    

sm24dp4xaErpsStatusPort0ReceiveAPS OBJECT-TYPE
   SYNTAX      DisplayString
   MAX-ACCESS  read-only
   STATUS      current
   DESCRIPTION
       "The received APS on Port 0 according to State Transition Tables in G.8032.
	   "
   ::= { sm24dp4xaERPSConfigInstanceEntry 18 } 

sm24dp4xaErpsStatusPort1ReceiveAPS OBJECT-TYPE
   SYNTAX      DisplayString
   MAX-ACCESS  read-only
   STATUS      current
   DESCRIPTION
       "The received APS on Port 1 according to State Transition Tables in G.8032.
	   "
   ::= { sm24dp4xaERPSConfigInstanceEntry 19 }    
   
sm24dp4xaErpsStatusWTRRemaining OBJECT-TYPE
   SYNTAX      Integer32
   MAX-ACCESS  read-only
   STATUS      current
   DESCRIPTION
       "Remaining WTR timeout in milliseconds.
	   "
   ::= { sm24dp4xaERPSConfigInstanceEntry 20 }   
   
sm24dp4xaErpsStatusRPLUnblocked OBJECT-TYPE
   SYNTAX      DisplayString
   MAX-ACCESS  read-only
   STATUS      current
   DESCRIPTION
       "APS is received on the working flow.
	   "
   ::= { sm24dp4xaERPSConfigInstanceEntry 21 }      
   
sm24dp4xaErpsStatusNoAPSReceived OBJECT-TYPE
   SYNTAX      DisplayString
   MAX-ACCESS  read-only
   STATUS      current
   DESCRIPTION
       "RAPS PDU is not received from the other end.
	   "
   ::= { sm24dp4xaERPSConfigInstanceEntry 22 }   
   
sm24dp4xaErpsStatusPort0BlockStatus OBJECT-TYPE
   SYNTAX      DisplayString
   MAX-ACCESS  read-only
   STATUS      current
   DESCRIPTION
       "Block status for Port 0 (Both traffic and R-APS block status). R-APS channel is never blocked on sub-rings without virtual channel.
	   "
   ::= { sm24dp4xaERPSConfigInstanceEntry 23 }      
   
sm24dp4xaErpsStatusPort1BlockStatus OBJECT-TYPE
   SYNTAX      DisplayString
   MAX-ACCESS  read-only
   STATUS      current
   DESCRIPTION
       "Block status for Port 1 (Both traffic and R-APS block status). R-APS channel is never blocked on sub-rings without virtual channel.
	   "
   ::= { sm24dp4xaERPSConfigInstanceEntry 24 }       
   
sm24dp4xaErpsStatusFOPAlarm OBJECT-TYPE
   SYNTAX      DisplayString
   MAX-ACCESS  read-only
   STATUS      current
   DESCRIPTION
       "Failure of Protocol Defect(FOP) status:
	   FOP is not detected
	   FOP is detected
	   "
   ::= { sm24dp4xaERPSConfigInstanceEntry 25 }      
   
sm24dp4xaErpsConfigInstanceVLANConfigTable  OBJECT-TYPE
   SYNTAX      SEQUENCE OF SM24DP4XAErpsConfigInstanceVLANConfigEntry
   MAX-ACCESS  not-accessible
   STATUS      current
   DESCRIPTION
       "A table of ERPS VLANConfig."
 ::= { sm24dp4xaERPS 4 }

sm24dp4xaErpsConfigInstanceVLANConfigEntry OBJECT-TYPE
    SYNTAX        SM24DP4XAErpsConfigInstanceVLANConfigEntry
    MAX-ACCESS    not-accessible
    STATUS        current
    DESCRIPTION
        ""
    INDEX        { sm24dp4xaErpsConfigInstanceVLANConfigIndex }
    ::= { sm24dp4xaErpsConfigInstanceVLANConfigTable 1 }

SM24DP4XAErpsConfigInstanceVLANConfigEntry ::=
    SEQUENCE {
        sm24dp4xaErpsConfigInstanceVLANConfigIndex            Integer32,
        sm24dp4xaErpsConfigInstanceVLANConfigVLANID           Integer32,
        sm24dp4xaErpsConfigInstanceVLANConfigRowStatus        RowStatus
    }

sm24dp4xaErpsConfigInstanceVLANConfigIndex OBJECT-TYPE
   SYNTAX      Integer32 (1..65535)
   MAX-ACCESS  not-accessible
   STATUS      current
   DESCRIPTION
       "Index"
   ::= { sm24dp4xaErpsConfigInstanceVLANConfigEntry 1 }

sm24dp4xaErpsConfigInstanceVLANConfigVLANID OBJECT-TYPE
   SYNTAX      Integer32 (1..4095)
   MAX-ACCESS  read-create
   STATUS      current
   DESCRIPTION
       "ERPS VLAN Config ID. Range:1-4095."
   ::= {sm24dp4xaErpsConfigInstanceVLANConfigEntry 2 }

sm24dp4xaErpsConfigInstanceVLANConfigRowStatus OBJECT-TYPE
   SYNTAX      RowStatus
   MAX-ACCESS  read-create
   STATUS      current
   DESCRIPTION
       "ERPS VLAN Config Row Status."
   ::= {sm24dp4xaErpsConfigInstanceVLANConfigEntry 3 }   
-- =======================================================================================================================

sm24dp4xaVLANTranslation    OBJECT IDENTIFIER ::= { sm24dp4xaConfiguration 25 }

sm24dp4xaVLANTranslationPortTable  OBJECT-TYPE
   SYNTAX      SEQUENCE OF SM24DP4XAVLANTranslationPortEntry
   MAX-ACCESS  not-accessible
   STATUS      current
   DESCRIPTION
       "A table of VLANTranslationPort."
 ::= { sm24dp4xaVLANTranslation 1 }

sm24dp4xaVLANTranslationPortEntry OBJECT-TYPE
    SYNTAX        SM24DP4XAVLANTranslationPortEntry
    MAX-ACCESS    not-accessible
    STATUS        current
    DESCRIPTION
        "An entry in the VLANTranslationPort table."
    INDEX        { sm24dp4xaVLANTranslationPortIndex }
    ::= { sm24dp4xaVLANTranslationPortTable 1 }

SM24DP4XAVLANTranslationPortEntry ::=
    SEQUENCE {
        sm24dp4xaVLANTranslationPortIndex                Integer32,
        sm24dp4xaVLANTranslationPortDefault              Integer32,
        sm24dp4xaVLANTranslationPortGroupID              Integer32
    }

sm24dp4xaVLANTranslationPortIndex OBJECT-TYPE
   SYNTAX      Integer32 (1..65535)
   MAX-ACCESS  not-accessible
   STATUS      current
   DESCRIPTION
       "VLANTranslationPort index."
   ::= {sm24dp4xaVLANTranslationPortEntry 1 }

sm24dp4xaVLANTranslationPortDefault OBJECT-TYPE
   SYNTAX      Integer32
   MAX-ACCESS  read-write
   STATUS      current
   DESCRIPTION
       "Set the switch port to use the default VLAN Translation Group.
	   1:set
	   0:not set"
   ::= {sm24dp4xaVLANTranslationPortEntry 2 }

sm24dp4xaVLANTranslationPortGroupID OBJECT-TYPE
   SYNTAX      Integer32
   MAX-ACCESS  read-write
   STATUS      current
   DESCRIPTION
       "The VLAN Translation mappings are organized into Groups, identified by the Group ID."
   ::= {sm24dp4xaVLANTranslationPortEntry 3 }
   
   
   
sm24dp4xaVLANTranslationMappingTable  OBJECT-TYPE
   SYNTAX      SEQUENCE OF SM24DP4XAVLANTranslationMappingEntry
   MAX-ACCESS  not-accessible
   STATUS      current
   DESCRIPTION
       "A table of VLANTranslationMapping."
 ::= { sm24dp4xaVLANTranslation 2 }

sm24dp4xaVLANTranslationMappingEntry OBJECT-TYPE
    SYNTAX        SM24DP4XAVLANTranslationMappingEntry
    MAX-ACCESS    not-accessible
    STATUS        current
    DESCRIPTION
        "An entry in the VLANTranslationMapping table."
    INDEX        { sm24dp4xaVLANTranslationMappingIndex }
    ::= { sm24dp4xaVLANTranslationMappingTable 1 }

SM24DP4XAVLANTranslationMappingEntry ::=
    SEQUENCE {
        sm24dp4xaVLANTranslationMappingIndex                Integer32,
        sm24dp4xaVLANTranslationMappingGroupID              Integer32,
        sm24dp4xaVLANTranslationMappingVID                  Integer32,
		sm24dp4xaVLANTranslationMappingTVID                 Integer32,
		sm24dp4xaVLANTranslationMappingRowStatus            RowStatus
    }

sm24dp4xaVLANTranslationMappingIndex OBJECT-TYPE
   SYNTAX      Integer32 (1..65535)
   MAX-ACCESS  not-accessible
   STATUS      current
   DESCRIPTION
       "VLANTranslationMapping index."
   ::= {sm24dp4xaVLANTranslationMappingEntry 1 }

sm24dp4xaVLANTranslationMappingGroupID OBJECT-TYPE
   SYNTAX      Integer32
   MAX-ACCESS  read-create
   STATUS      current
   DESCRIPTION
       "The VLAN Translation mappings are organized into Groups, identified by the Group ID."
   ::= {sm24dp4xaVLANTranslationMappingEntry 2 }

sm24dp4xaVLANTranslationMappingVID OBJECT-TYPE
   SYNTAX      Integer32
   MAX-ACCESS  read-create
   STATUS      current
   DESCRIPTION
       "Range:1-4095"
   ::= {sm24dp4xaVLANTranslationMappingEntry 3 }

sm24dp4xaVLANTranslationMappingTVID OBJECT-TYPE
   SYNTAX      Integer32
   MAX-ACCESS  read-create
   STATUS      current
   DESCRIPTION
       "Range:1-4095"
   ::= {sm24dp4xaVLANTranslationMappingEntry 4 }   
   
sm24dp4xaVLANTranslationMappingRowStatus OBJECT-TYPE
   SYNTAX      RowStatus
   MAX-ACCESS  read-create
   STATUS      current
   DESCRIPTION
       "VLANTranslationMapping Row Status."
   ::= {sm24dp4xaVLANTranslationMappingEntry 5 }
   
sm24dp4xaMEP    OBJECT IDENTIFIER ::= { sm24dp4xaConfiguration 26 }    

sm24dp4xaMEPTable  OBJECT-TYPE
   SYNTAX      SEQUENCE OF SM24DP4XAMEPEntry
   MAX-ACCESS  not-accessible
   STATUS      current
   DESCRIPTION
       "A table of MEP."
 ::= { sm24dp4xaMEP 1 }

sm24dp4xaMEPEntry OBJECT-TYPE
    SYNTAX        SM24DP4XAMEPEntry
    MAX-ACCESS    not-accessible
    STATUS        current
    DESCRIPTION
        "An entry in the MEP table."
    INDEX        { sm24dp4xaMEPIndex }
    ::= { sm24dp4xaMEPTable 1 }

SM24DP4XAMEPEntry ::=
    SEQUENCE {
        sm24dp4xaMEPIndex                         Integer32,
        sm24dp4xaMepInstance                      Integer32,
        sm24dp4xaMepDomain                        Integer32,
        sm24dp4xaMepMode                          Integer32,
		sm24dp4xaMepDirection                     Integer32,
		sm24dp4xaMepResidencePort                 Integer32,
		sm24dp4xaMepLevel                         Integer32,
		sm24dp4xaMepFlowInstance                  Integer32,
		sm24dp4xaMepTaggedVID                     Integer32,
		sm24dp4xaMepEPSInstance                   DisplayString,
		sm24dp4xaMepThisMAC                       DisplayString,
		sm24dp4xaMepAlarm                         DisplayString,
        sm24dp4xaMepRowStatus                     RowStatus
    }

sm24dp4xaMEPIndex OBJECT-TYPE
   SYNTAX      Integer32 (1..65535)
   MAX-ACCESS  not-accessible
   STATUS      current
   DESCRIPTION
       "MEP Table index."
   ::= {sm24dp4xaMEPEntry 1 }

sm24dp4xaMepInstance OBJECT-TYPE
   SYNTAX      Integer32
   MAX-ACCESS  read-create
   STATUS      current
   DESCRIPTION
       ""
   ::= {sm24dp4xaMEPEntry 2 }

sm24dp4xaMepDomain OBJECT-TYPE
   SYNTAX      Integer32
   MAX-ACCESS  read-create
   STATUS      current
   DESCRIPTION
       ""
   ::= {sm24dp4xaMEPEntry 3 }  
   
sm24dp4xaMepMode OBJECT-TYPE
   SYNTAX      Integer32
   MAX-ACCESS  read-create
   STATUS      current
   DESCRIPTION
       ""
   ::= {sm24dp4xaMEPEntry 4 }    

sm24dp4xaMepDirection OBJECT-TYPE
   SYNTAX      Integer32
   MAX-ACCESS  read-create
   STATUS      current
   DESCRIPTION
       ""
   ::= {sm24dp4xaMEPEntry 5 }  

sm24dp4xaMepResidencePort OBJECT-TYPE
   SYNTAX      Integer32
   MAX-ACCESS  read-create
   STATUS      current
   DESCRIPTION
       ""
   ::= {sm24dp4xaMEPEntry 6 }  

sm24dp4xaMepLevel OBJECT-TYPE
   SYNTAX      Integer32
   MAX-ACCESS  read-create
   STATUS      current
   DESCRIPTION
       ""
   ::= {sm24dp4xaMEPEntry 7 }  

sm24dp4xaMepFlowInstance OBJECT-TYPE
   SYNTAX      Integer32
   MAX-ACCESS  read-create
   STATUS      current
   DESCRIPTION
       ""
   ::= {sm24dp4xaMEPEntry 8 }  

sm24dp4xaMepTaggedVID OBJECT-TYPE
   SYNTAX      Integer32
   MAX-ACCESS  read-create
   STATUS      current
   DESCRIPTION
       ""
   ::= {sm24dp4xaMEPEntry 9 }    

sm24dp4xaMepEPSInstance OBJECT-TYPE
   SYNTAX      DisplayString
   MAX-ACCESS  read-only
   STATUS      current
   DESCRIPTION
       ""
   ::= {sm24dp4xaMEPEntry 10 }     
   
sm24dp4xaMepThisMAC OBJECT-TYPE
   SYNTAX      DisplayString
   MAX-ACCESS  read-only
   STATUS      current
   DESCRIPTION
       ""
   ::= {sm24dp4xaMEPEntry 11 }

sm24dp4xaMepAlarm OBJECT-TYPE
   SYNTAX      DisplayString
   MAX-ACCESS  read-only
   STATUS      current
   DESCRIPTION
       ""
   ::= {sm24dp4xaMEPEntry 12 }  
   
sm24dp4xaMepRowStatus OBJECT-TYPE
   SYNTAX      RowStatus
   MAX-ACCESS  read-create
   STATUS      current
   DESCRIPTION
       "MEP Row Status."
   ::= {sm24dp4xaMEPEntry 13 }
 
sm24dp4xaMepInstanceID   OBJECT-TYPE
   SYNTAX      Integer32
   MAX-ACCESS  read-write
   STATUS      current
   DESCRIPTION
	   "Specify MEP Instance ID for the following item and table uesd."
   ::= {sm24dp4xaMEP 2 } 
 

sm24dp4xaMepInstanceConfEntry    OBJECT IDENTIFIER ::= { sm24dp4xaMEP 3 }

sm24dp4xaMepInstanceConfLevel OBJECT-TYPE
   SYNTAX      Integer32
   MAX-ACCESS  read-write
   STATUS      current
   DESCRIPTION
       ""
   ::= {sm24dp4xaMepInstanceConfEntry 2 }  

sm24dp4xaMepInstanceConfFormat OBJECT-TYPE
   SYNTAX      Integer32
   MAX-ACCESS  read-write
   STATUS      current
   DESCRIPTION
       ""
   ::= {sm24dp4xaMepInstanceConfEntry 3 }  

sm24dp4xaMepInstanceConfDomainName OBJECT-TYPE
   SYNTAX      DisplayString
   MAX-ACCESS  read-write
   STATUS      current
   DESCRIPTION
       ""
   ::= {sm24dp4xaMepInstanceConfEntry 4 }  

sm24dp4xaMepInstanceConfMEGid OBJECT-TYPE
   SYNTAX      DisplayString
   MAX-ACCESS  read-write
   STATUS      current
   DESCRIPTION
       ""
   ::= {sm24dp4xaMepInstanceConfEntry 5 } 

sm24dp4xaMepInstanceConfMEPid OBJECT-TYPE
   SYNTAX      Integer32
   MAX-ACCESS  read-write
   STATUS      current
   DESCRIPTION
       ""
   ::= {sm24dp4xaMepInstanceConfEntry 6 }   

sm24dp4xaMepInstanceConfTaggedVID OBJECT-TYPE
   SYNTAX      Integer32
   MAX-ACCESS  read-write
   STATUS      current
   DESCRIPTION
       ""
   ::= {sm24dp4xaMepInstanceConfEntry 7 }      
  
sm24dp4xaMepInstanceConfSyslog OBJECT-TYPE
   SYNTAX      Integer32
   MAX-ACCESS  read-write
   STATUS      current
   DESCRIPTION
       ""
   ::= {sm24dp4xaMepInstanceConfEntry 8 }  
  
sm24dp4xaMepInstanceConfcLevel OBJECT-TYPE
   SYNTAX      DisplayString
   MAX-ACCESS  read-only
   STATUS      current
   DESCRIPTION
       ""
   ::= {sm24dp4xaMepInstanceConfEntry 9 }  
 
sm24dp4xaMepInstanceConfcMEG OBJECT-TYPE
   SYNTAX      DisplayString
   MAX-ACCESS  read-only
   STATUS      current
   DESCRIPTION
       ""
   ::= {sm24dp4xaMepInstanceConfEntry 10 }   
 
sm24dp4xaMepInstanceConfcMEP OBJECT-TYPE
   SYNTAX      DisplayString
   MAX-ACCESS  read-only
   STATUS      current
   DESCRIPTION
       ""
   ::= {sm24dp4xaMepInstanceConfEntry 11 }   
 
sm24dp4xaMepInstanceConfcAIS OBJECT-TYPE
   SYNTAX      DisplayString
   MAX-ACCESS  read-only
   STATUS      current
   DESCRIPTION
       ""
   ::= {sm24dp4xaMepInstanceConfEntry 12 }   
   
sm24dp4xaMepInstanceConfcLCK OBJECT-TYPE
   SYNTAX      DisplayString
   MAX-ACCESS  read-only
   STATUS      current
   DESCRIPTION
       ""
   ::= {sm24dp4xaMepInstanceConfEntry 13 }   
 
sm24dp4xaMepInstanceConfcLoop OBJECT-TYPE
   SYNTAX      DisplayString
   MAX-ACCESS  read-only
   STATUS      current
   DESCRIPTION
       ""
   ::= {sm24dp4xaMepInstanceConfEntry 14 }  

sm24dp4xaMepInstanceConfcConfig OBJECT-TYPE
   SYNTAX      DisplayString
   MAX-ACCESS  read-only
   STATUS      current
   DESCRIPTION
       ""
   ::= {sm24dp4xaMepInstanceConfEntry 15 }  

sm24dp4xaMepInstanceConfcDEG OBJECT-TYPE
   SYNTAX      DisplayString
   MAX-ACCESS  read-only
   STATUS      current
   DESCRIPTION
       ""
   ::= {sm24dp4xaMepInstanceConfEntry 16 }  

sm24dp4xaMepInstanceConfcSSF OBJECT-TYPE
   SYNTAX      DisplayString
   MAX-ACCESS  read-only
   STATUS      current
   DESCRIPTION
       ""
   ::= {sm24dp4xaMepInstanceConfEntry 17 }  

sm24dp4xaMepInstanceConfaBLK OBJECT-TYPE
   SYNTAX      DisplayString
   MAX-ACCESS  read-only
   STATUS      current
   DESCRIPTION
       ""
   ::= {sm24dp4xaMepInstanceConfEntry 18 }  

sm24dp4xaMepInstanceConfaTSD OBJECT-TYPE
   SYNTAX      DisplayString
   MAX-ACCESS  read-only
   STATUS      current
   DESCRIPTION
       ""
   ::= {sm24dp4xaMepInstanceConfEntry 19 }  

sm24dp4xaMepInstanceConfaTSF OBJECT-TYPE
   SYNTAX      DisplayString
   MAX-ACCESS  read-only
   STATUS      current
   DESCRIPTION
       ""
   ::= {sm24dp4xaMepInstanceConfEntry 20 }     
 
 
sm24dp4xaPeerMepConfTable  OBJECT-TYPE
   SYNTAX      SEQUENCE OF SM24DP4XAPeerMepConfEntry
   MAX-ACCESS  not-accessible
   STATUS      current
   DESCRIPTION
       "A table of MEP."
 ::= { sm24dp4xaMEP 4 }

sm24dp4xaPeerMepConfEntry OBJECT-TYPE
    SYNTAX        SM24DP4XAPeerMepConfEntry
    MAX-ACCESS    not-accessible
    STATUS        current
    DESCRIPTION
        ""
    INDEX        { sm24dp4xaPeerMepConfIndex }
    ::= { sm24dp4xaPeerMepConfTable 1 }

SM24DP4XAPeerMepConfEntry ::=
    SEQUENCE {
        sm24dp4xaPeerMepConfIndex                       Integer32,
        sm24dp4xaPeerMepConfPeerMEPID                   Integer32,
		sm24dp4xaPeerMepConfUnicastPeerMAC              DisplayString,
        sm24dp4xaPeerMepConfcLOC                        DisplayString,
        sm24dp4xaPeerMepConfcRDI                        DisplayString,
        sm24dp4xaPeerMepConfcPeriod                     DisplayString,	
        sm24dp4xaPeerMepConfcPriority                   DisplayString,			
        sm24dp4xaPeerMepConfRowStatus                   RowStatus
    }

sm24dp4xaPeerMepConfIndex OBJECT-TYPE
   SYNTAX      Integer32 (1..65535)
   MAX-ACCESS  not-accessible
   STATUS      current
   DESCRIPTION
       "Index"
   ::= { sm24dp4xaPeerMepConfEntry 1 }

sm24dp4xaPeerMepConfPeerMEPID OBJECT-TYPE
   SYNTAX      Integer32 
   MAX-ACCESS  read-create
   STATUS      current
   DESCRIPTION
       "Peer MEP ID"
   ::= {sm24dp4xaPeerMepConfEntry 2 }

sm24dp4xaPeerMepConfUnicastPeerMAC OBJECT-TYPE
   SYNTAX      DisplayString
   MAX-ACCESS  read-create
   STATUS      current
   DESCRIPTION
       ""
   ::= {sm24dp4xaPeerMepConfEntry 3 }   
   
sm24dp4xaPeerMepConfcLOC OBJECT-TYPE
   SYNTAX      DisplayString
   MAX-ACCESS  read-create
   STATUS      current
   DESCRIPTION
       ""
   ::= {sm24dp4xaPeerMepConfEntry 4 }      
   
sm24dp4xaPeerMepConfcRDI OBJECT-TYPE
   SYNTAX      DisplayString
   MAX-ACCESS  read-create
   STATUS      current
   DESCRIPTION
       ""
   ::= {sm24dp4xaPeerMepConfEntry 5 }    
   
sm24dp4xaPeerMepConfcPeriod OBJECT-TYPE
   SYNTAX      DisplayString
   MAX-ACCESS  read-create
   STATUS      current
   DESCRIPTION
       ""
   ::= {sm24dp4xaPeerMepConfEntry 6 }  

sm24dp4xaPeerMepConfcPriority OBJECT-TYPE
   SYNTAX      DisplayString
   MAX-ACCESS  read-create
   STATUS      current
   DESCRIPTION
       ""
   ::= {sm24dp4xaPeerMepConfEntry 7 }  
   
sm24dp4xaPeerMepConfRowStatus OBJECT-TYPE
   SYNTAX      RowStatus
   MAX-ACCESS  read-create
   STATUS      current
   DESCRIPTION
       "Peer Mep Conf Row Status."
   ::= {sm24dp4xaPeerMepConfEntry 8 }
   
sm24dp4xaFunctionalConf    OBJECT IDENTIFIER ::= { sm24dp4xaMEP 5 }

sm24dp4xaFunctionalConfContinuityCheckEnable OBJECT-TYPE
   SYNTAX      Integer32
   MAX-ACCESS  read-write
   STATUS      current
   DESCRIPTION
       "0:disable
	   1:enable"
   ::= {sm24dp4xaFunctionalConf 2 } 
   
sm24dp4xaFunctionalConfContinuityCheckPriority OBJECT-TYPE
   SYNTAX      Integer32
   MAX-ACCESS  read-write
   STATUS      current
   DESCRIPTION
       "range:0-7"
   ::= {sm24dp4xaFunctionalConf 3 } 
   
sm24dp4xaFunctionalConfContinuityCheckFrameRate OBJECT-TYPE
   SYNTAX      Integer32
   MAX-ACCESS  read-write
   STATUS      current
   DESCRIPTION
       "range:1-7
	   1: 300 f/sec
	   2: 100 f/sec
	   3: 10 f/sec
	   4: 1 f/sec
	   5: 6 f/min
	   6: 1 f/min
	   7: 6 f/hour"
   ::= {sm24dp4xaFunctionalConf 4 }    

sm24dp4xaFunctionalConfContinuityCheckTLV OBJECT-TYPE
   SYNTAX      Integer32
   MAX-ACCESS  read-write
   STATUS      current
   DESCRIPTION
       "0:disable
	   1:enable"
   ::= {sm24dp4xaFunctionalConf 5 } 

sm24dp4xaFunctionalConfAPSProtocolEnable OBJECT-TYPE
   SYNTAX      Integer32
   MAX-ACCESS  read-write
   STATUS      current
   DESCRIPTION
       "0:disable
	   1:enable"
   ::= {sm24dp4xaFunctionalConf 6 }   

sm24dp4xaFunctionalConfAPSProtocolPriority OBJECT-TYPE
   SYNTAX      Integer32
   MAX-ACCESS  read-write
   STATUS      current
   DESCRIPTION
       "range:0-7"
   ::= {sm24dp4xaFunctionalConf 7 }   
   
sm24dp4xaFunctionalConfAPSProtocolCast OBJECT-TYPE
   SYNTAX      Integer32
   MAX-ACCESS  read-write
   STATUS      current
   DESCRIPTION
       "0: Unicast destination address
	   1: Multicast destination address"
   ::= {sm24dp4xaFunctionalConf 8 }     

sm24dp4xaFunctionalConfAPSProtocolType OBJECT-TYPE
   SYNTAX      Integer32
   MAX-ACCESS  read-write
   STATUS      current
   DESCRIPTION
       "1: Linear protection APS
	   2: Ring protection APS"
   ::= {sm24dp4xaFunctionalConf 9 }  

sm24dp4xaFunctionalConfAPSProtocolLastOctet OBJECT-TYPE
   SYNTAX      Integer32
   MAX-ACCESS  read-write
   STATUS      current
   DESCRIPTION
       "range:0-255"
   ::= {sm24dp4xaFunctionalConf 10 }    
   
sm24dp4xaTLVConf    OBJECT IDENTIFIER ::= { sm24dp4xaMEP 6 }   

sm24dp4xaTLVConfOUIFirst OBJECT-TYPE
   SYNTAX      Integer32
   MAX-ACCESS  read-write
   STATUS      current
   DESCRIPTION
       "range:0-255"
   ::= {sm24dp4xaTLVConf 2 } 
   
sm24dp4xaTLVConfOUISecond OBJECT-TYPE
   SYNTAX      Integer32
   MAX-ACCESS  read-write
   STATUS      current
   DESCRIPTION
       "range:0-255"
   ::= {sm24dp4xaTLVConf 3 } 
   
sm24dp4xaTLVConfOUIThird OBJECT-TYPE
   SYNTAX      Integer32
   MAX-ACCESS  read-write
   STATUS      current
   DESCRIPTION
       "range:0-255"
   ::= {sm24dp4xaTLVConf 4 } 
   
sm24dp4xaTLVConfSubType OBJECT-TYPE
   SYNTAX      Integer32
   MAX-ACCESS  read-write
   STATUS      current
   DESCRIPTION
       "range:0-255"
   ::= {sm24dp4xaTLVConf 5 }    
   
sm24dp4xaTLVConfValue OBJECT-TYPE
   SYNTAX      Integer32
   MAX-ACCESS  read-write
   STATUS      current
   DESCRIPTION
       "range:0-255"
   ::= {sm24dp4xaTLVConf 6 }  


sm24dp4xaTLVConfStateTable OBJECT-TYPE
   SYNTAX      SEQUENCE OF SM24DP4XATLVConfStateEntry
   MAX-ACCESS  not-accessible
   STATUS      current
   DESCRIPTION
       "TLV Conf State Table"
   ::= { sm24dp4xaMEP 7 }

sm24dp4xaTLVConfStateEntry OBJECT-TYPE
   SYNTAX      SM24DP4XATLVConfStateEntry
   MAX-ACCESS  not-accessible
   STATUS      current
   DESCRIPTION
       "TLV Conf State Entry"
   INDEX    { sm24dp4xaTLVConfStateIndex  }
   ::= { sm24dp4xaTLVConfStateTable 1 }

SM24DP4XATLVConfStateEntry ::= SEQUENCE {
   sm24dp4xaTLVConfStateIndex                                Integer32,
   sm24dp4xaTLVConfStatePeerMEPID                            Integer32,
   sm24dp4xaTLVConfStateCCOrganizationSpecificOUIFirst       Integer32,
   sm24dp4xaTLVConfStateCCOrganizationSpecificOUISecond      Integer32,
   sm24dp4xaTLVConfStateCCOrganizationSpecificOUIThird       Integer32,  
   sm24dp4xaTLVConfStateCCOrganizationSpecificSubType        Integer32,  
   sm24dp4xaTLVConfStateCCOrganizationSpecificValue          Integer32,  
   sm24dp4xaTLVConfStateCCOrganizationSpecificLastRX         DisplayString, 
   sm24dp4xaTLVConfStateCCPortStatusValue                    Integer32,
   sm24dp4xaTLVConfStateCCPortStatusLastRX                   DisplayString, 
   sm24dp4xaTLVConfStateCCInterfaceStatusValue               Integer32,
   sm24dp4xaTLVConfStateCCInterfaceStatusLastRX              DisplayString
}

sm24dp4xaTLVConfStateIndex OBJECT-TYPE
   SYNTAX      Integer32 (1..65535)
   MAX-ACCESS  not-accessible
   STATUS      current
   DESCRIPTION
       "Index"
   ::= { sm24dp4xaTLVConfStateEntry 1 }
   
sm24dp4xaTLVConfStatePeerMEPID OBJECT-TYPE
   SYNTAX      Integer32
   MAX-ACCESS  read-only
   STATUS      current
   DESCRIPTION
       "Peer MEP ID"
   ::= { sm24dp4xaTLVConfStateEntry 2 }   
   
sm24dp4xaTLVConfStateCCOrganizationSpecificOUIFirst OBJECT-TYPE
   SYNTAX      Integer32
   MAX-ACCESS  read-only
   STATUS      current
   DESCRIPTION
       "The last received first value in the OUI field."
   ::= { sm24dp4xaTLVConfStateEntry 3 }      
   
sm24dp4xaTLVConfStateCCOrganizationSpecificOUISecond OBJECT-TYPE
   SYNTAX      Integer32
   MAX-ACCESS  read-only
   STATUS      current
   DESCRIPTION
       "The last received second value in the OS TLV OUI field."
   ::= { sm24dp4xaTLVConfStateEntry 4 }    
   
sm24dp4xaTLVConfStateCCOrganizationSpecificOUIThird OBJECT-TYPE
   SYNTAX      Integer32
   MAX-ACCESS  read-only
   STATUS      current
   DESCRIPTION
       "The last received third value in the OS TLV OUI field."
   ::= { sm24dp4xaTLVConfStateEntry 5 }  
   
sm24dp4xaTLVConfStateCCOrganizationSpecificSubType OBJECT-TYPE
   SYNTAX      Integer32
   MAX-ACCESS  read-only
   STATUS      current
   DESCRIPTION
       "The last received value in the OS TLV Sub-Type field."
   ::= { sm24dp4xaTLVConfStateEntry 6 }   

sm24dp4xaTLVConfStateCCOrganizationSpecificValue OBJECT-TYPE
   SYNTAX      Integer32
   MAX-ACCESS  read-only
   STATUS      current
   DESCRIPTION
       "The last received value in the OS TLV Value field."
   ::= { sm24dp4xaTLVConfStateEntry 7 }  

sm24dp4xaTLVConfStateCCOrganizationSpecificLastRX OBJECT-TYPE
   SYNTAX      DisplayString
   MAX-ACCESS  read-only
   STATUS      current
   DESCRIPTION
       "OS TLV was received in the last received CCM PDU."
   ::= { sm24dp4xaTLVConfStateEntry 8 }  

sm24dp4xaTLVConfStateCCPortStatusValue OBJECT-TYPE
   SYNTAX      Integer32
   MAX-ACCESS  read-only
   STATUS      current
   DESCRIPTION
       "The last received value in the PS TLV Value field."
   ::= { sm24dp4xaTLVConfStateEntry 9 }

sm24dp4xaTLVConfStateCCPortStatusLastRX OBJECT-TYPE
   SYNTAX      DisplayString
   MAX-ACCESS  read-only
   STATUS      current
   DESCRIPTION
       "PS TLV was received in the last received CCM PDU."
   ::= { sm24dp4xaTLVConfStateEntry 10 }  
   
sm24dp4xaTLVConfStateCCInterfaceStatusValue OBJECT-TYPE
   SYNTAX      Integer32
   MAX-ACCESS  read-only
   STATUS      current
   DESCRIPTION
       "The last received value in the IS TLV Value field."
   ::= { sm24dp4xaTLVConfStateEntry 11 }   
   
sm24dp4xaTLVConfStateCCInterfaceStatusLastRX OBJECT-TYPE
   SYNTAX      DisplayString
   MAX-ACCESS  read-only
   STATUS      current
   DESCRIPTION
       "IS TLV was received in the last received CCM PDU."
   ::= { sm24dp4xaTLVConfStateEntry 12 } 

sm24dp4xaLinkStateTracking OBJECT-TYPE
   SYNTAX      Integer32
   MAX-ACCESS  read-write
   STATUS      current
   DESCRIPTION
       "0:disable
	   1:enable"
   ::= { sm24dp4xaMEP 8 } 

   
sm24dp4xaFaultManagement    OBJECT IDENTIFIER ::= { sm24dp4xaMEP 9 }   

sm24dp4xaFaultMgmtLoopBackConfEnable OBJECT-TYPE
   SYNTAX      Integer32
   MAX-ACCESS  read-write
   STATUS      current
   DESCRIPTION
       "0:disable
	   1:enable"
   ::= { sm24dp4xaFaultManagement 2 } 

sm24dp4xaFaultMgmtLoopBackConfDEI OBJECT-TYPE
   SYNTAX      Integer32
   MAX-ACCESS  read-write
   STATUS      current
   DESCRIPTION
       "0:disable
	   1:enable"
   ::= { sm24dp4xaFaultManagement 3 } 
   
sm24dp4xaFaultMgmtLoopBackConfPriority OBJECT-TYPE
   SYNTAX      Integer32
   MAX-ACCESS  read-write
   STATUS      current
   DESCRIPTION
       "range:0-7"
   ::= { sm24dp4xaFaultManagement 4 } 
 
sm24dp4xaFaultMgmtLoopBackConfCast OBJECT-TYPE
   SYNTAX      Integer32
   MAX-ACCESS  read-write
   STATUS      current
   DESCRIPTION
       "0:Unicast destination address
	   1:Multicast destination address"
   ::= { sm24dp4xaFaultManagement 5 }  
 
sm24dp4xaFaultMgmtLoopBackConfPeerMEP OBJECT-TYPE
   SYNTAX      Integer32
   MAX-ACCESS  read-write
   STATUS      current
   DESCRIPTION
       "This is only used if the 'Unicast MAC' is configured to all zero. 
	   The LBM unicast MAC will be taken from the 'Unicast Peer MAC' configuration of this peer."
   ::= { sm24dp4xaFaultManagement 6 }  
 
sm24dp4xaFaultMgmtLoopBackConfUnicastMAC OBJECT-TYPE
   SYNTAX      DisplayString
   MAX-ACCESS  read-write
   STATUS      current
   DESCRIPTION
       "This is only used if NOT configured to all zero. 
	   This will be used as the LBM PDU unicast MAC. 
	   This is the only way to configure Loop Back to-wards a MIP. "
   ::= { sm24dp4xaFaultManagement 7 }  
   
sm24dp4xaFaultMgmtLoopBackConfToSend OBJECT-TYPE
   SYNTAX      Integer32
   MAX-ACCESS  read-write
   STATUS      current
   DESCRIPTION
       "The number of LBM PDU to send in one loop test. 
	   The value 0 indicate infinite transmission (test behaviour). 
	   This is HW based LBM/LBR and Requires VOE."
   ::= { sm24dp4xaFaultManagement 8 } 
   
sm24dp4xaFaultMgmtLoopBackConfSize OBJECT-TYPE
   SYNTAX      Integer32
   MAX-ACCESS  read-write
   STATUS      current
   DESCRIPTION
       "The LBM frame size."
   ::= { sm24dp4xaFaultManagement 9 } 
   
sm24dp4xaFaultMgmtLoopBackConfInterval OBJECT-TYPE
   SYNTAX      Integer32
   MAX-ACCESS  read-write
   STATUS      current
   DESCRIPTION
       "The interval between transmitting LBM PDU."
   ::= { sm24dp4xaFaultManagement 10 } 
   
   
sm24dp4xaFaultManagementState    OBJECT IDENTIFIER ::= { sm24dp4xaMEP 10 }  
   
   
sm24dp4xaFaultMgmtStateTransactionID OBJECT-TYPE
   SYNTAX      Integer32
   MAX-ACCESS  read-only
   STATUS      current
   DESCRIPTION
       "The transaction id of the first LBM transmitted. 
	   For each LBM transmitted the transaction id in the PDU is incremented."
   ::= { sm24dp4xaFaultManagementState 1 } 
   

sm24dp4xaFaultMgmtStateTransmitted OBJECT-TYPE
   SYNTAX      Integer32
   MAX-ACCESS  read-only
   STATUS      current
   DESCRIPTION
       "The total number of LBM PDU transmitted."
   ::= { sm24dp4xaFaultManagementState 2 } 
   
   
sm24dp4xaFaultMgmtStateTable OBJECT-TYPE
   SYNTAX      SEQUENCE OF SM24DP4XAFaultMgmtStateEntry
   MAX-ACCESS  not-accessible
   STATUS      current
   DESCRIPTION
       " "
   ::= { sm24dp4xaFaultManagementState 3 }

sm24dp4xaFaultMgmtStateEntry OBJECT-TYPE
   SYNTAX      SM24DP4XAFaultMgmtStateEntry
   MAX-ACCESS  not-accessible
   STATUS      current
   DESCRIPTION
       " "
   INDEX    { sm24dp4xaFaultMgmtStateIndex  }
   ::= { sm24dp4xaFaultMgmtStateTable 1 }

SM24DP4XAFaultMgmtStateEntry ::= SEQUENCE {
   sm24dp4xaFaultMgmtStateIndex               Integer32,
   sm24dp4xaFaultMgmtStateReplyMAC            DisplayString,
   sm24dp4xaFaultMgmtStateReceived            Integer32,
   sm24dp4xaFaultMgmtStateOutOfOrder          Integer32
}

sm24dp4xaFaultMgmtStateIndex OBJECT-TYPE
   SYNTAX      Integer32 (1..65535)
   MAX-ACCESS  not-accessible
   STATUS      current
   DESCRIPTION
       "Index"
   ::= { sm24dp4xaFaultMgmtStateEntry 1 }

sm24dp4xaFaultMgmtStateReplyMAC OBJECT-TYPE
   SYNTAX      DisplayString
   MAX-ACCESS  read-only
   STATUS      current
   DESCRIPTION
       "The MAC of the replying MEP/MIP. 
	   In case of multi-cast LBM, replies can be received from all peer MEP in the group. 
	   This MAC is not shown in case of 'To Send' == 0."
   ::= { sm24dp4xaFaultMgmtStateEntry 2 }

sm24dp4xaFaultMgmtStateReceived OBJECT-TYPE
   SYNTAX      Integer32
   MAX-ACCESS  read-only
   STATUS      current
   DESCRIPTION
       "The total number of LBR PDU received from this 'Reply MAC'."
   ::= { sm24dp4xaFaultMgmtStateEntry 3 }   
   
sm24dp4xaFaultMgmtStateOutOfOrder OBJECT-TYPE
   SYNTAX      Integer32
   MAX-ACCESS  read-only
   STATUS      current
   DESCRIPTION
       "The number of LBR PDU received from this 'Reply MAC' with incorrect 'Transaction ID'."
   ::= { sm24dp4xaFaultMgmtStateEntry 4 }  
   
sm24dp4xaFaultMgmtTestSignal    OBJECT IDENTIFIER ::= { sm24dp4xaMEP 11 }  

sm24dp4xaFaultMgmtTestSignalTx OBJECT-TYPE
   SYNTAX      Integer32
   MAX-ACCESS  read-write
   STATUS      current
   DESCRIPTION
       "Test Signal based on transmitting TST PDU can be enabled/disabled.
	   0:disable
	   1:enable"
   ::= { sm24dp4xaFaultMgmtTestSignal 2 }  
   
sm24dp4xaFaultMgmtTestSignalRx OBJECT-TYPE
   SYNTAX      Integer32
   MAX-ACCESS  read-write
   STATUS      current
   DESCRIPTION
       "Test Signal based on transmitting TST PDU can be enabled/disabled.
	   0:disable
	   1:enable"
   ::= { sm24dp4xaFaultMgmtTestSignal 3 }  
   
sm24dp4xaFaultMgmtTestSignalDEI OBJECT-TYPE
   SYNTAX      Integer32
   MAX-ACCESS  read-write
   STATUS      current
   DESCRIPTION
       "The DEI to be inserted as PCP bits in TAG (if any).
	   0:disable
	   1:enable"
   ::= { sm24dp4xaFaultMgmtTestSignal 4 }  

sm24dp4xaFaultMgmtTestSignalPriority OBJECT-TYPE
   SYNTAX      Integer32
   MAX-ACCESS  read-write
   STATUS      current
   DESCRIPTION
       "The priority to be inserted as PCP bits in TAG (if any).
       Range:0-7"
   ::= { sm24dp4xaFaultMgmtTestSignal 5 }    
   
sm24dp4xaFaultMgmtTestSignalPeerMEP OBJECT-TYPE
   SYNTAX      Integer32
   MAX-ACCESS  read-write
   STATUS      current
   DESCRIPTION
       "The TST frame destination MAC will be taken from the 'Unicast Peer MAC' configuration of this peer."
   ::= { sm24dp4xaFaultMgmtTestSignal 6 }    
   
sm24dp4xaFaultMgmtTestSignalRate OBJECT-TYPE
   SYNTAX      Integer32
   MAX-ACCESS  read-write
   STATUS      current
   DESCRIPTION
       "The TST frame transmission bit rate - in Mega bits pr. second. 
	   Limit is 400 Mbps. This is the bit rate of a standard frame without any encapsulation. 
	   If 1 Mbps rate is selected in a EVC MEP, the added tag will give a higher bitrate on the wire."
   ::= { sm24dp4xaFaultMgmtTestSignal 7 }  
   
sm24dp4xaFaultMgmtTestSignalSize OBJECT-TYPE
   SYNTAX      Integer32
   MAX-ACCESS  read-write
   STATUS      current
   DESCRIPTION
       "The TST frame size. This is entered as the wanted size (in bytes) of a un-tagged frame containing TST OAM PDU - including CRC (four bytes)."
   ::= { sm24dp4xaFaultMgmtTestSignal 8 }  
   
sm24dp4xaFaultMgmtTestSignalPattern OBJECT-TYPE
   SYNTAX      Integer32
   MAX-ACCESS  read-write
   STATUS      current
   DESCRIPTION
       "The 'empty' TST PDU has the size of 12 bytes. 
	   In order to achieve the configured frame size a data TLV will be added with a pattern.
	   0:All Zero
	   1:All One
	   2:10101010"
   ::= { sm24dp4xaFaultMgmtTestSignal 9 }  
   
sm24dp4xaFaultMgmtTestSignalSequenceNumber OBJECT-TYPE
   SYNTAX      Integer32
   MAX-ACCESS  read-write
   STATUS      current
   DESCRIPTION
       "0:disable
	   1:enable"
   ::= { sm24dp4xaFaultMgmtTestSignal 10 }  
   
sm24dp4xaFaultMgmtTestSignalState    OBJECT IDENTIFIER ::= { sm24dp4xaMEP 12 }  
   
sm24dp4xaFaultMgmtTestSignalStateTXFrameCount OBJECT-TYPE
   SYNTAX      Integer32
   MAX-ACCESS  read-only
   STATUS      current
   DESCRIPTION
       "The number of transmitted TST frames since last 'Clear'."
   ::= { sm24dp4xaFaultMgmtTestSignalState 2 }  
   
sm24dp4xaFaultMgmtTestSignalStateRXFrameCount OBJECT-TYPE
   SYNTAX      Integer32
   MAX-ACCESS  read-only
   STATUS      current
   DESCRIPTION
       "The number of received TST frames since last 'Clear'."
   ::= { sm24dp4xaFaultMgmtTestSignalState 3 }  
   
sm24dp4xaFaultMgmtTestSignalStateRXRate OBJECT-TYPE
   SYNTAX      Integer32
   MAX-ACCESS  read-only
   STATUS      current
   DESCRIPTION
       "The current received TST frame bit rate in Kbps. 
	   This is calculated on a 1 s. basis, starting when first TST frame is received after 'Clear'. 
	   The frame size used for this calculation is the first received after 'Clear'"
   ::= { sm24dp4xaFaultMgmtTestSignalState 4 }  
   
sm24dp4xaFaultMgmtTestSignalStateTestTime OBJECT-TYPE
   SYNTAX      Integer32
   MAX-ACCESS  read-only
   STATUS      current
   DESCRIPTION
       "The number of seconds passed since first TST frame received after last 'Clear'."
   ::= { sm24dp4xaFaultMgmtTestSignalState 5 }  
   
   
sm24dp4xaFaultMgmtTestSignalStateClear OBJECT-TYPE
   SYNTAX      Integer32
   MAX-ACCESS  read-write
   STATUS      current
   DESCRIPTION
       "This will clear all Test Signal State. 
	   Transmission of TST frame will be restarted. 
	   Calculation of 'Rx frame count', 'RX rate' and 'Test time' will be started when receiving first TST frame."
   ::= { sm24dp4xaFaultMgmtTestSignalState 6 }     
   
   
sm24dp4xaFaultMgmtClientConfigFlow    OBJECT IDENTIFIER ::= { sm24dp4xaMEP 13 }  

sm24dp4xaFaultMgmtClientConfigFlowTable OBJECT-TYPE
   SYNTAX      SEQUENCE OF SM24DP4XAFaultMgmtClientConfigFlowEntry
   MAX-ACCESS  not-accessible
   STATUS      current
   DESCRIPTION
       " "
   ::= { sm24dp4xaFaultMgmtClientConfigFlow 1 }

sm24dp4xaFaultMgmtClientConfigFlowEntry OBJECT-TYPE
   SYNTAX      SM24DP4XAFaultMgmtClientConfigFlowEntry
   MAX-ACCESS  not-accessible
   STATUS      current
   DESCRIPTION
       " "
   INDEX    { sm24dp4xaFaultMgmtClientConfigFlowIndex  }
   ::= { sm24dp4xaFaultMgmtClientConfigFlowTable 1 }

SM24DP4XAFaultMgmtClientConfigFlowEntry ::= SEQUENCE {
   sm24dp4xaFaultMgmtClientConfigFlowIndex     Integer32,
   sm24dp4xaFaultMgmtClientConfigFlowDomain    Integer32,
   sm24dp4xaFaultMgmtClientConfigFlowInstance  Integer32,
   sm24dp4xaFaultMgmtClientConfigFlowLevel     Integer32,
   sm24dp4xaFaultMgmtClientConfigFlowAISprio   Integer32,
   sm24dp4xaFaultMgmtClientConfigFlowLCKprio   Integer32,
   sm24dp4xaFaultMgmtClientConfigFlowRowStatus RowStatus
}

sm24dp4xaFaultMgmtClientConfigFlowIndex OBJECT-TYPE
   SYNTAX      Integer32 (1..65535)
   MAX-ACCESS  not-accessible
   STATUS      current
   DESCRIPTION
       "Index"
   ::= { sm24dp4xaFaultMgmtClientConfigFlowEntry 1 }

sm24dp4xaFaultMgmtClientConfigFlowDomain OBJECT-TYPE
   SYNTAX      Integer32
   MAX-ACCESS  read-create
   STATUS      current
   DESCRIPTION
       "The domain of the client layer flow.
	   Ranfew:0-6
	   0:Port
	   1:EVC
	   2:VLAN
	   3:MPLS_LINK
	   4:MPLS_TUNNEL
	   5:MPLS_PW
	   6:MPLS_LSP"
   ::= { sm24dp4xaFaultMgmtClientConfigFlowEntry 2 }  

sm24dp4xaFaultMgmtClientConfigFlowInstance OBJECT-TYPE
   SYNTAX      Integer32
   MAX-ACCESS  read-create
   STATUS      current
   DESCRIPTION
       "Client layer flow instance numbers."
   ::= { sm24dp4xaFaultMgmtClientConfigFlowEntry 3 }  
   
sm24dp4xaFaultMgmtClientConfigFlowLevel OBJECT-TYPE
   SYNTAX      Integer32
   MAX-ACCESS  read-create
   STATUS      current
   DESCRIPTION
       "Client layer level - AIS and LCK PDU transmitted in this client layer flow will be on this level."
   ::= { sm24dp4xaFaultMgmtClientConfigFlowEntry 4 }  
   
sm24dp4xaFaultMgmtClientConfigFlowAISprio OBJECT-TYPE
   SYNTAX      Integer32
   MAX-ACCESS  read-create
   STATUS      current
   DESCRIPTION
       "The priority to be used when transmitting AIS in each client flow. 
	   Priority resulting in highest possible PCP can be selected.
	   Range:0-7. 255 indicate highest possible is requested"
   ::= { sm24dp4xaFaultMgmtClientConfigFlowEntry 5 }  
   
sm24dp4xaFaultMgmtClientConfigFlowLCKprio OBJECT-TYPE
   SYNTAX      Integer32
   MAX-ACCESS  read-create
   STATUS      current
   DESCRIPTION
       "The priority to be used when transmitting LCK in each client flow. 
	   Priority resulting in highest possible PCP can be selected.
	   Range:0-7. 255 indicate highest possible is requested"
   ::= { sm24dp4xaFaultMgmtClientConfigFlowEntry 6 }  
   
sm24dp4xaFaultMgmtClientConfigFlowRowStatus OBJECT-TYPE
   SYNTAX      RowStatus
   MAX-ACCESS  read-create
   STATUS      current
   DESCRIPTION
       "FaultMgmtClientConfigFlow Row Status."
   ::= {sm24dp4xaFaultMgmtClientConfigFlowEntry 7 }
   
   
sm24dp4xaFaultMgmtAISLOCK    OBJECT IDENTIFIER ::= { sm24dp4xaMEP 14 }  
   
sm24dp4xaFaultMgmtAISEnable OBJECT-TYPE
   SYNTAX      Integer32
   MAX-ACCESS  read-write
   STATUS      current
   DESCRIPTION
       "Insertion of AIS signal (AIS PDU transmission) in client layer flows, can be enable/disabled.
	   0:disable
	   1:enable"
   ::= { sm24dp4xaFaultMgmtAISLOCK 2 }  
   
sm24dp4xaFaultMgmtAISFrameRate OBJECT-TYPE
   SYNTAX      Integer32
   MAX-ACCESS  read-write
   STATUS      current
   DESCRIPTION
       "Selecting the frame rate of AIS PDU. 
	   This is the inverse of transmission period as described in Y.1731.
       1: 300 frames per second
	   2: 100 frames per second
	   3: 10 frames per second
	   4: 1 frames per second
	   5: 6 frames per minute
	   6: 1 frames per minute
	   7: 6 frames per hour"
   ::= { sm24dp4xaFaultMgmtAISLOCK 3 }  
   
sm24dp4xaFaultMgmtAISProtection OBJECT-TYPE
   SYNTAX      Integer32
   MAX-ACCESS  read-write
   STATUS      current
   DESCRIPTION
       "Selecting this means that the first 3 AIS PDU is transmitted as fast as possible - in case of using this for protection in the end point.
	   0:disable
	   1:enable"
   ::= { sm24dp4xaFaultMgmtAISLOCK 4 }     
   
   
sm24dp4xaFaultMgmtLOCKEnable OBJECT-TYPE
   SYNTAX      Integer32
   MAX-ACCESS  read-write
   STATUS      current
   DESCRIPTION
       "Insertion of LOCK signal (LCK PDU transmission) in client layer flows, can be enable/disabled.
	   0:disable
	   1:enable"
   ::= { sm24dp4xaFaultMgmtAISLOCK 5 }   
   
sm24dp4xaFaultMgmtLOCKFrameRate OBJECT-TYPE
   SYNTAX      Integer32
   MAX-ACCESS  read-write
   STATUS      current
   DESCRIPTION
       "Selecting the frame rate of LCK PDU. This is the inverse of transmission period as described in Y.1731.
       1: 300 frames per second
	   2: 100 frames per second
	   3: 10 frames per second
	   4: 1 frames per second
	   5: 6 frames per minute
	   6: 1 frames per minute
	   7: 6 frames per hour"
   ::= { sm24dp4xaFaultMgmtAISLOCK 6 }  

sm24dp4xaPerformanceMonitor  OBJECT IDENTIFIER ::= { sm24dp4xaMEP 15 }  

sm24dp4xaDataSetEnable OBJECT-TYPE
   SYNTAX      Integer32
   MAX-ACCESS  read-write
   STATUS      current
   DESCRIPTION
       "
	   When enabled this MEP instance will contribute to the 'PM Data Set' gathered by the PM Session.
	   0:disable
	   1:enable"
   ::= { sm24dp4xaPerformanceMonitor 2 }   
   
sm24dp4xaLossMeasureEnable OBJECT-TYPE
   SYNTAX      Integer32
   MAX-ACCESS  read-write
   STATUS      current
   DESCRIPTION
       "
	   Loss Measurement based on transmitting/receiving CCM or LMM/LMR PDU can be enabled/disabled - see 'Ended'. 
	   This is only valid with one Peer MEP configured.
	   0:disable
	   1:enable"
   ::= { sm24dp4xaPerformanceMonitor 3 }     
   
sm24dp4xaLossMeasurePriority OBJECT-TYPE
   SYNTAX      Integer32
   MAX-ACCESS  read-write
   STATUS      current
   DESCRIPTION
       "
	   The priority to be inserted as PCP bits in TAG (if any). 
	   In case of enable of Continuity Check and Loss Measurement both implemented on SW based CCM, 'Priority' has to be the same.
	   range:0-7"
   ::= { sm24dp4xaPerformanceMonitor 4 } 
   
sm24dp4xaLossMeasureFrameRate OBJECT-TYPE
   SYNTAX      Integer32
   MAX-ACCESS  read-write
   STATUS      current
   DESCRIPTION
       "
	   1: 300 frames per second
	   2: 100 frames per second
	   3: 10 frames per second
	   4: 1 frames per second
	   5: 6 frames per minute
	   6: 1 frames per minute
	   7: 6 frames per hour"
   ::= { sm24dp4xaPerformanceMonitor 5 }   
   
sm24dp4xaLossMeasureCast OBJECT-TYPE
   SYNTAX      Integer32
   MAX-ACCESS  read-write
   STATUS      current
   DESCRIPTION
       "
	   0: Unicast destination address
	   1: Multicast destination address 
	   "
   ::= { sm24dp4xaPerformanceMonitor 6 }  
   
sm24dp4xaLossMeasureEnded OBJECT-TYPE
   SYNTAX      Integer32
   MAX-ACCESS  read-write
   STATUS      current
   DESCRIPTION
       "
	   0: Single ended LM based on LMM/LMR or DM based on DMM/DMR 
	   1: Dual ended LM based on CCM or DM based on 1DM
	   "
   ::= { sm24dp4xaPerformanceMonitor 7 }  
   
sm24dp4xaLossMeasureFLRInterv OBJECT-TYPE
   SYNTAX      Integer32
   MAX-ACCESS  read-write
   STATUS      current
   DESCRIPTION
       "
       This is the interval in seconds where the Frame Loss Ratio is calculated.
	   "
   ::= { sm24dp4xaPerformanceMonitor 8 }  
   
sm24dp4xaLossMeasureLossThreshold OBJECT-TYPE
   SYNTAX      Integer32
   MAX-ACCESS  read-write
   STATUS      current
   DESCRIPTION
       "
       Far end loss threshold count is incremented if a loss measurement is above this threshold.
	   "
   ::= { sm24dp4xaPerformanceMonitor 9 }   
    
sm24dp4xaLossMeasureStateTx OBJECT-TYPE
   SYNTAX      Integer32
   MAX-ACCESS  read-only
   STATUS      current
   DESCRIPTION
       "
	   "
   ::= { sm24dp4xaPerformanceMonitor 10 }     
    
sm24dp4xaLossMeasureStateRx OBJECT-TYPE
   SYNTAX      Integer32
   MAX-ACCESS  read-only
   STATUS      current
   DESCRIPTION
       "
	   "
   ::= { sm24dp4xaPerformanceMonitor 11 }
   
sm24dp4xaLossMeasureStateNearEndLossCnt OBJECT-TYPE
   SYNTAX      Integer32
   MAX-ACCESS  read-only
   STATUS      current
   DESCRIPTION
       "The accumulated near end frame loss count - since last 'clear'.
	   "
   ::= { sm24dp4xaPerformanceMonitor 12 }
   
sm24dp4xaLossMeasureStateFarEndLossCnt OBJECT-TYPE
   SYNTAX      Integer32
   MAX-ACCESS  read-only
   STATUS      current
   DESCRIPTION
       "The accumulated far end frame loss count - since last 'clear'.
	   "
   ::= { sm24dp4xaPerformanceMonitor 13 }
   
sm24dp4xaLossMeasureStateNearEndLossRatio OBJECT-TYPE
   SYNTAX      Integer32
   MAX-ACCESS  read-only
   STATUS      current
   DESCRIPTION
       "The near end frame loss ratio calculated based on the near end frame loss count and far end frame transmitted - in the latest 'FLR Interval'. 
	   The result is given in percent.
	   "
   ::= { sm24dp4xaPerformanceMonitor 14 }
   
sm24dp4xaLossMeasureStateFarEndLossRatio OBJECT-TYPE
   SYNTAX      Integer32
   MAX-ACCESS  read-only
   STATUS      current
   DESCRIPTION
       "The far end frame loss ratio calculated based on the far end frame loss count and near end frame transmitted - in the latest 'FLR Interval'. 
	   The result is given in percent.
	   "
   ::= { sm24dp4xaPerformanceMonitor 15 }
   
sm24dp4xaLossMeasureStateClear OBJECT-TYPE
   SYNTAX      Integer32
   MAX-ACCESS  read-write
   STATUS      current
   DESCRIPTION
       "Set of this check and save will clear the accumulated counters and restart ratio calculation.
	   "
   ::= { sm24dp4xaPerformanceMonitor 16 }
   
sm24dp4xaLossMeasureAvailEnable OBJECT-TYPE
   SYNTAX      Integer32
   MAX-ACCESS  read-write
   STATUS      current
   DESCRIPTION
       "Enable/disable of loss measurement availability.
	   0:disable
	   1:enable	   
	   "
   ::= { sm24dp4xaPerformanceMonitor 17 }
   
sm24dp4xaLossMeasureAvailInterv OBJECT-TYPE
   SYNTAX      Integer32
   MAX-ACCESS  read-write
   STATUS      current
   DESCRIPTION
       "Availability interval - number of measurements with same availability in order to change availability state.
	   
	   "
   ::= { sm24dp4xaPerformanceMonitor 18 }
   
sm24dp4xaLossMeasureAvailFLRThreshold OBJECT-TYPE
   SYNTAX      Integer32
   MAX-ACCESS  read-write
   STATUS      current
   DESCRIPTION
       "Availability frame loss ratio threshold in per mille.
	   "
   ::= { sm24dp4xaPerformanceMonitor 19 }
   
sm24dp4xaLossMeasureAvailMaintenance OBJECT-TYPE
   SYNTAX      Integer32
   MAX-ACCESS  read-write
   STATUS      current
   DESCRIPTION
       "Enable/disable of loss measurement availability maintenance.
	   "
   ::= { sm24dp4xaPerformanceMonitor 20 }  
   
   
sm24dp4xaLossMeasureAvailStateNearAvailCnt OBJECT-TYPE
   SYNTAX      Integer32
   MAX-ACCESS  read-only
   STATUS      current
   DESCRIPTION
       "Near end availability count.
	   "
   ::= { sm24dp4xaPerformanceMonitor 21 }     
   
sm24dp4xaLossMeasureAvailStateFarAvailCnt OBJECT-TYPE
   SYNTAX      Integer32
   MAX-ACCESS  read-only
   STATUS      current
   DESCRIPTION
       "Far end availability count.
	   "
   ::= { sm24dp4xaPerformanceMonitor 22 }  
   
sm24dp4xaLossMeasureAvailStateNearUnavailCnt OBJECT-TYPE
   SYNTAX      Integer32
   MAX-ACCESS  read-only
   STATUS      current
   DESCRIPTION
       "Near end unavailability count.
	   "
   ::= { sm24dp4xaPerformanceMonitor 23 }  
   
sm24dp4xaLossMeasureAvailStateFarUnavailCnt OBJECT-TYPE
   SYNTAX      Integer32
   MAX-ACCESS  read-only
   STATUS      current
   DESCRIPTION
       "Far end unavailability count.
	   "
   ::= { sm24dp4xaPerformanceMonitor 24 }  
   
sm24dp4xaLossMeasureAvailStateNearState OBJECT-TYPE
   SYNTAX      Integer32
   MAX-ACCESS  read-only
   STATUS      current
   DESCRIPTION
       "Near end availability state.
	   "
   ::= { sm24dp4xaPerformanceMonitor 25 }  
   
sm24dp4xaLossMeasureAvailStateFarState OBJECT-TYPE
   SYNTAX      Integer32
   MAX-ACCESS  read-only
   STATUS      current
   DESCRIPTION
       "Far end availability state.
	   "
   ::= { sm24dp4xaPerformanceMonitor 26 }  
   
sm24dp4xaLossMeasureHighLossIntervEnable OBJECT-TYPE
   SYNTAX      Integer32
   MAX-ACCESS  read-write
   STATUS      current
   DESCRIPTION
       "Enable/disable of loss measurement high loss interval.
	   0:disable
	   1:enable	 
	   "
   ::= { sm24dp4xaPerformanceMonitor 27 }  
   
sm24dp4xaLossMeasureHighLossIntervFLRThreshold OBJECT-TYPE
   SYNTAX      Integer32
   MAX-ACCESS  read-write
   STATUS      current
   DESCRIPTION
       "High Loss Interval frame loss ratio threshold in per mille.
	   "
   ::= { sm24dp4xaPerformanceMonitor 28 }  
   
sm24dp4xaLossMeasureHighLossIntervConsecInterv OBJECT-TYPE
   SYNTAX      Integer32
   MAX-ACCESS  read-write
   STATUS      current
   DESCRIPTION
       "High Loss Interval consecutive interval (number of measurements).
	   "
   ::= { sm24dp4xaPerformanceMonitor 29 }   
   
sm24dp4xaLossMeasureHighLossIntervStateNearCnt OBJECT-TYPE
   SYNTAX      Integer32
   MAX-ACCESS  read-only
   STATUS      current
   DESCRIPTION
       "Near end high loss interval count (number of measurements where availability state is available and FLR is above high loss interval FLR threshold.
	   "
   ::= { sm24dp4xaPerformanceMonitor 30 }   
   
sm24dp4xaLossMeasureHighLossIntervStateFarCnt OBJECT-TYPE
   SYNTAX      Integer32
   MAX-ACCESS  read-only
   STATUS      current
   DESCRIPTION
       "Far end high loss interval count (number of measurements where availability state is available and FLR is above high loss interval FLR threshold.
	   "
   ::= { sm24dp4xaPerformanceMonitor 31 }  
   
sm24dp4xaLossMeasureHighLossIntervStateNearConsecCnt OBJECT-TYPE
   SYNTAX      Integer32
   MAX-ACCESS  read-only
   STATUS      current
   DESCRIPTION
       "Near end high loss interval consecutive count.
	   "
   ::= { sm24dp4xaPerformanceMonitor 32 }  
   
sm24dp4xaLossMeasureHighLossIntervStateFarConsecCnt OBJECT-TYPE
   SYNTAX      Integer32
   MAX-ACCESS  read-only
   STATUS      current
   DESCRIPTION
       "Far end high loss interval consecutive count.
	   "
   ::= { sm24dp4xaPerformanceMonitor 33 } 
   
sm24dp4xaLossMeasureSignalDegradeEnable OBJECT-TYPE
   SYNTAX      Integer32
   MAX-ACCESS  read-write
   STATUS      current
   DESCRIPTION
       "Enable/disable of loss measurement signal degrade.
	   0:disable
	   1:enable	 	   
	   "
   ::= { sm24dp4xaPerformanceMonitor 34 } 
   
sm24dp4xaLossMeasureSignalDegradeTXMinimum OBJECT-TYPE
   SYNTAX      Integer32
   MAX-ACCESS  read-write
   STATUS      current
   DESCRIPTION
       "Minimum number of frames that must be transmitted in a measurement before frame loss ratio is tested against loss ratio threshold.
 	   
	   "
   ::= { sm24dp4xaPerformanceMonitor 35 } 
   
sm24dp4xaLossMeasureSignalDegradeFLRThreshold OBJECT-TYPE
   SYNTAX      Integer32
   MAX-ACCESS  read-write
   STATUS      current
   DESCRIPTION
       "Signal Degraded frame loss ratio threshold in per mille.
	   "
   ::= { sm24dp4xaPerformanceMonitor 36 } 
   
sm24dp4xaLossMeasureSignalDegradeBadThreshold OBJECT-TYPE
   SYNTAX      Integer32
   MAX-ACCESS  read-write
   STATUS      current
   DESCRIPTION
       "Number of consecutive bad interval measurements required to set degrade state.
	   "
   ::= { sm24dp4xaPerformanceMonitor 37 }    
   
sm24dp4xaLossMeasureSignalDegradeGoodThreshold OBJECT-TYPE
   SYNTAX      Integer32
   MAX-ACCESS  read-write
   STATUS      current
   DESCRIPTION
       "Number of consecutive good interval measurements required to clear degrade state.
	   "
   ::= { sm24dp4xaPerformanceMonitor 38 } 
   
sm24dp4xaDelayMeasureEnable OBJECT-TYPE
   SYNTAX      Integer32
   MAX-ACCESS  read-write
   STATUS      current
   DESCRIPTION
       "Delay Measurement based on transmitting 1DM/DMM PDU can be enabled/disabled. 
	   Delay Measurement based on receiving and handling 1DM/DMR PDU is always enabled.
	   0:disable
	   1:enable		   
	   "
   ::= { sm24dp4xaPerformanceMonitor 39 } 
   
sm24dp4xaDelayMeasurePriority OBJECT-TYPE
   SYNTAX      Integer32
   MAX-ACCESS  read-write
   STATUS      current
   DESCRIPTION
       "The priority to be inserted as PCP bits in TAG (if any).
       Range:0-7	   
	   "
   ::= { sm24dp4xaPerformanceMonitor 40 }  
   
sm24dp4xaDelayMeasureCast OBJECT-TYPE
   SYNTAX      Integer32
   MAX-ACCESS  read-write
   STATUS      current
   DESCRIPTION
       "Selection of 1DM/DMM PDU transmitted unicast or multicast. 
	   The unicast MAC will be configured through 'Peer MEP'.   
	   0: Unicast destination address
	   1: Multicast destination address 	   
	   "
   ::= { sm24dp4xaPerformanceMonitor 41 } 
   
sm24dp4xaDelayMeasurePeerMEP OBJECT-TYPE
   SYNTAX      Integer32
   MAX-ACCESS  read-write
   STATUS      current
   DESCRIPTION
       "This is only used if the 'Cast' is configured to Uni. 
	   The 1DM/DMR unicast MAC will be taken from the 'Unicast Peer MAC' configuration of this peer. 
	   "
   ::= { sm24dp4xaPerformanceMonitor 42 } 
   
sm24dp4xaDelayMeasureEnded OBJECT-TYPE
   SYNTAX      Integer32
   MAX-ACCESS  read-write
   STATUS      current
   DESCRIPTION
       "0:One-Way: One-Way Delay Measurement implemented on 1DM.
        1:Two-Way: Two-Way Delay Measurement implemented on DMM/DMR.
	   "
   ::= { sm24dp4xaPerformanceMonitor 43 } 
   
sm24dp4xaDelayMeasureTxMode OBJECT-TYPE
   SYNTAX      Integer32
   MAX-ACCESS  read-write
   STATUS      current
   DESCRIPTION
       "0:Standardize: Y.1731 standardize way to transmit 1DM/DMR.
        1:Proprietary: Vitesse proprietary way with follow-up packets to transmit 1DM/DMR.
	   "
   ::= { sm24dp4xaPerformanceMonitor 44 } 
   
sm24dp4xaDelayMeasureCalc OBJECT-TYPE
   SYNTAX      Integer32
   MAX-ACCESS  read-write
   STATUS      current
   DESCRIPTION
       "This is only used if the 'Way' is configured to Two-way.
        0:Round trip: The frame delay calculated by the transmitting and receiving timestamps of initiators. 
		    Frame Delay = RxTimeb-TxTimeStampf
        1:Flow: The frame delay calculated by the transmitting and receiving timestamps of initiators and remotes. 
		    Frame Delay = (RxTimeb-TxTimeStampf)-(TxTimeStampb-RxTimeStampf)
	   "
   ::= { sm24dp4xaPerformanceMonitor 45 } 
   
sm24dp4xaDelayMeasureGap OBJECT-TYPE
   SYNTAX      Integer32
   MAX-ACCESS  read-write
   STATUS      current
   DESCRIPTION
       "The gap between transmitting 1DM/DMM PDU in 10ms. The range is 10 to 65535.
	   "
   ::= { sm24dp4xaPerformanceMonitor 46 } 

sm24dp4xaDelayMeasureCnt OBJECT-TYPE
   SYNTAX      Integer32
   MAX-ACCESS  read-write
   STATUS      current
   DESCRIPTION
       "The number of last records to calculate. The range is 10 to 2000.
	   "
   ::= { sm24dp4xaPerformanceMonitor 47 } 
   
sm24dp4xaDelayMeasureUnit OBJECT-TYPE
   SYNTAX      Integer32
   MAX-ACCESS  read-write
   STATUS      current
   DESCRIPTION
       "The time resolution.
	   0:us
	   1:ns
	   "
   ::= { sm24dp4xaPerformanceMonitor 48 }  
   
sm24dp4xaDelayMeasureD2forD1 OBJECT-TYPE
   SYNTAX      Integer32
   MAX-ACCESS  read-write
   STATUS      current
   DESCRIPTION
       "Enable to use DMM/DMR packet to calculate one-way DM.
	   0:disable
	   1:enable	
	   "
   ::= { sm24dp4xaPerformanceMonitor 49 }  
   
sm24dp4xaDelayMeasureCounterOverflowAction OBJECT-TYPE
   SYNTAX      Integer32
   MAX-ACCESS  read-write
   STATUS      current
   DESCRIPTION
       "The action to counter when overflow happens.
	   0: Keep:When internal total delay counter overflow, DM is disabled automatically
	   1: Reset:When internal total delay counter overflow, counter is reset and DM continues running
	   "
   ::= { sm24dp4xaPerformanceMonitor 50 }  
   
sm24dp4xaDelayMeasureStateOnewayTx OBJECT-TYPE
   SYNTAX      DisplayString
   MAX-ACCESS  read-only
   STATUS      current
   DESCRIPTION
       "The accumulated transmit count - since last 'clear'.
	   "
   ::= { sm24dp4xaPerformanceMonitor 51 } 
   
sm24dp4xaDelayMeasureStateOnewayRx OBJECT-TYPE
   SYNTAX      DisplayString
   MAX-ACCESS  read-only
   STATUS      current
   DESCRIPTION
       "The accumulated receive count - since last 'clear'.
	   "
   ::= { sm24dp4xaPerformanceMonitor 52 } 
   
sm24dp4xaDelayMeasureStateOnewayRxTimeout OBJECT-TYPE
   SYNTAX      DisplayString
   MAX-ACCESS  read-only
   STATUS      current
   DESCRIPTION
       "The accumulated receive timeout count for two-way only - since last 'clear'.
	   "
   ::= { sm24dp4xaPerformanceMonitor 53 } 
   
sm24dp4xaDelayMeasureStateOnewayRxError OBJECT-TYPE
   SYNTAX      DisplayString
   MAX-ACCESS  read-only
   STATUS      current
   DESCRIPTION
       "The accumulated receive error count - since last 'clear'. 
	   This is counting if the frame delay is larger than 1 second or if far end residence time is larger than the round trip time.
	   "
   ::= { sm24dp4xaPerformanceMonitor 54 }
   
sm24dp4xaDelayMeasureStateOnewayAvDelayTot OBJECT-TYPE
   SYNTAX      DisplayString
   MAX-ACCESS  read-only
   STATUS      current
   DESCRIPTION
       "The average total delay - since last 'clear'.
	   "
   ::= { sm24dp4xaPerformanceMonitor 55 }
   
sm24dp4xaDelayMeasureStateOnewayAvDelaylastN OBJECT-TYPE
   SYNTAX      DisplayString
   MAX-ACCESS  read-only
   STATUS      current
   DESCRIPTION
       "The average delay of the last n packets - since last 'clear'.
	   "
   ::= { sm24dp4xaPerformanceMonitor 56 }
   
sm24dp4xaDelayMeasureStateOnewayDelayMin OBJECT-TYPE
   SYNTAX      DisplayString
   MAX-ACCESS  read-only
   STATUS      current
   DESCRIPTION
       "The minimum delay - since last 'clear'.
	   "
   ::= { sm24dp4xaPerformanceMonitor 57 }
   
sm24dp4xaDelayMeasureStateOnewayDelayMax OBJECT-TYPE
   SYNTAX      DisplayString
   MAX-ACCESS  read-only
   STATUS      current
   DESCRIPTION
       "The maximum delay - since last 'clear'.
	   "
   ::= { sm24dp4xaPerformanceMonitor 58 }
   
sm24dp4xaDelayMeasureStateOnewayAvDelayVarTot OBJECT-TYPE
   SYNTAX      DisplayString
   MAX-ACCESS  read-only
   STATUS      current
   DESCRIPTION
       "The average total delay variation - since last 'clear'.
	   "
   ::= { sm24dp4xaPerformanceMonitor 59 }
   
sm24dp4xaDelayMeasureStateOnewayAvDelayVarlastN OBJECT-TYPE
   SYNTAX      DisplayString
   MAX-ACCESS  read-only
   STATUS      current
   DESCRIPTION
       "The average delay variation of the last n packets - since last 'clear'.
	   "
   ::= { sm24dp4xaPerformanceMonitor 60 }
   
sm24dp4xaDelayMeasureStateOnewayDelayVarMin OBJECT-TYPE
   SYNTAX      DisplayString
   MAX-ACCESS  read-only
   STATUS      current
   DESCRIPTION
       "The minimum delay variation - since last 'clear'.
	   "
   ::= { sm24dp4xaPerformanceMonitor 61 }
   
sm24dp4xaDelayMeasureStateOnewayDelayVarMax OBJECT-TYPE
   SYNTAX      DisplayString
   MAX-ACCESS  read-only
   STATUS      current
   DESCRIPTION
       "The maximum delay variation - since last 'clear'.
	   "
   ::= { sm24dp4xaPerformanceMonitor 62 }
   
sm24dp4xaDelayMeasureStateOnewayOverflow OBJECT-TYPE
   SYNTAX      DisplayString
   MAX-ACCESS  read-only
   STATUS      current
   DESCRIPTION
       "The number of counter overflow - since last 'clear'.
	   "
   ::= { sm24dp4xaPerformanceMonitor 63 }
   
sm24dp4xaDelayMeasureStateFtoNTx OBJECT-TYPE
   SYNTAX      Integer32
   MAX-ACCESS  read-only
   STATUS      current
   DESCRIPTION
       "The accumulated transmit count - since last 'clear'.
	   "
   ::= { sm24dp4xaPerformanceMonitor 64 } 
   
sm24dp4xaDelayMeasureStateFtoNRx OBJECT-TYPE
   SYNTAX      Integer32
   MAX-ACCESS  read-only
   STATUS      current
   DESCRIPTION
       "The accumulated receive count - since last 'clear'.
	   "
   ::= { sm24dp4xaPerformanceMonitor 65 } 
   
sm24dp4xaDelayMeasureStateFtoNRxTimeout OBJECT-TYPE
   SYNTAX      Integer32
   MAX-ACCESS  read-only
   STATUS      current
   DESCRIPTION
       "The accumulated receive timeout count for two-way only - since last 'clear'.
	   "
   ::= { sm24dp4xaPerformanceMonitor 66 } 
   
sm24dp4xaDelayMeasureStateFtoNRxError OBJECT-TYPE
   SYNTAX      Integer32
   MAX-ACCESS  read-only
   STATUS      current
   DESCRIPTION
       "The accumulated receive error count - since last 'clear'. 
	   This is counting if the frame delay is larger than 1 second or if far end residence time is larger than the round trip time.
	   "
   ::= { sm24dp4xaPerformanceMonitor 67 }
   
sm24dp4xaDelayMeasureStateFtoNAvDelayTot OBJECT-TYPE
   SYNTAX      Integer32
   MAX-ACCESS  read-only
   STATUS      current
   DESCRIPTION
       "The average total delay - since last 'clear'.
	   "
   ::= { sm24dp4xaPerformanceMonitor 68 }
   
sm24dp4xaDelayMeasureStateFtoNAvDelaylastN OBJECT-TYPE
   SYNTAX      Integer32
   MAX-ACCESS  read-only
   STATUS      current
   DESCRIPTION
       "The average delay of the last n packets - since last 'clear'.
	   "
   ::= { sm24dp4xaPerformanceMonitor 69 }
   
sm24dp4xaDelayMeasureStateFtoNDelayMin OBJECT-TYPE
   SYNTAX      Integer32
   MAX-ACCESS  read-only
   STATUS      current
   DESCRIPTION
       "The minimum delay - since last 'clear'.
	   "
   ::= { sm24dp4xaPerformanceMonitor 70 }
   
sm24dp4xaDelayMeasureStateFtoNDelayMax OBJECT-TYPE
   SYNTAX      Integer32
   MAX-ACCESS  read-only
   STATUS      current
   DESCRIPTION
       "The maximum delay - since last 'clear'.
	   "
   ::= { sm24dp4xaPerformanceMonitor 71 }
   
sm24dp4xaDelayMeasureStateFtoNAvDelayVarTot OBJECT-TYPE
   SYNTAX      Integer32
   MAX-ACCESS  read-only
   STATUS      current
   DESCRIPTION
       "The average total delay variation - since last 'clear'.
	   "
   ::= { sm24dp4xaPerformanceMonitor 72 }
   
sm24dp4xaDelayMeasureStateFtoNAvDelayVarlastN OBJECT-TYPE
   SYNTAX      Integer32
   MAX-ACCESS  read-only
   STATUS      current
   DESCRIPTION
       "The average delay variation of the last n packets - since last 'clear'.
	   "
   ::= { sm24dp4xaPerformanceMonitor 73 }
   
sm24dp4xaDelayMeasureStateFtoNDelayVarMin OBJECT-TYPE
   SYNTAX      Integer32
   MAX-ACCESS  read-only
   STATUS      current
   DESCRIPTION
       "The minimum delay variation - since last 'clear'.
	   "
   ::= { sm24dp4xaPerformanceMonitor 74 }
   
sm24dp4xaDelayMeasureStateFtoNDelayVarMax OBJECT-TYPE
   SYNTAX      Integer32
   MAX-ACCESS  read-only
   STATUS      current
   DESCRIPTION
       "The maximum delay variation - since last 'clear'.
	   "
   ::= { sm24dp4xaPerformanceMonitor 75 }
   
sm24dp4xaDelayMeasureStateFtoNOverflow OBJECT-TYPE
   SYNTAX      Integer32
   MAX-ACCESS  read-only
   STATUS      current
   DESCRIPTION
       "The number of counter overflow - since last 'clear'.
	   "
   ::= { sm24dp4xaPerformanceMonitor 76 }
   
sm24dp4xaDelayMeasureStateNtoFTx OBJECT-TYPE
   SYNTAX      Integer32
   MAX-ACCESS  read-only
   STATUS      current
   DESCRIPTION
       "The accumulated transmit count - since last 'clear'.
	   "
   ::= { sm24dp4xaPerformanceMonitor 77 } 
   
sm24dp4xaDelayMeasureStateNtoFRx OBJECT-TYPE
   SYNTAX      Integer32
   MAX-ACCESS  read-only
   STATUS      current
   DESCRIPTION
       "The accumulated receive count - since last 'clear'.
	   "
   ::= { sm24dp4xaPerformanceMonitor 78 } 
   
sm24dp4xaDelayMeasureStateNtoFRxTimeout OBJECT-TYPE
   SYNTAX      Integer32
   MAX-ACCESS  read-only
   STATUS      current
   DESCRIPTION
       "The accumulated receive timeout count for two-way only - since last 'clear'.
	   "
   ::= { sm24dp4xaPerformanceMonitor 79 } 
   
sm24dp4xaDelayMeasureStateNtoFRxError OBJECT-TYPE
   SYNTAX      Integer32
   MAX-ACCESS  read-only
   STATUS      current
   DESCRIPTION
       "The accumulated receive error count - since last 'clear'. 
	   This is counting if the frame delay is larger than 1 second or if far end residence time is larger than the round trip time.
	   "
   ::= { sm24dp4xaPerformanceMonitor 80 }
   
sm24dp4xaDelayMeasureStateNtoFAvDelayTot OBJECT-TYPE
   SYNTAX      Integer32
   MAX-ACCESS  read-only
   STATUS      current
   DESCRIPTION
       "The average total delay - since last 'clear'.
	   "
   ::= { sm24dp4xaPerformanceMonitor 81 }
   
sm24dp4xaDelayMeasureStateNtoFAvDelaylastN OBJECT-TYPE
   SYNTAX      Integer32
   MAX-ACCESS  read-only
   STATUS      current
   DESCRIPTION
       "The average delay of the last n packets - since last 'clear'.
	   "
   ::= { sm24dp4xaPerformanceMonitor 82 }
   
sm24dp4xaDelayMeasureStateNtoFDelayMin OBJECT-TYPE
   SYNTAX      Integer32
   MAX-ACCESS  read-only
   STATUS      current
   DESCRIPTION
       "The minimum delay - since last 'clear'.
	   "
   ::= { sm24dp4xaPerformanceMonitor 83 }
   
sm24dp4xaDelayMeasureStateNtoFDelayMax OBJECT-TYPE
   SYNTAX      Integer32
   MAX-ACCESS  read-only
   STATUS      current
   DESCRIPTION
       "The maximum delay - since last 'clear'.
	   "
   ::= { sm24dp4xaPerformanceMonitor 84 }
   
sm24dp4xaDelayMeasureStateNtoFAvDelayVarTot OBJECT-TYPE
   SYNTAX      Integer32
   MAX-ACCESS  read-only
   STATUS      current
   DESCRIPTION
       "The average total delay variation - since last 'clear'.
	   "
   ::= { sm24dp4xaPerformanceMonitor 85 }
   
sm24dp4xaDelayMeasureStateNtoFAvDelayVarlastN OBJECT-TYPE
   SYNTAX      Integer32
   MAX-ACCESS  read-only
   STATUS      current
   DESCRIPTION
       "The average delay variation of the last n packets - since last 'clear'.
	   "
   ::= { sm24dp4xaPerformanceMonitor 86 }
   
sm24dp4xaDelayMeasureStateNtoFDelayVarMin OBJECT-TYPE
   SYNTAX      Integer32
   MAX-ACCESS  read-only
   STATUS      current
   DESCRIPTION
       "The minimum delay variation - since last 'clear'.
	   "
   ::= { sm24dp4xaPerformanceMonitor 87 }
   
sm24dp4xaDelayMeasureStateNtoFDelayVarMax OBJECT-TYPE
   SYNTAX      Integer32
   MAX-ACCESS  read-only
   STATUS      current
   DESCRIPTION
       "The maximum delay variation - since last 'clear'.
	   "
   ::= { sm24dp4xaPerformanceMonitor 88 }
   
sm24dp4xaDelayMeasureStateNtoFOverflow OBJECT-TYPE
   SYNTAX      Integer32
   MAX-ACCESS  read-only
   STATUS      current
   DESCRIPTION
       "The number of counter overflow - since last 'clear'.
	   "
   ::= { sm24dp4xaPerformanceMonitor 89 }
   
sm24dp4xaDelayMeasureStateTwowayTx OBJECT-TYPE
   SYNTAX      Integer32
   MAX-ACCESS  read-only
   STATUS      current
   DESCRIPTION
       "The accumulated transmit count - since last 'clear'.
	   "
   ::= { sm24dp4xaPerformanceMonitor 90 } 
   
sm24dp4xaDelayMeasureStateTwowayRx OBJECT-TYPE
   SYNTAX      Integer32
   MAX-ACCESS  read-only
   STATUS      current
   DESCRIPTION
       "The accumulated receive count - since last 'clear'.
	   "
   ::= { sm24dp4xaPerformanceMonitor 91 } 
   
sm24dp4xaDelayMeasureStateTwowayRxTimeout OBJECT-TYPE
   SYNTAX      Integer32
   MAX-ACCESS  read-only
   STATUS      current
   DESCRIPTION
       "The accumulated receive timeout count for two-way only - since last 'clear'.
	   "
   ::= { sm24dp4xaPerformanceMonitor 92 } 
   
sm24dp4xaDelayMeasureStateTwowayRxError OBJECT-TYPE
   SYNTAX      Integer32
   MAX-ACCESS  read-only
   STATUS      current
   DESCRIPTION
       "The accumulated receive error count - since last 'clear'. 
	   This is counting if the frame delay is larger than 1 second or if far end residence time is larger than the round trip time.
	   "
   ::= { sm24dp4xaPerformanceMonitor 93 }
   
sm24dp4xaDelayMeasureStateTwowayAvDelayTot OBJECT-TYPE
   SYNTAX      Integer32
   MAX-ACCESS  read-only
   STATUS      current
   DESCRIPTION
       "The average total delay - since last 'clear'.
	   "
   ::= { sm24dp4xaPerformanceMonitor 94 }
   
sm24dp4xaDelayMeasureStateTwowayAvDelaylastN OBJECT-TYPE
   SYNTAX      Integer32
   MAX-ACCESS  read-only
   STATUS      current
   DESCRIPTION
       "The average delay of the last n packets - since last 'clear'.
	   "
   ::= { sm24dp4xaPerformanceMonitor 95 }
   
sm24dp4xaDelayMeasureStateTwowayDelayMin OBJECT-TYPE
   SYNTAX      Integer32
   MAX-ACCESS  read-only
   STATUS      current
   DESCRIPTION
       "The minimum delay - since last 'clear'.
	   "
   ::= { sm24dp4xaPerformanceMonitor 96 }
   
sm24dp4xaDelayMeasureStateTwowayDelayMax OBJECT-TYPE
   SYNTAX      Integer32
   MAX-ACCESS  read-only
   STATUS      current
   DESCRIPTION
       "The maximum delay - since last 'clear'.
	   "
   ::= { sm24dp4xaPerformanceMonitor 97 }
   
sm24dp4xaDelayMeasureStateTwowayAvDelayVarTot OBJECT-TYPE
   SYNTAX      Integer32
   MAX-ACCESS  read-only
   STATUS      current
   DESCRIPTION
       "The average total delay variation - since last 'clear'.
	   "
   ::= { sm24dp4xaPerformanceMonitor 98 }
   
sm24dp4xaDelayMeasureStateTwowayAvDelayVarlastN OBJECT-TYPE
   SYNTAX      Integer32
   MAX-ACCESS  read-only
   STATUS      current
   DESCRIPTION
       "The average delay variation of the last n packets - since last 'clear'.
	   "
   ::= { sm24dp4xaPerformanceMonitor 99 }
   
sm24dp4xaDelayMeasureStateTwowayDelayVarMin OBJECT-TYPE
   SYNTAX      Integer32
   MAX-ACCESS  read-only
   STATUS      current
   DESCRIPTION
       "The minimum delay variation - since last 'clear'.
	   "
   ::= { sm24dp4xaPerformanceMonitor 100 }
   
sm24dp4xaDelayMeasureStateTwowayDelayVarMax OBJECT-TYPE
   SYNTAX      Integer32
   MAX-ACCESS  read-only
   STATUS      current
   DESCRIPTION
       "The maximum delay variation - since last 'clear'.
	   "
   ::= { sm24dp4xaPerformanceMonitor 101 }
   
sm24dp4xaDelayMeasureStateTwowayOverflow OBJECT-TYPE
   SYNTAX      Integer32
   MAX-ACCESS  read-only
   STATUS      current
   DESCRIPTION
       "The number of counter overflow - since last 'clear'.
	   "
   ::= { sm24dp4xaPerformanceMonitor 102 }
   
sm24dp4xaDelayMeasureStateClear OBJECT-TYPE
   SYNTAX      Integer32
   MAX-ACCESS  read-write
   STATUS      current
   DESCRIPTION
       "Set of this check and save will clear the accumulated counters.
	   1:clear
	   "
   ::= { sm24dp4xaPerformanceMonitor 103 }
   
sm24dp4xaDelayMeasureBinsMeasureBinsforFD OBJECT-TYPE
   SYNTAX      Integer32
   MAX-ACCESS  read-write
   STATUS      current
   DESCRIPTION
       "Configurable number of Frame Delay Measurement Bins per Measurement Interval.
	   range: 2-10
	   "
   ::= { sm24dp4xaPerformanceMonitor 104 }
   
sm24dp4xaDelayMeasureBinsMeasureBinsforIFDV OBJECT-TYPE
   SYNTAX      Integer32
   MAX-ACCESS  read-write
   STATUS      current
   DESCRIPTION
       "Configurable number of Inter-Frame Delay Variation Measurement Bins per Measurement Interval.
	   range: 2-10
	   "
   ::= { sm24dp4xaPerformanceMonitor 105 }
   
sm24dp4xaDelayMeasureBinsMeasureThreshold OBJECT-TYPE
   SYNTAX      Integer32
   MAX-ACCESS  read-write
   STATUS      current
   DESCRIPTION
       "Configurable the Measurement Threshold for each Measurement Bin.
	   "
   ::= { sm24dp4xaPerformanceMonitor 106 }
   
   
   
   
sm24dp4xaPerformMonitorDelayMeasureBinsforFDTable OBJECT-TYPE
   SYNTAX      SEQUENCE OF SM24DP4XAPerformMonitorDelayMeasureBinsforFDEntry
   MAX-ACCESS  not-accessible
   STATUS      current
   DESCRIPTION
       " "
   ::= { sm24dp4xaMEP 16 }

sm24dp4xaPerformMonitorDelayMeasureBinsforFDEntry OBJECT-TYPE
   SYNTAX      SM24DP4XAPerformMonitorDelayMeasureBinsforFDEntry
   MAX-ACCESS  not-accessible
   STATUS      current
   DESCRIPTION
       " "
   INDEX    { sm24dp4xaPerformMonitorDelayMeasureBinsforFDIndex  }
   ::= { sm24dp4xaPerformMonitorDelayMeasureBinsforFDTable 1 }

SM24DP4XAPerformMonitorDelayMeasureBinsforFDEntry ::= SEQUENCE {
   sm24dp4xaPerformMonitorDelayMeasureBinsforFDIndex    Integer32,
   sm24dp4xaPerformMonitorDelayMeasureBinsforFDOneway   Integer32,
   sm24dp4xaPerformMonitorDelayMeasureBinsforFDFtoN     Integer32,
   sm24dp4xaPerformMonitorDelayMeasureBinsforFDNtoF     Integer32,
   sm24dp4xaPerformMonitorDelayMeasureBinsforFDTwoway   Integer32

}

sm24dp4xaPerformMonitorDelayMeasureBinsforFDIndex OBJECT-TYPE
   SYNTAX      Integer32 (1..65535)
   MAX-ACCESS  not-accessible
   STATUS      current
   DESCRIPTION
       "Index"
   ::= { sm24dp4xaPerformMonitorDelayMeasureBinsforFDEntry 1 }

sm24dp4xaPerformMonitorDelayMeasureBinsforFDOneway OBJECT-TYPE
   SYNTAX      Integer32
   MAX-ACCESS  read-only
   STATUS      current
   DESCRIPTION
       " "
   ::= { sm24dp4xaPerformMonitorDelayMeasureBinsforFDEntry 2 }

sm24dp4xaPerformMonitorDelayMeasureBinsforFDFtoN OBJECT-TYPE
   SYNTAX      Integer32
   MAX-ACCESS  read-only
   STATUS      current
   DESCRIPTION
       " "
   ::= { sm24dp4xaPerformMonitorDelayMeasureBinsforFDEntry 3 }
   
sm24dp4xaPerformMonitorDelayMeasureBinsforFDNtoF OBJECT-TYPE
   SYNTAX      Integer32
   MAX-ACCESS  read-only
   STATUS      current
   DESCRIPTION
       " "
   ::= { sm24dp4xaPerformMonitorDelayMeasureBinsforFDEntry 4 }
   
sm24dp4xaPerformMonitorDelayMeasureBinsforFDTwoway OBJECT-TYPE
   SYNTAX      Integer32
   MAX-ACCESS  read-only
   STATUS      current
   DESCRIPTION
       " "
   ::= { sm24dp4xaPerformMonitorDelayMeasureBinsforFDEntry 5 }
   
   
   
   
sm24dp4xaPerformMonitorDelayMeasureBinsforIFDVTable OBJECT-TYPE
   SYNTAX      SEQUENCE OF SM24DP4XAPerformMonitorDelayMeasureBinsforIFDVEntry
   MAX-ACCESS  not-accessible
   STATUS      current
   DESCRIPTION
       " "
   ::= { sm24dp4xaMEP 17 }

sm24dp4xaPerformMonitorDelayMeasureBinsforIFDVEntry OBJECT-TYPE
   SYNTAX      SM24DP4XAPerformMonitorDelayMeasureBinsforIFDVEntry
   MAX-ACCESS  not-accessible
   STATUS      current
   DESCRIPTION
       " "
   INDEX    { sm24dp4xaPerformMonitorDelayMeasureBinsforIFDVIndex  }
   ::= { sm24dp4xaPerformMonitorDelayMeasureBinsforIFDVTable 1 }

SM24DP4XAPerformMonitorDelayMeasureBinsforIFDVEntry ::= SEQUENCE {
   sm24dp4xaPerformMonitorDelayMeasureBinsforIFDVIndex    Integer32,
   sm24dp4xaPerformMonitorDelayMeasureBinsforIFDVOneway   Integer32,
   sm24dp4xaPerformMonitorDelayMeasureBinsforIFDVFtoN     Integer32,
   sm24dp4xaPerformMonitorDelayMeasureBinsforIFDVNtoF     Integer32,
   sm24dp4xaPerformMonitorDelayMeasureBinsforIFDVTwoway   Integer32

}

sm24dp4xaPerformMonitorDelayMeasureBinsforIFDVIndex OBJECT-TYPE
   SYNTAX      Integer32 (1..65535)
   MAX-ACCESS  not-accessible
   STATUS      current
   DESCRIPTION
       "Index"
   ::= { sm24dp4xaPerformMonitorDelayMeasureBinsforIFDVEntry 1 }

sm24dp4xaPerformMonitorDelayMeasureBinsforIFDVOneway OBJECT-TYPE
   SYNTAX      Integer32
   MAX-ACCESS  read-only
   STATUS      current
   DESCRIPTION
       " "
   ::= { sm24dp4xaPerformMonitorDelayMeasureBinsforIFDVEntry 2 }

sm24dp4xaPerformMonitorDelayMeasureBinsforIFDVFtoN OBJECT-TYPE
   SYNTAX      Integer32
   MAX-ACCESS  read-only
   STATUS      current
   DESCRIPTION
       " "
   ::= { sm24dp4xaPerformMonitorDelayMeasureBinsforIFDVEntry 3 }
   
sm24dp4xaPerformMonitorDelayMeasureBinsforIFDVNtoF OBJECT-TYPE
   SYNTAX      Integer32
   MAX-ACCESS  read-only
   STATUS      current
   DESCRIPTION
       " "
   ::= { sm24dp4xaPerformMonitorDelayMeasureBinsforIFDVEntry 4 }
   
sm24dp4xaPerformMonitorDelayMeasureBinsforIFDVTwoway OBJECT-TYPE
   SYNTAX      Integer32
   MAX-ACCESS  read-only
   STATUS      current
   DESCRIPTION
       " "
   ::= { sm24dp4xaPerformMonitorDelayMeasureBinsforIFDVEntry 5 }
   
sm24dp4xaRRING    OBJECT IDENTIFIER ::= { sm24dp4xaConfiguration 27 }   
   
sm24dp4xaRRINGTable OBJECT-TYPE
   SYNTAX      SEQUENCE OF SM24DP4XARRINGEntry
   MAX-ACCESS  not-accessible
   STATUS      current
   DESCRIPTION
       " "
   ::= { sm24dp4xaRRING 1 }

sm24dp4xaRRINGEntry OBJECT-TYPE
   SYNTAX      SM24DP4XARRINGEntry
   MAX-ACCESS  not-accessible
   STATUS      current
   DESCRIPTION
       " "
   INDEX    { sm24dp4xaRRINGIndex  }
   ::= { sm24dp4xaRRINGTable 1 }

SM24DP4XARRINGEntry ::= SEQUENCE {
   sm24dp4xaRRINGIndex     Integer32,
   sm24dp4xaRRINGRole      Integer32,
   sm24dp4xaRRINGPort1     Integer32,
   sm24dp4xaRRINGPort2     Integer32,
   sm24dp4xaRRINGStatus1   DisplayString,
   sm24dp4xaRRINGStatus2   DisplayString
}

sm24dp4xaRRINGIndex OBJECT-TYPE
   SYNTAX      Integer32 (1..65535)
   MAX-ACCESS  not-accessible
   STATUS      current
   DESCRIPTION
       "Index"
   ::= { sm24dp4xaRRINGEntry 1 }

sm24dp4xaRRINGRole OBJECT-TYPE
   SYNTAX      Integer32
   MAX-ACCESS  read-write
   STATUS      current
   DESCRIPTION
       "Set role value.
	   0:Disabled
	   1:Master
	   2:Member
	   3:Rapid-Chain
	   "
   ::= { sm24dp4xaRRINGEntry 2 }

sm24dp4xaRRINGPort1 OBJECT-TYPE
   SYNTAX      Integer32
   MAX-ACCESS  read-write
   STATUS      current
   DESCRIPTION
       "The switch port number of the port1 .
	   "
   ::= { sm24dp4xaRRINGEntry 3 }
   
sm24dp4xaRRINGPort2 OBJECT-TYPE
   SYNTAX      Integer32
   MAX-ACCESS  read-write
   STATUS      current
   DESCRIPTION
       "The switch port number of the port2 .
	   "
   ::= { sm24dp4xaRRINGEntry 4 }  
   
sm24dp4xaRRINGStatus1 OBJECT-TYPE
   SYNTAX      DisplayString
   MAX-ACCESS  read-only
   STATUS      current
   DESCRIPTION
       "The current Rapid Ring status of the port1. "
   ::= { sm24dp4xaRRINGEntry 5 } 
   
sm24dp4xaRRINGStatus2 OBJECT-TYPE
   SYNTAX      DisplayString
   MAX-ACCESS  read-only
   STATUS      current
   DESCRIPTION
       "The current Rapid Ring status of the port2. "
   ::= { sm24dp4xaRRINGEntry 6 }    

sm24dp4xaRINGtoRINGRole OBJECT-TYPE
   SYNTAX      Integer32
   MAX-ACCESS  read-write
   STATUS      current
   DESCRIPTION
       "Set ring-to-ring role value.
	   0:Disabled
	   1:Active
	   2:Backup
	   "
   ::= { sm24dp4xaRRING 2 }

sm24dp4xaRINGtoRINGPort OBJECT-TYPE
   SYNTAX      Integer32
   MAX-ACCESS  read-write
   STATUS      current
   DESCRIPTION
       "The switch port number of the ring-to-ring port.
	   "
   ::= { sm24dp4xaRRING 3 }
   

sm24dp4xaRINGtoRINGStatus OBJECT-TYPE
   SYNTAX      DisplayString
   MAX-ACCESS  read-only
   STATUS      current
   DESCRIPTION
       "The current ring-to-ring status of the port."
   ::= { sm24dp4xaRRING 4 }
   
   
sm24dp4xaPTP    OBJECT IDENTIFIER ::= { sm24dp4xaConfiguration 28 }   

sm24dp4xaPTPOnePPSMode OBJECT-TYPE
   SYNTAX      Integer32
   MAX-ACCESS  read-write
   STATUS      current
   DESCRIPTION
       "This Selection box will allow you to select the One_pps_mode configuration.
		The following values are possible:
		0:Disable
		1. Output
		2. Input
		3. Output Input
		"
   ::= { sm24dp4xaPTP 1 }
   
sm24dp4xaPTPExternalEnable OBJECT-TYPE
   SYNTAX      Integer32
   MAX-ACCESS  read-write
   STATUS      current
   DESCRIPTION
       "This Selection box will allow you to configure the External Clock output.
		The following values are possible:
		1. True : Enable the external clock output
		0. False : Disable the external clock output
		"
   ::= { sm24dp4xaPTP 2 }   
   
sm24dp4xaPTPAdjustMethod OBJECT-TYPE
   SYNTAX      Integer32
   MAX-ACCESS  read-write
   STATUS      current
   DESCRIPTION
       "This Selection box will allow you to configure the Frequency adjustment configuration.
		0: LTC frequency : Select Local Time Counter (LTC) frequency control
		1: SyncE-DPLL : Select SyncE DPLL frequency control, if allowed by SyncE
		2: Oscillator : Select an oscillator independent of SyncE for frequency control, if supported by the HW
		3: LTC phase : Select Local Time Counter (LTC) phase control (assumes that the frequency is locked by means of SyncE)
		"
   ::= { sm24dp4xaPTP 3 }      
   
sm24dp4xaPTPClockFrequency OBJECT-TYPE
   SYNTAX      Integer32
   MAX-ACCESS  read-write
   STATUS      current
   DESCRIPTION
       "This will allow to set the Clock Frequency.
        The possible range of values are 1 - 25000000 (1 - 25MHz)
	   "
   ::= { sm24dp4xaPTP 4 }   
   


sm24dp4xaPTPClockConfTable  OBJECT-TYPE
   SYNTAX      SEQUENCE OF SM24DP4XAPTPClockConfEntry
   MAX-ACCESS  not-accessible
   STATUS      current
   DESCRIPTION
       "A table of PTP Clock Conf."
 ::= { sm24dp4xaPTP 5 }

sm24dp4xaPTPClockConfEntry OBJECT-TYPE
    SYNTAX        SM24DP4XAPTPClockConfEntry
    MAX-ACCESS    not-accessible
    STATUS        current
    DESCRIPTION
        "An entry in the PTP Clock Conf table."
    INDEX        { sm24dp4xaPTPClockConfIndex }
    ::= { sm24dp4xaPTPClockConfTable 1 }

SM24DP4XAPTPClockConfEntry ::=
    SEQUENCE {
        sm24dp4xaPTPClockConfIndex                    Integer32,
        sm24dp4xaPTPClockConfClockInstance            Integer32,
        sm24dp4xaPTPClockConfDeviceType               Integer32,
		sm24dp4xaPTPClockConfProfile                  Integer32,
        sm24dp4xaPTPClockConfRowStatus                RowStatus
    }

sm24dp4xaPTPClockConfIndex OBJECT-TYPE
   SYNTAX      Integer32 (1..65535)
   MAX-ACCESS  not-accessible
   STATUS      current
   DESCRIPTION
       "PTP Clock Conf index."
   ::= {sm24dp4xaPTPClockConfEntry 1 }

sm24dp4xaPTPClockConfClockInstance OBJECT-TYPE
   SYNTAX      Integer32
   MAX-ACCESS  read-create
   STATUS      current
   DESCRIPTION
       "Indicates the Instance of a particular Clock Instance [0..3]."
   ::= {sm24dp4xaPTPClockConfEntry 2 }

sm24dp4xaPTPClockConfDeviceType OBJECT-TYPE
   SYNTAX      Integer32
   MAX-ACCESS  read-create
   STATUS      current
   DESCRIPTION
       "Indicates the Type of the Clock Instance. There are five Device Types.
	    0: Inactive - passive clock instance
		1: Ord-Bound - clock's Device Type is Ordinary-Boundary Clock.
		2: P2p Transp - clock's Device Type is Peer to Peer Transparent Clock.
		3: E2e Transp - clock's Device Type is End to End Transparent Clock.
		4: Master Only - clock's Device Type is Master Only.
		5: Slave Only - clock's Device Type is Slave Only.
		6: Boundary Clock frontend clock instance, only 1-step, 1-way is supported."
   ::= {sm24dp4xaPTPClockConfEntry 3 }
   
sm24dp4xaPTPClockConfProfile OBJECT-TYPE
   SYNTAX      Integer32
   MAX-ACCESS  read-create
   STATUS      current
   DESCRIPTION
       "0:No profile
	   1:1588
	   2:G8265.1
	   3:G8275.1
	   "
   ::= {sm24dp4xaPTPClockConfEntry 4 }   
   
sm24dp4xaPTPClockConfRowStatus OBJECT-TYPE
   SYNTAX      RowStatus
   MAX-ACCESS  read-create
   STATUS      current
   DESCRIPTION
       "PTP Clock Conf Row Status."
   ::= {sm24dp4xaPTPClockConfEntry 5 }
   
sm24dp4xaPTPClockInstance OBJECT-TYPE
   SYNTAX      Integer32
   MAX-ACCESS  read-write
   STATUS      current
   DESCRIPTION
       "Specify the PTP clock instance for the following item used [0..3]."
   ::= {sm24dp4xaPTP 6 }
   
   
sm24dp4xaPTPClkConfAndStatus    OBJECT IDENTIFIER ::= { sm24dp4xaPTP 7 }

sm24dp4xaPTPClkConfEntClkInstance OBJECT-TYPE
   SYNTAX      Integer32
   MAX-ACCESS  read-only
   STATUS      current
   DESCRIPTION
       ""
   ::= {sm24dp4xaPTPClkConfAndStatus 2 }

sm24dp4xaPTPClkConfEntDeviceType OBJECT-TYPE
   SYNTAX      DisplayString
   MAX-ACCESS  read-only
   STATUS      current
   DESCRIPTION
       ""
   ::= {sm24dp4xaPTPClkConfAndStatus 3 }
   
sm24dp4xaPTPClkConfEntProfile OBJECT-TYPE
   SYNTAX      DisplayString
   MAX-ACCESS  read-only
   STATUS      current
   DESCRIPTION
       ""
   ::= {sm24dp4xaPTPClkConfAndStatus 4 }

sm24dp4xaPTPClkConfEntApplyProfileDefaults OBJECT-TYPE
   SYNTAX      Integer32
   MAX-ACCESS  read-write
   STATUS      current
   DESCRIPTION
       "-1:n/a
	   0:normal state
	   1:apply profile default"
   ::= {sm24dp4xaPTPClkConfAndStatus 5 }
   
sm24dp4xaPTPClkConfEntPTPTime OBJECT-TYPE
   SYNTAX      DisplayString
   MAX-ACCESS  read-only
   STATUS      current
   DESCRIPTION
       "Shows the actual PTP time with nanosecond resolution."
   ::= {sm24dp4xaPTPClkConfAndStatus 6 }
   
sm24dp4xaPTPClkConfEntClkAdjustmentMethod OBJECT-TYPE
   SYNTAX      DisplayString
   MAX-ACCESS  read-only
   STATUS      current
   DESCRIPTION
       "Shows the actual clock adjustment method. The method depends on the available hardware."
   ::= {sm24dp4xaPTPClkConfAndStatus 7 }
   
sm24dp4xaPTPClkConfEntSynchronizeToSystemClk OBJECT-TYPE
   SYNTAX      Integer32
   MAX-ACCESS  read-write
   STATUS      current
   DESCRIPTION
       "Activate this button to synchronize the System Clock to PTP Time.
	   1:Synchronize to system clock."
   ::= {sm24dp4xaPTPClkConfAndStatus 8 }

sm24dp4xaPTPClkConfEntClkCurDataSetstpRm OBJECT-TYPE
   SYNTAX      Integer32
   MAX-ACCESS  read-only
   STATUS      current
   DESCRIPTION
       "Steps Removed : It is the number of PTP clocks traversed from the grandmaster to the local slave clock."
   ::= {sm24dp4xaPTPClkConfAndStatus 9 }
   
sm24dp4xaPTPClkConfEntClkCurDataSetOffsetFromMaster OBJECT-TYPE
   SYNTAX      DisplayString
   MAX-ACCESS  read-only
   STATUS      current
   DESCRIPTION
       "Time difference between the master clock and the local slave clock, measured in ns."
   ::= {sm24dp4xaPTPClkConfAndStatus 10 }
  
sm24dp4xaPTPClkConfEntClkCurDataSetMeanPathDelay OBJECT-TYPE
   SYNTAX      DisplayString
   MAX-ACCESS  read-only
   STATUS      current
   DESCRIPTION
       "The mean propagation time for the link between the master and the local slave."
   ::= {sm24dp4xaPTPClkConfAndStatus 11 }
   
sm24dp4xaPTPClkConfEntClkCurDataSetSlavePort OBJECT-TYPE
   SYNTAX      Integer32
   MAX-ACCESS  read-only
   STATUS      current
   DESCRIPTION
       "Shows which port is in slave mode. The value is 0 if no ports are in slave mode."
   ::= {sm24dp4xaPTPClkConfAndStatus 12 }
   
sm24dp4xaPTPClkConfEntClkCurDataSetSlaveState OBJECT-TYPE
   SYNTAX      DisplayString
   MAX-ACCESS  read-only
   STATUS      current
   DESCRIPTION
       "Shows synchronization state of the slave."
   ::= {sm24dp4xaPTPClkConfAndStatus 13 }
   
sm24dp4xaPTPClkConfEntClkCurDataSetHoldover OBJECT-TYPE
   SYNTAX      DisplayString
   MAX-ACCESS  read-only
   STATUS      current
   DESCRIPTION
       "After the slave has been in Locked mode during the stabilization period, 
	   this value shows the actual clock offset between the freerun and the actual holdover frequency, 
	   the value is shown in parts pr billion (ppb). 
	   During the stabilization period, the value is shown as N.A. 
	   The stabilization period is 60 sec as default, it can be changed from the CLI interface."
   ::= {sm24dp4xaPTPClkConfAndStatus 14 }

sm24dp4xaPTPClkConfEntClkParentDataSetParentPortID OBJECT-TYPE
   SYNTAX      DisplayString
   MAX-ACCESS  read-only
   STATUS      current
   DESCRIPTION
       "Clock identity for the parent clock, if the local clock is not a slave, the value is the clocks own id."
   ::= {sm24dp4xaPTPClkConfAndStatus 15 }
  
sm24dp4xaPTPClkConfEntClkParentDataSetPort OBJECT-TYPE
   SYNTAX      Integer32
   MAX-ACCESS  read-only
   STATUS      current
   DESCRIPTION
       "Port Id for the parent master port"
   ::= {sm24dp4xaPTPClkConfAndStatus 16 }

sm24dp4xaPTPClkConfEntClkParentDataSetPStat OBJECT-TYPE
   SYNTAX      DisplayString
   MAX-ACCESS  read-only
   STATUS      current
   DESCRIPTION
       "Parents Stats (always false)."
   ::= {sm24dp4xaPTPClkConfAndStatus 17 }
   
sm24dp4xaPTPClkConfEntClkParentDataSetVar OBJECT-TYPE
   SYNTAX      Integer32
   MAX-ACCESS  read-only
   STATUS      current
   DESCRIPTION
       "It is observed parent offset scaled log variance"
   ::= {sm24dp4xaPTPClkConfAndStatus 18 }
   
sm24dp4xaPTPClkConfEntClkParentDataSetRate OBJECT-TYPE
   SYNTAX      Integer32
   MAX-ACCESS  read-only
   STATUS      current
   DESCRIPTION
       "Observed Parent Clock Phase Change Rate. i.e. the slave clocks rate offset compared to the master. 
	   (unit = ns per s)."
   ::= {sm24dp4xaPTPClkConfAndStatus 19 }

sm24dp4xaPTPClkConfEntClkParentDataSetGrandMasterID OBJECT-TYPE
   SYNTAX      DisplayString
   MAX-ACCESS  read-only
   STATUS      current
   DESCRIPTION
       "Clock identity for the grand master clock, if the local clock is not a slave, the value is the clocks own id."
   ::= {sm24dp4xaPTPClkConfAndStatus 20 }

sm24dp4xaConfEntClkParentDataSetGrandMasterClkQuality OBJECT-TYPE
   SYNTAX      DisplayString
   MAX-ACCESS  read-only
   STATUS      current
   DESCRIPTION
       "The clock quality announced by the grand master (See description of Clock Default DataSet:Clock Quality)"
   ::= {sm24dp4xaPTPClkConfAndStatus 21 }
   
sm24dp4xaPTPClkConfEntClkParentDataSetPri1 OBJECT-TYPE
   SYNTAX      Integer32
   MAX-ACCESS  read-only
   STATUS      current
   DESCRIPTION
       "Clock priority 1 announced by the grand master"
   ::= {sm24dp4xaPTPClkConfAndStatus 22 }

sm24dp4xaPTPClkConfEntClkParentDataSetPri2 OBJECT-TYPE
   SYNTAX      Integer32
   MAX-ACCESS  read-only
   STATUS      current
   DESCRIPTION
       "Clock priority 2 announced by the grand master."
   ::= {sm24dp4xaPTPClkConfAndStatus 23 }
   
sm24dp4xaPTPClkConfEntClkDefaultDataSetClkID OBJECT-TYPE
   SYNTAX      Integer32
   MAX-ACCESS  read-only
   STATUS      current
   DESCRIPTION
       "An internal instance id (0..3)"
   ::= {sm24dp4xaPTPClkConfAndStatus 24 }
   
sm24dp4xaPTPClkConfEntClkDefaultDataSetDeviceType OBJECT-TYPE
   SYNTAX      DisplayString
   MAX-ACCESS  read-only
   STATUS      current
   DESCRIPTION
       "Indicates the Type of the Clock Instance. There are five Device Types.
		1. Ord-Bound - Clock's Device Type is Ordinary-Boundary Clock.
		2. P2p Transp - Clock's Device Type is Peer to Peer Transparent Clock.
		3. E2e Transp - Clock's Device Type is End to End Transparent Clock.
		4. Master Only - Clock's Device Type is Master Only.
		5. Slave Only - Clock's Device Type is Slave Only."
   ::= {sm24dp4xaPTPClkConfAndStatus 25 }

sm24dp4xaPTPClkConfEntClkDefaultDataSet2StepFlag OBJECT-TYPE
   SYNTAX      Integer32
   MAX-ACCESS  read-write
   STATUS      current
   DESCRIPTION
       "True if two-step Sync events and Pdelay_Resp events are used
	   0:false
	   1:true"
   ::= {sm24dp4xaPTPClkConfAndStatus 26 }

sm24dp4xaPTPClkConfEntClkDefaultDataSetPorts OBJECT-TYPE
   SYNTAX      Integer32
   MAX-ACCESS  read-only
   STATUS      current
   DESCRIPTION
       "The total number of physical ports in the node"
   ::= {sm24dp4xaPTPClkConfAndStatus 27 }
   
sm24dp4xaPTPClkConfEntClkDefaultDataSetClkIdentity OBJECT-TYPE
   SYNTAX      DisplayString
   MAX-ACCESS  read-only
   STATUS      current
   DESCRIPTION
       "It shows unique clock identifier"
   ::= {sm24dp4xaPTPClkConfAndStatus 28 }

sm24dp4xaPTPClkConfEntClkDefaultDataSetDom OBJECT-TYPE
   SYNTAX      Integer32
   MAX-ACCESS  read-write
   STATUS      current
   DESCRIPTION
       "Clock domain [0..127]."
   ::= {sm24dp4xaPTPClkConfAndStatus 29 }
   
sm24dp4xaPTPClkConfEntClkDefaultDataSetClkQuality OBJECT-TYPE
   SYNTAX      DisplayString
   MAX-ACCESS  read-only
   STATUS      current
   DESCRIPTION
       "The clock quality is determined by the system, and holds 3 parts: Clock Class, Clock Accuracy and OffsetScaledLog Variance as defined in IEEE1588.
The Clock Accuracy values are defined in IEEE1588 table 6 (Currently the clock Accuracy is set to 'Unknown' as default)."
   ::= {sm24dp4xaPTPClkConfAndStatus 30 }
   
sm24dp4xaPTPClkConfEntClkDefaultDataSetPri1 OBJECT-TYPE
   SYNTAX      Integer32
   MAX-ACCESS  read-write
   STATUS      current
   DESCRIPTION
       "Clock priority 1 [0..255] used by the BMC master select algorithm."
   ::= {sm24dp4xaPTPClkConfAndStatus 31 }
   
sm24dp4xaPTPClkConfEntClkDefaultDataSetPri2 OBJECT-TYPE
   SYNTAX      Integer32
   MAX-ACCESS  read-write
   STATUS      current
   DESCRIPTION
       "Clock priority 2 [0..255] used by the BMC master select algorithm."
   ::= {sm24dp4xaPTPClkConfAndStatus 32 }
   
sm24dp4xaPTPClkConfEntClkDefaultDataSetProtocol OBJECT-TYPE
   SYNTAX      Integer32
   MAX-ACCESS  read-write
   STATUS      current
   DESCRIPTION
       "0:Ethernet
	   1:Ethernet Mixed
	   2:IP4Multi
	   3:IP4Mixed
	   4:IP4Uni
	   5:OAM
	   6:OnePPS"
   ::= {sm24dp4xaPTPClkConfAndStatus 33 }
   
sm24dp4xaPTPClkConfEntClkDefaultDataSetOneWay OBJECT-TYPE
   SYNTAX      Integer32
   MAX-ACCESS  read-write
   STATUS      current
   DESCRIPTION
       "If true, one way measurements are used. 
	   This parameter applies only to a slave. 
	   In one-way mode no delay measurements are performed, i.e. this is applicable only if frequency synchronization is needed. 
	   The master always responds to delay requests.
	   0:false
	   1:true"
   ::= {sm24dp4xaPTPClkConfAndStatus 34 }
   
sm24dp4xaPTPClkConfEntClkDefaultDataSetVLANTagEnable OBJECT-TYPE
   SYNTAX      Integer32
   MAX-ACCESS  read-write
   STATUS      current
   DESCRIPTION
       "The VLAN Tag Enable parameter is ignored, because the tagging is controlled by the VLAN configuration.
	   0:false
	   1:true"
   ::= {sm24dp4xaPTPClkConfAndStatus 35 }

sm24dp4xaPTPClkConfEntClkDefaultDataSetVID OBJECT-TYPE
   SYNTAX      Integer32
   MAX-ACCESS  read-write
   STATUS      current
   DESCRIPTION
       "TVLAN Identifier used for tagging the VLAN packets.
	   range:1-4095"
   ::= {sm24dp4xaPTPClkConfAndStatus 36 }

sm24dp4xaPTPClkConfEntClkDefaultDataSetPCP OBJECT-TYPE
   SYNTAX      Integer32
   MAX-ACCESS  read-write
   STATUS      current
   DESCRIPTION
       "Priority Code Point value used for PTP frames. range:0-7"
   ::= {sm24dp4xaPTPClkConfAndStatus 37 }
   
sm24dp4xaPTPClkConfEntClkDefaultDataSetDSCP OBJECT-TYPE
   SYNTAX      Integer32
   MAX-ACCESS  read-write
   STATUS      current
   DESCRIPTION
       ""
   ::= {sm24dp4xaPTPClkConfAndStatus 38 }
   
sm24dp4xaPTPClkConfEntClkTimePropDataSetUtcOffset OBJECT-TYPE
   SYNTAX      Integer32
   MAX-ACCESS  read-write
   STATUS      current
   DESCRIPTION
       "range: 0-10000"
   ::= {sm24dp4xaPTPClkConfAndStatus 39 }
 
sm24dp4xaPTPClkConfEntClkTimePropDataSetValid OBJECT-TYPE
   SYNTAX      Integer32
   MAX-ACCESS  read-write
   STATUS      current
   DESCRIPTION
       "0:false
	   1:true"
   ::= {sm24dp4xaPTPClkConfAndStatus 40 }
   
sm24dp4xaPTPClkConfEntClkTimePropDataSetLeap59 OBJECT-TYPE
   SYNTAX      Integer32
   MAX-ACCESS  read-write
   STATUS      current
   DESCRIPTION
       "0:false
	   1:true"
   ::= {sm24dp4xaPTPClkConfAndStatus 41 }
   
sm24dp4xaPTPClkConfEntClkTimePropDataSetLeap61 OBJECT-TYPE
   SYNTAX      Integer32
   MAX-ACCESS  read-write
   STATUS      current
   DESCRIPTION
       "0:false
	   1:true"
   ::= {sm24dp4xaPTPClkConfAndStatus 42 }
   
sm24dp4xaPTPClkConfEntClkTimePropDataSetTimeTrac OBJECT-TYPE
   SYNTAX      Integer32
   MAX-ACCESS  read-write
   STATUS      current
   DESCRIPTION
       "0:false
	   1:true"
   ::= {sm24dp4xaPTPClkConfAndStatus 43 }
   
sm24dp4xaPTPClkConfEntClkTimePropDataSetFreqTrac OBJECT-TYPE
   SYNTAX      Integer32
   MAX-ACCESS  read-write
   STATUS      current
   DESCRIPTION
       "0:false
	   1:true"
   ::= {sm24dp4xaPTPClkConfAndStatus 44 }
   
sm24dp4xaPTPClkConfEntClkTimePropDataSetPTPTimeScale OBJECT-TYPE
   SYNTAX      Integer32
   MAX-ACCESS  read-write
   STATUS      current
   DESCRIPTION
       "0:false
	   1:true"
   ::= {sm24dp4xaPTPClkConfAndStatus 45 }
   
sm24dp4xaPTPClkConfEntClkTimePropDataSetTimeSource OBJECT-TYPE
   SYNTAX      Integer32
   MAX-ACCESS  read-write
   STATUS      current
   DESCRIPTION
       "range: 0-255"
   ::= {sm24dp4xaPTPClkConfAndStatus 46 }
   
sm24dp4xaPTPClkConfEntFilterParametersFilterType OBJECT-TYPE
   SYNTAX      Integer32
   MAX-ACCESS  read-write
   STATUS      current
   DESCRIPTION
       "Shows the filter type used which can be either the basic filter or an advanced filter that can be configured to use only a fraction of the packets received 
	   (i.e. the packets that have experienced the least latency).
	   0:BASIC"
   ::= {sm24dp4xaPTPClkConfAndStatus 47 }
   
sm24dp4xaPTPClkConfEntFilterParametersDelayFilter OBJECT-TYPE
   SYNTAX      Integer32
   MAX-ACCESS  read-write
   STATUS      current
   DESCRIPTION
       "range:0-6"
   ::= {sm24dp4xaPTPClkConfAndStatus 48 }
   
sm24dp4xaPTPClkConfEntFilterParametersPeriod OBJECT-TYPE
   SYNTAX      Integer32
   MAX-ACCESS  read-write
   STATUS      current
   DESCRIPTION
       "range:1-10000"
   ::= {sm24dp4xaPTPClkConfAndStatus 49 }

sm24dp4xaPTPClkConfEntFilterParametersDist OBJECT-TYPE
   SYNTAX      Integer32
   MAX-ACCESS  read-write
   STATUS      current
   DESCRIPTION
       "range:1-10"
   ::= {sm24dp4xaPTPClkConfAndStatus 50 }

sm24dp4xaPTPClkConfEntServoParametersDisplay OBJECT-TYPE
   SYNTAX      Integer32
   MAX-ACCESS  read-write
   STATUS      current
   DESCRIPTION
       "If true then Offset From Master, MeanPathDelay and clockAdjustment are logged on the debug terminal
	   0:false
	   1:true"
   ::= {sm24dp4xaPTPClkConfAndStatus 51 }

sm24dp4xaPTPClkConfEntServoParametersPEnable OBJECT-TYPE
   SYNTAX      Integer32
   MAX-ACCESS  read-write
   STATUS      current
   DESCRIPTION
       "If true the P part of the algorithm is included
	   0:false
	   1:true"
   ::= {sm24dp4xaPTPClkConfAndStatus 52 }
   
sm24dp4xaPTPClkConfEntServoParametersIEnable OBJECT-TYPE
   SYNTAX      Integer32
   MAX-ACCESS  read-write
   STATUS      current
   DESCRIPTION
       "If true the I part of the algorithm is included
	   0:false
	   1:true"
   ::= {sm24dp4xaPTPClkConfAndStatus 53 }
   
sm24dp4xaPTPClkConfEntServoParametersDEnable OBJECT-TYPE
   SYNTAX      Integer32
   MAX-ACCESS  read-write
   STATUS      current
   DESCRIPTION
       "If true the D part of the algorithm is included
	   0:false
	   1:true"
   ::= {sm24dp4xaPTPClkConfAndStatus 54 }
   
sm24dp4xaPTPClkConfEntServoParametersPConstant OBJECT-TYPE
   SYNTAX      Integer32
   MAX-ACCESS  read-write
   STATUS      current
   DESCRIPTION
       "range:0-1000"
   ::= {sm24dp4xaPTPClkConfAndStatus 55 }
   
sm24dp4xaPTPClkConfEntServoParametersIConstant OBJECT-TYPE
   SYNTAX      Integer32
   MAX-ACCESS  read-write
   STATUS      current
   DESCRIPTION
       "range:0-10000"
   ::= {sm24dp4xaPTPClkConfAndStatus 56 }

sm24dp4xaPTPClkConfEntServoParametersDConstant OBJECT-TYPE
   SYNTAX      Integer32
   MAX-ACCESS  read-write
   STATUS      current
   DESCRIPTION
       "range:0-1000"
   ::= {sm24dp4xaPTPClkConfAndStatus 57 }

   
sm24dp4xaPTPClockPortDataSetConfTable OBJECT-TYPE
   SYNTAX      SEQUENCE OF SM24DP4XAPTPClockPortDataSetConfEntry
   MAX-ACCESS  not-accessible
   STATUS      current
   DESCRIPTION
       " "
   ::= { sm24dp4xaPTP 8 }

sm24dp4xaPTPClockPortDataSetConfEntry OBJECT-TYPE
   SYNTAX      SM24DP4XAPTPClockPortDataSetConfEntry
   MAX-ACCESS  not-accessible
   STATUS      current
   DESCRIPTION
       " "
   INDEX    { sm24dp4xaPTPClockPortDataSetConfPort  }
   ::= { sm24dp4xaPTPClockPortDataSetConfTable 1 }

SM24DP4XAPTPClockPortDataSetConfEntry ::= SEQUENCE {
   sm24dp4xaPTPClockPortDataSetConfPort               Integer32,
   sm24dp4xaPTPClockConfEntryPortConfEnable           Integer32,
   sm24dp4xaPTPClockConfEntryPortConfStat             DisplayString,
   sm24dp4xaPTPClockConfEntryPortConfMDR              Integer32,
   sm24dp4xaPTPClockConfEntryPortConfPeerMeanPathDel  DisplayString,
   sm24dp4xaPTPClockConfEntryPortConfAnv              Integer32,
   sm24dp4xaPTPClockConfEntryPortConfATo              Integer32,
   sm24dp4xaPTPClockConfEntryPortConfSyv              Integer32,
   sm24dp4xaPTPClockConfEntryPortConfDlm              Integer32,
   sm24dp4xaPTPClockConfEntryPortConfMPR              Integer32,
   sm24dp4xaPTPClockConfEntryPortConfDelayAsymmetry   Integer32,
   sm24dp4xaPTPClockConfEntryPortConfIngressLatency   Integer32,
   sm24dp4xaPTPClockConfEntryPortConfEgressLatency    Integer32,
   sm24dp4xaPTPClockConfEntryPortConfVersion          Integer32
}

sm24dp4xaPTPClockPortDataSetConfPort OBJECT-TYPE
   SYNTAX      Integer32 (1..65535)
   MAX-ACCESS  not-accessible
   STATUS      current
   DESCRIPTION
       "Index"
   ::= { sm24dp4xaPTPClockPortDataSetConfEntry 1 }

sm24dp4xaPTPClockConfEntryPortConfEnable OBJECT-TYPE
   SYNTAX      Integer32
   MAX-ACCESS  read-write
   STATUS      current
   DESCRIPTION
       "0:false
	   1:true"
   ::= { sm24dp4xaPTPClockPortDataSetConfEntry 2 }
   
sm24dp4xaPTPClockConfEntryPortConfStat OBJECT-TYPE
   SYNTAX      DisplayString
   MAX-ACCESS  read-only
   STATUS      current
   DESCRIPTION
       "Dynamic member portState: Current state of the port."
   ::= { sm24dp4xaPTPClockPortDataSetConfEntry 3 }   
   
sm24dp4xaPTPClockConfEntryPortConfMDR OBJECT-TYPE
   SYNTAX      Integer32
   MAX-ACCESS  read-only
   STATUS      current
   DESCRIPTION
       "Dynamic member log Min Delay Req Interval: The delay request interval announced by the master."
   ::= { sm24dp4xaPTPClockPortDataSetConfEntry 4 }      

sm24dp4xaPTPClockConfEntryPortConfPeerMeanPathDel OBJECT-TYPE
   SYNTAX      DisplayString
   MAX-ACCESS  read-only
   STATUS      current
   DESCRIPTION
       "The path delay measured by the port in P2P mode. In E2E mode this value is 0"
   ::= { sm24dp4xaPTPClockPortDataSetConfEntry 5 }  
   

   
sm24dp4xaPTPClockConfEntryPortConfAnv OBJECT-TYPE
   SYNTAX      Integer32
   MAX-ACCESS  read-write
   STATUS      current
   DESCRIPTION
       "The interval for issuing announce messages in master state. Range is -3 to 4."
   ::= { sm24dp4xaPTPClockPortDataSetConfEntry 6 }     
   
sm24dp4xaPTPClockConfEntryPortConfATo OBJECT-TYPE
   SYNTAX      Integer32
   MAX-ACCESS  read-write
   STATUS      current
   DESCRIPTION
       "The timeout for receiving announce messages on the port. Range is 1 to 10."
   ::= { sm24dp4xaPTPClockPortDataSetConfEntry 7 }    
   
sm24dp4xaPTPClockConfEntryPortConfSyv OBJECT-TYPE
   SYNTAX      Integer32
   MAX-ACCESS  read-write
   STATUS      current
   DESCRIPTION
       "The interval for issuing sync messages in master. Range is -7 to 4."
   ::= { sm24dp4xaPTPClockPortDataSetConfEntry 8 }     

sm24dp4xaPTPClockConfEntryPortConfDlm OBJECT-TYPE
   SYNTAX      Integer32
   MAX-ACCESS  read-write
   STATUS      current
   DESCRIPTION
       "Configurable member delayMechanism: The delay mechanism used for the port:
		e2e	End to end delay measurement
		p2p	Peer to peer delay measurement.
		Can be defined per port in an Ordinary/Boundary clock.
		In a transparent clock all ports use the same delay mechanism, determined by the clock type.
		1:e2e
		2:p2p"
   ::= { sm24dp4xaPTPClockPortDataSetConfEntry 9 }    

sm24dp4xaPTPClockConfEntryPortConfMPR OBJECT-TYPE
   SYNTAX      Integer32
   MAX-ACCESS  read-write
   STATUS      current
   DESCRIPTION
       "The interval for issuing Delay_Req messages for the port in E2e mode. This value is announced from the master to the slave in an announce message. The value is reflected in the MDR field in the Slave
The interval for issuing Pdelay_Req messages for the port in P2P mode
Note: The interpretation of this parameter has changed from release 2.40. In earlier versions the value was interpreted relative to the Sync interval, this was a violation of the standard, so now the value is interpreted as an interval. I.e. MPR = 0 => 1 Delay_Req pr sec, independent of the Sync rate.
Range is -7 to 5."
   ::= { sm24dp4xaPTPClockPortDataSetConfEntry 10 }    

sm24dp4xaPTPClockConfEntryPortConfDelayAsymmetry OBJECT-TYPE
   SYNTAX      Integer32
   MAX-ACCESS  read-write
   STATUS      current
   DESCRIPTION
       "If the transmission delay for a link in not symmetric, the asymmetry can be configured here, see IEEE 1588 Section 7.4.2 Communication path asymmetry
Range is -100000 to 100000."
   ::= { sm24dp4xaPTPClockPortDataSetConfEntry 11 }    
   
sm24dp4xaPTPClockConfEntryPortConfIngressLatency OBJECT-TYPE
   SYNTAX      Integer32
   MAX-ACCESS  read-write
   STATUS      current
   DESCRIPTION
       "Ingress latency measured in ns, as defined in IEEE 1588 Section 7.3.4.2.
Range is -100000 to 100000."
   ::= { sm24dp4xaPTPClockPortDataSetConfEntry 12 }     
   
sm24dp4xaPTPClockConfEntryPortConfEgressLatency OBJECT-TYPE
   SYNTAX      Integer32
   MAX-ACCESS  read-write
   STATUS      current
   DESCRIPTION
       "Egress latency measured in ns, as defined in IEEE 1588 Section 7.3.4.2.
Range is -100000 to 100000."
   ::= { sm24dp4xaPTPClockPortDataSetConfEntry 13 }     
   
sm24dp4xaPTPClockConfEntryPortConfVersion OBJECT-TYPE
   SYNTAX      Integer32
   MAX-ACCESS  read-only
   STATUS      current
   DESCRIPTION
       "The current implementation only supports PTP version 2"
   ::= { sm24dp4xaPTPClockPortDataSetConfEntry 14 }    
   
  
sm24dp4xaPTPClockUnicastSlaveConfTable OBJECT-TYPE
   SYNTAX      SEQUENCE OF SM24DP4XAPTPClockUnicastSlaveConfEntry
   MAX-ACCESS  not-accessible
   STATUS      current
   DESCRIPTION
       " "
   ::= { sm24dp4xaPTP 9 }

sm24dp4xaPTPClockUnicastSlaveConfEntry OBJECT-TYPE
   SYNTAX      SM24DP4XAPTPClockUnicastSlaveConfEntry
   MAX-ACCESS  not-accessible
   STATUS      current
   DESCRIPTION
       " "
   INDEX    { sm24dp4xaPTPClockConfEntryUnicastSlaveConfIndex  }
   ::= { sm24dp4xaPTPClockUnicastSlaveConfTable 1 }

SM24DP4XAPTPClockUnicastSlaveConfEntry ::= SEQUENCE {
   sm24dp4xaPTPClockConfEntryUnicastSlaveConfIndex              Integer32,
   sm24dp4xaPTPClockConfEntryUnicastSlaveConfDuration           Integer32,
   sm24dp4xaPTPClockConfEntryUnicastSlaveConfIPAddress          IpAddress,
   sm24dp4xaPTPClockConfEntryUnicastSlaveConfGrant              Integer32,
   sm24dp4xaPTPClockConfEntryUnicastSlaveConfCommState          DisplayString
}

sm24dp4xaPTPClockConfEntryUnicastSlaveConfIndex OBJECT-TYPE
   SYNTAX      Integer32 (1..65535)
   MAX-ACCESS  not-accessible
   STATUS      current
   DESCRIPTION
       "Index"
   ::= { sm24dp4xaPTPClockUnicastSlaveConfEntry 1 }

sm24dp4xaPTPClockConfEntryUnicastSlaveConfDuration OBJECT-TYPE
   SYNTAX      Integer32
   MAX-ACCESS  read-write
   STATUS      current
   DESCRIPTION
       "The number of seconds a master is requested to send Announce/Sync messages. 
	   The request is repeated from the slave each Duration/4 seconds.
	   range:10-1000"
   ::= { sm24dp4xaPTPClockUnicastSlaveConfEntry 2 }
      
sm24dp4xaPTPClockConfEntryUnicastSlaveConfIPAddress OBJECT-TYPE
   SYNTAX      IpAddress
   MAX-ACCESS  read-write
   STATUS      current
   DESCRIPTION
       "IPv4 Address of the Master clock"
   ::= { sm24dp4xaPTPClockUnicastSlaveConfEntry 3 }
   
sm24dp4xaPTPClockConfEntryUnicastSlaveConfGrant OBJECT-TYPE
   SYNTAX      Integer32
   MAX-ACCESS  read-only
   STATUS      current
   DESCRIPTION
       "The granted repetition period for the sync message"
   ::= { sm24dp4xaPTPClockUnicastSlaveConfEntry 4 }   
   
sm24dp4xaPTPClockConfEntryUnicastSlaveConfCommState OBJECT-TYPE
   SYNTAX      DisplayString
   MAX-ACCESS  read-only
   STATUS      current
   DESCRIPTION
       "The state of the communication with the master, possible values are:
		IDLE : The entry is not in use.
		INIT : Announce is sent to the master (Waiting for a response).
		CONN : The master has responded.
		SELL : The assigned master is selected as current master.
		SYNC : The master is sending Sync messages."
   ::= { sm24dp4xaPTPClockUnicastSlaveConfEntry 5 }   

sm24dp4xaETHLINKOAM    OBJECT IDENTIFIER ::= { sm24dp4xaConfiguration 29 } 

sm24dp4xaEthLinkOAMPortConfTable OBJECT-TYPE
   SYNTAX      SEQUENCE OF SM24DP4XAEthLinkOAMPortConfEntry
   MAX-ACCESS  not-accessible
   STATUS      current
   DESCRIPTION
       " "
   ::= { sm24dp4xaETHLINKOAM 1 }

sm24dp4xaEthLinkOAMPortConfEntry OBJECT-TYPE
   SYNTAX      SM24DP4XAEthLinkOAMPortConfEntry
   MAX-ACCESS  not-accessible
   STATUS      current
   DESCRIPTION
       " "
   INDEX    { sm24dp4xaEthLinkOAMPortConfIndex  }
   ::= { sm24dp4xaEthLinkOAMPortConfTable 1 }

SM24DP4XAEthLinkOAMPortConfEntry ::= SEQUENCE {
   sm24dp4xaEthLinkOAMPortConfIndex               Integer32,
   sm24dp4xaEthLinkOAMPortConfOAMEnable           Integer32,
   sm24dp4xaEthLinkOAMPortConfOAMMode             Integer32,
   sm24dp4xaEthLinkOAMPortConfLoopbackSupport     Integer32,
   sm24dp4xaEthLinkOAMPortConfLinkMonitorSupport  Integer32,
   sm24dp4xaEthLinkOAMPortConfMIBRetrievalSupport Integer32,
   sm24dp4xaEthLinkOAMPortConfLoopbackOperation   Integer32
}

sm24dp4xaEthLinkOAMPortConfIndex OBJECT-TYPE
   SYNTAX      Integer32 (1..65535)
   MAX-ACCESS  not-accessible
   STATUS      current
   DESCRIPTION
       "Index"
   ::= { sm24dp4xaEthLinkOAMPortConfEntry 1 }

sm24dp4xaEthLinkOAMPortConfOAMEnable OBJECT-TYPE
   SYNTAX      Integer32
   MAX-ACCESS  read-write
   STATUS      current
   DESCRIPTION
       "Controls whether Link OAM is enabled on this switch port. 
	   Enabling Link OAM provides the network operators the ability to monitor the health of the network and 
	   quickly determine the location of failing links or fault conditions.
	   0:disable
	   1:enable"
   ::= { sm24dp4xaEthLinkOAMPortConfEntry 2 }
   
sm24dp4xaEthLinkOAMPortConfOAMMode OBJECT-TYPE
   SYNTAX      Integer32
   MAX-ACCESS  read-write
   STATUS      current
   DESCRIPTION
       "Configures the OAM Mode as Active or Passive. The default mode is Passive.
	   0:Passive mode
	   1:Active mode"
   ::= { sm24dp4xaEthLinkOAMPortConfEntry 3 }   
   
sm24dp4xaEthLinkOAMPortConfLoopbackSupport OBJECT-TYPE
   SYNTAX      Integer32
   MAX-ACCESS  read-write
   STATUS      current
   DESCRIPTION
       "Controls whether the loopback support is enabled for the switch port. 
	   0:disable
	   1:enable"
   ::= { sm24dp4xaEthLinkOAMPortConfEntry 4 }     
   
sm24dp4xaEthLinkOAMPortConfLinkMonitorSupport OBJECT-TYPE
   SYNTAX      Integer32
   MAX-ACCESS  read-write
   STATUS      current
   DESCRIPTION
       "Controls whether the Link Monitor support is enabled for the switch port.
	   0:disable
	   1:enable"
   ::= { sm24dp4xaEthLinkOAMPortConfEntry 5 }

sm24dp4xaEthLinkOAMPortConfMIBRetrievalSupport OBJECT-TYPE
   SYNTAX      Integer32
   MAX-ACCESS  read-write
   STATUS      current
   DESCRIPTION
       "Controls whether the MIB Retrieval Support is enabled for the switch port. 
	   0:disable
	   1:enable"
   ::= { sm24dp4xaEthLinkOAMPortConfEntry 6 }    
   
sm24dp4xaEthLinkOAMPortConfLoopbackOperation OBJECT-TYPE
   SYNTAX      Integer32
   MAX-ACCESS  read-write
   STATUS      current
   DESCRIPTION
       "If the Loopback support is enabled, enabling this field will start a loopback operation for the port.
	   0:disable
	   1:enable"
   ::= { sm24dp4xaEthLinkOAMPortConfEntry 7 }       
   
   
   
sm24dp4xaEthLinkOAMPortDetailStatusTable OBJECT-TYPE
   SYNTAX      SEQUENCE OF SM24DP4XAEthLinkOAMPortDetailStatusEntry
   MAX-ACCESS  not-accessible
   STATUS      current
   DESCRIPTION
       "Eth Link OAM Port Detail Status table"
   ::= { sm24dp4xaETHLINKOAM 2 }

sm24dp4xaEthLinkOAMPortDetailStatusEntry OBJECT-TYPE
   SYNTAX      SM24DP4XAEthLinkOAMPortDetailStatusEntry
   MAX-ACCESS  not-accessible
   STATUS      current
   DESCRIPTION
       "Eth Link OAM Port Detail Status entry"
   INDEX    { sm24dp4xaEthLinkOAMPortDetailStatusIndex  }
   ::= { sm24dp4xaEthLinkOAMPortDetailStatusTable 1 }

SM24DP4XAEthLinkOAMPortDetailStatusEntry ::= SEQUENCE {
   sm24dp4xaEthLinkOAMPortDetailStatusIndex                       Integer32,
   sm24dp4xaEthLinkOAMPortPDUPermission                           DisplayString,
   sm24dp4xaEthLinkOAMPortDiscoveryState                          DisplayString,
   sm24dp4xaEthLinkOAMPortPeerMACAddress                          DisplayString,
   sm24dp4xaEthLinkOAMPortLocalMode                               DisplayString,
   sm24dp4xaEthLinkOAMPortLocalUnidirectOperSupport               DisplayString,
   sm24dp4xaEthLinkOAMPortLocalRemoteLoopbackSupport              DisplayString,
   sm24dp4xaEthLinkOAMPortLocalLinkMonitoringSupport              DisplayString,
   sm24dp4xaEthLinkOAMPortLocalMIBRetrievalSupport                DisplayString,
   sm24dp4xaEthLinkOAMPortLocalMTUSize                            Integer32,  
   sm24dp4xaEthLinkOAMPortLocalMultiplexerState                   DisplayString,  
   sm24dp4xaEthLinkOAMPortLocalParserState                        DisplayString,  
   sm24dp4xaEthLinkOAMPortLocalOrganUniqueIdent                   DisplayString,
   sm24dp4xaEthLinkOAMPortLocalPDURevision                        Integer32,  
   sm24dp4xaEthLinkOAMPortPeerMode                                DisplayString,  
   sm24dp4xaEthLinkOAMPortPeerUnidirectOperSupport                DisplayString,
   sm24dp4xaEthLinkOAMPortPeerRemoteLoopbackSupport               DisplayString,  
   sm24dp4xaEthLinkOAMPortPeerLinkMonitoringSupport               DisplayString,  
   sm24dp4xaEthLinkOAMPortPeerMIBRetrievalSupport                 DisplayString,  
   sm24dp4xaEthLinkOAMPortPeerMTUSize                             DisplayString,  
   sm24dp4xaEthLinkOAMPortPeerMultiplexerState                    DisplayString,  
   sm24dp4xaEthLinkOAMPortPeerParserState                         DisplayString,  
   sm24dp4xaEthLinkOAMPortPeerOrganUniqueIdent                    DisplayString,
   sm24dp4xaEthLinkOAMPortPDURevision                             DisplayString     
}

sm24dp4xaEthLinkOAMPortDetailStatusIndex OBJECT-TYPE
   SYNTAX      Integer32 (1..65535)
   MAX-ACCESS  not-accessible
   STATUS      current
   DESCRIPTION
       "Index"
   ::= { sm24dp4xaEthLinkOAMPortDetailStatusEntry 1 }

sm24dp4xaEthLinkOAMPortPDUPermission OBJECT-TYPE
   SYNTAX      DisplayString
   MAX-ACCESS  read-only
   STATUS      current
   DESCRIPTION
       "This field is available only for the Local DTE. 
	   It displays the current permission rules set for the local DTE. 
	   Possible values are Link fault, Receive only, Information exchange only, ANY."
   ::= { sm24dp4xaEthLinkOAMPortDetailStatusEntry 2 }
   
sm24dp4xaEthLinkOAMPortDiscoveryState OBJECT-TYPE
   SYNTAX      DisplayString
   MAX-ACCESS  read-only
   STATUS      current
   DESCRIPTION
       "Displays the current state of the discovery process. 
	   Possible states are Fault state, Active state, Passive state, 
	   SEND_LOCAL_REMOTE_STATE, SEND_LOCAL_REMOTE_OK_STATE, SEND_ANY_STATE."
   ::= { sm24dp4xaEthLinkOAMPortDetailStatusEntry 3 }   
   
sm24dp4xaEthLinkOAMPortPeerMACAddress OBJECT-TYPE
   SYNTAX      DisplayString
   MAX-ACCESS  read-only
   STATUS      current
   DESCRIPTION
       " "
   ::= { sm24dp4xaEthLinkOAMPortDetailStatusEntry 4 }     
   
sm24dp4xaEthLinkOAMPortLocalMode OBJECT-TYPE
   SYNTAX      DisplayString
   MAX-ACCESS  read-only
   STATUS      current
   DESCRIPTION
       "The Mode in which the Link OAM is operating, Active or Passive."
   ::= { sm24dp4xaEthLinkOAMPortDetailStatusEntry 5 }

sm24dp4xaEthLinkOAMPortLocalUnidirectOperSupport OBJECT-TYPE
   SYNTAX      DisplayString
   MAX-ACCESS  read-only
   STATUS      current
   DESCRIPTION
       "This feature is not available to be configured by the user. The status of this configuration is retrieved from the PHY."
   ::= { sm24dp4xaEthLinkOAMPortDetailStatusEntry 6 }    
   
sm24dp4xaEthLinkOAMPortLocalRemoteLoopbackSupport OBJECT-TYPE
   SYNTAX      DisplayString
   MAX-ACCESS  read-only
   STATUS      current
   DESCRIPTION
       "If status is enabled, DTE is capable of OAM remote loopback mode."
   ::= { sm24dp4xaEthLinkOAMPortDetailStatusEntry 7 }       
   
sm24dp4xaEthLinkOAMPortLocalLinkMonitoringSupport OBJECT-TYPE
   SYNTAX      DisplayString
   MAX-ACCESS  read-only
   STATUS      current
   DESCRIPTION
       "If status is enabled, DTE supports interpreting Link Events."
   ::= { sm24dp4xaEthLinkOAMPortDetailStatusEntry 8 }   

sm24dp4xaEthLinkOAMPortLocalMIBRetrievalSupport OBJECT-TYPE
   SYNTAX      DisplayString
   MAX-ACCESS  read-only
   STATUS      current
   DESCRIPTION
       "If status ie enabled DTE supports sending Variable Response OAMPDUs."
   ::= { sm24dp4xaEthLinkOAMPortDetailStatusEntry 9 }   

sm24dp4xaEthLinkOAMPortLocalMTUSize OBJECT-TYPE
   SYNTAX      Integer32
   MAX-ACCESS  read-only
   STATUS      current
   DESCRIPTION
       "It represents the largest OAMPDU, in octets, supported by the DTE. 
	   This value is compared to the remotes Maximum PDU Size and the smaller of the two is used."
   ::= { sm24dp4xaEthLinkOAMPortDetailStatusEntry 10 }   
   
sm24dp4xaEthLinkOAMPortLocalMultiplexerState OBJECT-TYPE
   SYNTAX      DisplayString
   MAX-ACCESS  read-only
   STATUS      current
   DESCRIPTION
       "When in forwarding state, the Device is forwarding non-OAMPDUs to the lower sublayer. 
	   Incase of discarding, the device discards all the non-OAMPDU's."
   ::= { sm24dp4xaEthLinkOAMPortDetailStatusEntry 11 }  
   
sm24dp4xaEthLinkOAMPortLocalParserState OBJECT-TYPE
   SYNTAX      DisplayString
   MAX-ACCESS  read-only
   STATUS      current
   DESCRIPTION
       "When in forwarding state, Device is forwarding non-OAMPDUs to higher sublayer. 
	   When in loopback, Device is looping back non-OAMPDUs to the lower sublayer. 
	   When in discarding state, Device is discarding non-OAMPDUs."
   ::= { sm24dp4xaEthLinkOAMPortDetailStatusEntry 12 }  
   
sm24dp4xaEthLinkOAMPortLocalOrganUniqueIdent OBJECT-TYPE
   SYNTAX      DisplayString
   MAX-ACCESS  read-only
   STATUS      current
   DESCRIPTION
       "24-bit Organizationally Unique Identifier of the vendor."
   ::= { sm24dp4xaEthLinkOAMPortDetailStatusEntry 13 }   
   
sm24dp4xaEthLinkOAMPortLocalPDURevision OBJECT-TYPE
   SYNTAX      Integer32
   MAX-ACCESS  read-only
   STATUS      current
   DESCRIPTION
       "It indicates the current revision of the Information TLV. 
	   The value of this field shall start at zero and be incremented each time something in the Information TLV changes. 
	   Upon reception of an Information TLV from a peer, an OAM client may use this field to decide if it needs to be processed 
	   (an Information TLV that is identical to the previous Information TLV doesn't need to be parsed as nothing in it has changed)."
   ::= { sm24dp4xaEthLinkOAMPortDetailStatusEntry 14 } 
   
sm24dp4xaEthLinkOAMPortPeerMode OBJECT-TYPE
   SYNTAX      DisplayString
   MAX-ACCESS  read-only
   STATUS      current
   DESCRIPTION
       "The Mode in which the Link OAM is operating, Active or Passive."
   ::= { sm24dp4xaEthLinkOAMPortDetailStatusEntry 15 }  
   
sm24dp4xaEthLinkOAMPortPeerUnidirectOperSupport OBJECT-TYPE
   SYNTAX      DisplayString
   MAX-ACCESS  read-only
   STATUS      current
   DESCRIPTION
       "This feature is not available to be configured by the user. 
	   The status of this configuration is retrieved from the PHY."
   ::= { sm24dp4xaEthLinkOAMPortDetailStatusEntry 16 } 
   
sm24dp4xaEthLinkOAMPortPeerRemoteLoopbackSupport OBJECT-TYPE
   SYNTAX      DisplayString
   MAX-ACCESS  read-only
   STATUS      current
   DESCRIPTION
       "If status is enabled, DTE is capable of OAM remote loopback mode."
   ::= { sm24dp4xaEthLinkOAMPortDetailStatusEntry 17 } 
   
sm24dp4xaEthLinkOAMPortPeerLinkMonitoringSupport OBJECT-TYPE
   SYNTAX      DisplayString
   MAX-ACCESS  read-only
   STATUS      current
   DESCRIPTION
       "If status is enabled, DTE supports interpreting Link Events."
   ::= { sm24dp4xaEthLinkOAMPortDetailStatusEntry 18 } 
   
sm24dp4xaEthLinkOAMPortPeerMIBRetrievalSupport OBJECT-TYPE
   SYNTAX      DisplayString
   MAX-ACCESS  read-only
   STATUS      current
   DESCRIPTION
       "If status ie enabled DTE supports sending Variable Response OAMPDUs."
   ::= { sm24dp4xaEthLinkOAMPortDetailStatusEntry 19 } 
   
sm24dp4xaEthLinkOAMPortPeerMTUSize OBJECT-TYPE
   SYNTAX      DisplayString
   MAX-ACCESS  read-only
   STATUS      current
   DESCRIPTION
       "It represents the largest OAMPDU, in octets, supported by the DTE. 
	   This value is compared to the remotes Maximum PDU Size and the smaller of the two is used."
   ::= { sm24dp4xaEthLinkOAMPortDetailStatusEntry 20 } 
   
sm24dp4xaEthLinkOAMPortPeerMultiplexerState OBJECT-TYPE
   SYNTAX      DisplayString
   MAX-ACCESS  read-only
   STATUS      current
   DESCRIPTION
       "When in forwarding state, the Device is forwarding non-OAMPDUs to the lower sublayer. 
	   Incase of discarding, the device discards all the non-OAMPDU's."
   ::= { sm24dp4xaEthLinkOAMPortDetailStatusEntry 21 } 
   
sm24dp4xaEthLinkOAMPortPeerParserState OBJECT-TYPE
   SYNTAX      DisplayString
   MAX-ACCESS  read-only
   STATUS      current
   DESCRIPTION
       "When in forwarding state, Device is forwarding non-OAMPDUs to higher sublayer. 
	   When in loopback, Device is looping back non-OAMPDUs to the lower sublayer. 
	   When in discarding state, Device is discarding non-OAMPDUs."
   ::= { sm24dp4xaEthLinkOAMPortDetailStatusEntry 22 } 
   
sm24dp4xaEthLinkOAMPortPeerOrganUniqueIdent OBJECT-TYPE
   SYNTAX      DisplayString
   MAX-ACCESS  read-only
   STATUS      current
   DESCRIPTION
       "24-bit Organizationally Unique Identifier of the vendor."
   ::= { sm24dp4xaEthLinkOAMPortDetailStatusEntry 23 }      
   
sm24dp4xaEthLinkOAMPortPDURevision                              OBJECT-TYPE
   SYNTAX      DisplayString
   MAX-ACCESS  read-only
   STATUS      current
   DESCRIPTION
       "It indicates the current revision of the Information TLV. 
	   The value of this field shall start at zero and be incremented each time something in the Information TLV changes. 
	   Upon reception of an Information TLV from a peer, an OAM client may use this field to decide if it needs to be processed 
	   (an Information TLV that is identical to the previous Information TLV doesn't need to be parsed as nothing in it has changed)."
   ::= { sm24dp4xaEthLinkOAMPortDetailStatusEntry 24 }   


sm24dp4xaEthLinkOAMPortLinkEventConfTable OBJECT-TYPE
   SYNTAX      SEQUENCE OF SM24DP4XAEthLinkOAMPortLinkEventConfEntry
   MAX-ACCESS  not-accessible
   STATUS      current
   DESCRIPTION
       "Eth Link OAM Port Link Event Conf Table"
   ::= { sm24dp4xaETHLINKOAM 3 }

sm24dp4xaEthLinkOAMPortLinkEventConfEntry OBJECT-TYPE
   SYNTAX      SM24DP4XAEthLinkOAMPortLinkEventConfEntry
   MAX-ACCESS  not-accessible
   STATUS      current
   DESCRIPTION
       "Eth Link OAM Port Link Event Conf Entry"
   INDEX    { sm24dp4xaPortLinkEvtConfIndex  }
   ::= { sm24dp4xaEthLinkOAMPortLinkEventConfTable 1 }

SM24DP4XAEthLinkOAMPortLinkEventConfEntry ::= SEQUENCE {
   sm24dp4xaPortLinkEvtConfIndex                               Integer32,
   sm24dp4xaPortLinkEvtConfErrFrameEvtErrWindow                Integer32,
   sm24dp4xaPortLinkEvtConfErrFrameEvtErrThreshold             Integer32,
   sm24dp4xaPortLinkEvtConfSymbolPeriErrEvtErrWindow           Integer32,
   sm24dp4xaPortLinkEvtConfSymbolPeriErrEvtErrThreshold        Integer32,
   sm24dp4xaPortLinkEvtConfSecSummEvtErrWindow                 Integer32,
   sm24dp4xaPortLinkEvtConfSecSummEvtErrThreshold              Integer32
}

sm24dp4xaPortLinkEvtConfIndex OBJECT-TYPE
   SYNTAX      Integer32 (1..65535)
   MAX-ACCESS  not-accessible
   STATUS      current
   DESCRIPTION
       "Index"
   ::= { sm24dp4xaEthLinkOAMPortLinkEventConfEntry 1 }

sm24dp4xaPortLinkEvtConfErrFrameEvtErrWindow OBJECT-TYPE
   SYNTAX      Integer32
   MAX-ACCESS  read-write
   STATUS      current
   DESCRIPTION
       "The Errored Frame Event counts the number of errored frames detected during the specified period. 
	   Represents the window period in the order of 1 sec for the observation of various link events.
	   range: 1-60"
   ::= { sm24dp4xaEthLinkOAMPortLinkEventConfEntry 2 }
   
sm24dp4xaPortLinkEvtConfErrFrameEvtErrThreshold OBJECT-TYPE
   SYNTAX      Integer32
   MAX-ACCESS  read-write
   STATUS      current
   DESCRIPTION
       "The Errored Frame Event counts the number of errored frames detected during the specified period. 
	   Represents the threshold value for the window period for the appropriate Link event so as to notify the peer of this error.
	   range:0-0xffffffff"
   ::= { sm24dp4xaEthLinkOAMPortLinkEventConfEntry 3 }
   
sm24dp4xaPortLinkEvtConfSymbolPeriErrEvtErrWindow OBJECT-TYPE
   SYNTAX      Integer32
   MAX-ACCESS  read-write
   STATUS      current
   DESCRIPTION
       "The Errored Symbol Period Event counts the number of symbol errors that occurred during the specified period.
	   Represents the window period in the order of 1 sec for the observation of various link events.
	   range: 1-60"
   ::= { sm24dp4xaEthLinkOAMPortLinkEventConfEntry 4 }

sm24dp4xaPortLinkEvtConfSymbolPeriErrEvtErrThreshold OBJECT-TYPE
   SYNTAX      Integer32
   MAX-ACCESS  read-write
   STATUS      current
   DESCRIPTION
       "The Errored Symbol Period Event counts the number of symbol errors that occurred during the specified period.
	   Represents the threshold value for the window period for the appropriate Link event so as to notify the peer of this error.
	   range:0-0xffffffff"
   ::= { sm24dp4xaEthLinkOAMPortLinkEventConfEntry 5 }

sm24dp4xaPortLinkEvtConfSecSummEvtErrWindow OBJECT-TYPE
   SYNTAX      Integer32
   MAX-ACCESS  read-write
   STATUS      current
   DESCRIPTION
       "The Errored Frame Seconds Summary Event TLV counts the number of errored frame seconds that occurred during the specified period. 
	   Represents the window period in the order of 1 sec for the observation of various link events.
	   range: 10-900"
   ::= { sm24dp4xaEthLinkOAMPortLinkEventConfEntry 6 }   
   
sm24dp4xaPortLinkEvtConfSecSummEvtErrThreshold OBJECT-TYPE
   SYNTAX      Integer32
   MAX-ACCESS  read-write
   STATUS      current
   DESCRIPTION
       "The Errored Frame Seconds Summary Event TLV counts the number of errored frame seconds that occurred during the specified period. 
	   Represents the threshold value for the window period for the appropriate Link event so as to notify the peer of this error.
	   range:0-0xffff"
   ::= { sm24dp4xaEthLinkOAMPortLinkEventConfEntry 7 } 




sm24dp4xaEthLinkOAMPortDetailedStatisticsTable OBJECT-TYPE
   SYNTAX      SEQUENCE OF SM24DP4XAEthLinkOAMPortDetailedStatisticsEntry
   MAX-ACCESS  not-accessible
   STATUS      current
   DESCRIPTION
       "Eth Link OAM Port Detailed Statistics Table"
   ::= { sm24dp4xaETHLINKOAM 4 }

sm24dp4xaEthLinkOAMPortDetailedStatisticsEntry OBJECT-TYPE
   SYNTAX      SM24DP4XAEthLinkOAMPortDetailedStatisticsEntry
   MAX-ACCESS  not-accessible
   STATUS      current
   DESCRIPTION
       "Eth Link OAM Port Detailed Statistics Entry"
   INDEX    { sm24dp4xaPortDetailedStatisticsIndex  }
   ::= { sm24dp4xaEthLinkOAMPortDetailedStatisticsTable 1 }

SM24DP4XAEthLinkOAMPortDetailedStatisticsEntry ::= SEQUENCE {
   sm24dp4xaPortDetailedStatisticsIndex                             Integer32,
   sm24dp4xaPortDetailedStatisticsRxOAMInfoPDUs                     Integer32,
   sm24dp4xaPortDetailedStatisticsRxUniqueErrEvtNotif               Integer32,
   sm24dp4xaPortDetailedStatisticsRxDupErrEvtNotif                  Integer32,
   sm24dp4xaPortDetailedStatisticsRxLoopbackControl                 Integer32,
   sm24dp4xaPortDetailedStatisticsRxVariableRequest                 Integer32,
   sm24dp4xaPortDetailedStatisticsRxVariableResponse                Integer32,
   sm24dp4xaPortDetailedStatisticsRxOrgSpecificPDUs                 Integer32,
   sm24dp4xaPortDetailedStatisticsRxUnsupportedCodes                Integer32,
   sm24dp4xaPortDetailedStatisticsRxLinkFaultPDUs                   Integer32,
   sm24dp4xaPortDetailedStatisticsRxDyingGasp                       Integer32,
   sm24dp4xaPortDetailedStatisticsRxCriticalEvtPDUs                 Integer32,
   sm24dp4xaPortDetailedStatisticsTxOAMInfoPDUs                     Integer32,
   sm24dp4xaPortDetailedStatisticsTxUniqueErrEvtNotif               Integer32,
   sm24dp4xaPortDetailedStatisticsTxDupErrEvtNotif                  Integer32,
   sm24dp4xaPortDetailedStatisticsTxLoopbackControl                 Integer32,
   sm24dp4xaPortDetailedStatisticsTxVariableRequest                 Integer32,
   sm24dp4xaPortDetailedStatisticsTxVariableResponse                Integer32,
   sm24dp4xaPortDetailedStatisticsTxOrgSpecificPDUs                 Integer32,
   sm24dp4xaPortDetailedStatisticsTxUnsupportedCodes                Integer32,
   sm24dp4xaPortDetailedStatisticsTxLinkFaultPDUs                   Integer32,
   sm24dp4xaPortDetailedStatisticsTxDyingGasp                       Integer32,
   sm24dp4xaPortDetailedStatisticsTxCriticalEvtPDUs                 Integer32,
   sm24dp4xaPortDetailedStatisticsClear                             Integer32
}

sm24dp4xaPortDetailedStatisticsIndex OBJECT-TYPE
   SYNTAX      Integer32 (1..65535)
   MAX-ACCESS  not-accessible
   STATUS      current
   DESCRIPTION
       "Index"
   ::= { sm24dp4xaEthLinkOAMPortDetailedStatisticsEntry 1 }

sm24dp4xaPortDetailedStatisticsRxOAMInfoPDUs OBJECT-TYPE
   SYNTAX      Integer32
   MAX-ACCESS  read-only
   STATUS      current
   DESCRIPTION
       "The number of received and transmitted OAM Information PDU's. 
	   Discontinuities of this counter can occur at re-initialization of the management system."
   ::= { sm24dp4xaEthLinkOAMPortDetailedStatisticsEntry 2 }
   
sm24dp4xaPortDetailedStatisticsRxUniqueErrEvtNotif OBJECT-TYPE
   SYNTAX      Integer32
   MAX-ACCESS  read-only
   STATUS      current
   DESCRIPTION
       "A count of the number of unique Event OAMPDUs received and transmitted on this interface. 
	   Event Notifications may be sent in duplicate to increase the probability of successfully being received, 
	   given the possibility that a frame may be lost in transit. 
	   Duplicate Event Notification transmissions are counted by 
	   Duplicate Event Notification counters for Tx and Rx respectively. 
	   A unique Event Notification OAMPDU is indicated as an Event Notification OAMPDU with
	   a Sequence Number field that is distinct from the previously transmitted Event Notification OAMPDU Sequence Number."
   ::= { sm24dp4xaEthLinkOAMPortDetailedStatisticsEntry 3 }
   
sm24dp4xaPortDetailedStatisticsRxDupErrEvtNotif OBJECT-TYPE
   SYNTAX      Integer32
   MAX-ACCESS  read-only
   STATUS      current
   DESCRIPTION
       "A count of the number of duplicate Event OAMPDUs received and transmitted on this interface. 
	   Event Notification OAMPDUs may be sent in duplicate to increase the probability of successfully being received, 
	   given the possibility that a frame may be lost in transit. 
	   A duplicate Event Notification OAMPDU is indicated as an Event Notification OAMPDU with
	   a Sequence Number field that is identical to the previously transmitted Event Notification OAMPDU Sequence Number."
   ::= { sm24dp4xaEthLinkOAMPortDetailedStatisticsEntry 4 }
   
sm24dp4xaPortDetailedStatisticsRxLoopbackControl OBJECT-TYPE
   SYNTAX      Integer32
   MAX-ACCESS  read-only
   STATUS      current
   DESCRIPTION
       "A count of the number of Loopback Control OAMPDUs received and transmitted on this interface."
   ::= { sm24dp4xaEthLinkOAMPortDetailedStatisticsEntry 5 }
   
sm24dp4xaPortDetailedStatisticsRxVariableRequest OBJECT-TYPE
   SYNTAX      Integer32
   MAX-ACCESS  read-only
   STATUS      current
   DESCRIPTION
       "A count of the number of Variable Request OAMPDUs received and transmitted on this interface."
   ::= { sm24dp4xaEthLinkOAMPortDetailedStatisticsEntry 6 }
   
sm24dp4xaPortDetailedStatisticsRxVariableResponse OBJECT-TYPE
   SYNTAX      Integer32
   MAX-ACCESS  read-only
   STATUS      current
   DESCRIPTION
       "A count of the number of Variable Response OAMPDUs received and transmitted on this interface."
   ::= { sm24dp4xaEthLinkOAMPortDetailedStatisticsEntry 7 }
   
sm24dp4xaPortDetailedStatisticsRxOrgSpecificPDUs OBJECT-TYPE
   SYNTAX      Integer32
   MAX-ACCESS  read-only
   STATUS      current
   DESCRIPTION
       "A count of the number of Organization Specific OAMPDUs transmitted on this interface."
   ::= { sm24dp4xaEthLinkOAMPortDetailedStatisticsEntry 8 }
   
sm24dp4xaPortDetailedStatisticsRxUnsupportedCodes OBJECT-TYPE
   SYNTAX      Integer32
   MAX-ACCESS  read-only
   STATUS      current
   DESCRIPTION
       "A count of the number of OAMPDUs transmitted on this interface with an unsupported op-code."
   ::= { sm24dp4xaEthLinkOAMPortDetailedStatisticsEntry 9 }
   
sm24dp4xaPortDetailedStatisticsRxLinkFaultPDUs OBJECT-TYPE
   SYNTAX      Integer32
   MAX-ACCESS  read-only
   STATUS      current
   DESCRIPTION
       "A count of the number of Link fault PDU's received and transmitted on this interface."
   ::= { sm24dp4xaEthLinkOAMPortDetailedStatisticsEntry 10 }
   
sm24dp4xaPortDetailedStatisticsRxDyingGasp OBJECT-TYPE
   SYNTAX      Integer32
   MAX-ACCESS  read-only
   STATUS      current
   DESCRIPTION
       "A count of the number of Dying Gasp events received and transmitted on this interface."
   ::= { sm24dp4xaEthLinkOAMPortDetailedStatisticsEntry 11 }
   
sm24dp4xaPortDetailedStatisticsRxCriticalEvtPDUs OBJECT-TYPE
   SYNTAX      Integer32
   MAX-ACCESS  read-only
   STATUS      current
   DESCRIPTION
       "A count of the number of Critical event PDU's received and transmitted on this interface."
   ::= { sm24dp4xaEthLinkOAMPortDetailedStatisticsEntry 12 }
   
sm24dp4xaPortDetailedStatisticsTxOAMInfoPDUs OBJECT-TYPE
   SYNTAX      Integer32
   MAX-ACCESS  read-only
   STATUS      current
   DESCRIPTION
       "The number of received and transmitted OAM Information PDU's. 
	   Discontinuities of this counter can occur at re-initialization of the management system."
   ::= { sm24dp4xaEthLinkOAMPortDetailedStatisticsEntry 13 }
   
sm24dp4xaPortDetailedStatisticsTxUniqueErrEvtNotif OBJECT-TYPE
   SYNTAX      Integer32
   MAX-ACCESS  read-only
   STATUS      current
   DESCRIPTION
       "A count of the number of unique Event OAMPDUs received and transmitted on this interface. 
	   Event Notifications may be sent in duplicate to increase the probability of successfully being received, 
	   given the possibility that a frame may be lost in transit. 
	   Duplicate Event Notification transmissions are counted by 
	   Duplicate Event Notification counters for Tx and Rx respectively. 
	   A unique Event Notification OAMPDU is indicated as an Event Notification OAMPDU with
	   a Sequence Number field that is distinct from the previously transmitted Event Notification OAMPDU Sequence Number."
   ::= { sm24dp4xaEthLinkOAMPortDetailedStatisticsEntry 14 }
   
sm24dp4xaPortDetailedStatisticsTxDupErrEvtNotif OBJECT-TYPE
   SYNTAX      Integer32
   MAX-ACCESS  read-only
   STATUS      current
   DESCRIPTION
       "A count of the number of duplicate Event OAMPDUs received and transmitted on this interface. 
	   Event Notification OAMPDUs may be sent in duplicate to increase the probability of successfully being received, 
	   given the possibility that a frame may be lost in transit. 
	   A duplicate Event Notification OAMPDU is indicated as an Event Notification OAMPDU with
	   a Sequence Number field that is identical to the previously transmitted Event Notification OAMPDU Sequence Number."
   ::= { sm24dp4xaEthLinkOAMPortDetailedStatisticsEntry 15 }
   
sm24dp4xaPortDetailedStatisticsTxLoopbackControl OBJECT-TYPE
   SYNTAX      Integer32
   MAX-ACCESS  read-only
   STATUS      current
   DESCRIPTION
       "A count of the number of Loopback Control OAMPDUs received and transmitted on this interface."
   ::= { sm24dp4xaEthLinkOAMPortDetailedStatisticsEntry 16 }
   
sm24dp4xaPortDetailedStatisticsTxVariableRequest OBJECT-TYPE
   SYNTAX      Integer32
   MAX-ACCESS  read-only
   STATUS      current
   DESCRIPTION
       "A count of the number of Variable Request OAMPDUs received and transmitted on this interface."
   ::= { sm24dp4xaEthLinkOAMPortDetailedStatisticsEntry 17 }
   
sm24dp4xaPortDetailedStatisticsTxVariableResponse OBJECT-TYPE
   SYNTAX      Integer32
   MAX-ACCESS  read-only
   STATUS      current
   DESCRIPTION
       "A count of the number of Variable Response OAMPDUs received and transmitted on this interface."
   ::= { sm24dp4xaEthLinkOAMPortDetailedStatisticsEntry 18 }
   
sm24dp4xaPortDetailedStatisticsTxOrgSpecificPDUs OBJECT-TYPE
   SYNTAX      Integer32
   MAX-ACCESS  read-only
   STATUS      current
   DESCRIPTION
       "A count of the number of Organization Specific OAMPDUs transmitted on this interface."
   ::= { sm24dp4xaEthLinkOAMPortDetailedStatisticsEntry 19 }
   
sm24dp4xaPortDetailedStatisticsTxUnsupportedCodes OBJECT-TYPE
   SYNTAX      Integer32
   MAX-ACCESS  read-only
   STATUS      current
   DESCRIPTION
       "A count of the number of OAMPDUs transmitted on this interface with an unsupported op-code."
   ::= { sm24dp4xaEthLinkOAMPortDetailedStatisticsEntry 20 }
   
sm24dp4xaPortDetailedStatisticsTxLinkFaultPDUs OBJECT-TYPE
   SYNTAX      Integer32
   MAX-ACCESS  read-only
   STATUS      current
   DESCRIPTION
       "A count of the number of Link fault PDU's received and transmitted on this interface."
   ::= { sm24dp4xaEthLinkOAMPortDetailedStatisticsEntry 21 }
   
sm24dp4xaPortDetailedStatisticsTxDyingGasp OBJECT-TYPE
   SYNTAX      Integer32
   MAX-ACCESS  read-only
   STATUS      current
   DESCRIPTION
       "A count of the number of Dying Gasp events received and transmitted on this interface."
   ::= { sm24dp4xaEthLinkOAMPortDetailedStatisticsEntry 22 }
   
sm24dp4xaPortDetailedStatisticsTxCriticalEvtPDUs OBJECT-TYPE
   SYNTAX      Integer32
   MAX-ACCESS  read-only
   STATUS      current
   DESCRIPTION
       "A count of the number of Critical event PDU's received and transmitted on this interface."
   ::= { sm24dp4xaEthLinkOAMPortDetailedStatisticsEntry 23 }
   
sm24dp4xaPortDetailedStatisticsClear OBJECT-TYPE
   SYNTAX      Integer32
   MAX-ACCESS  read-write
   STATUS      current
   DESCRIPTION
       "Clears the counters for the selected port."
   ::= { sm24dp4xaEthLinkOAMPortDetailedStatisticsEntry 24 }
   
   
sm24dp4xaEthLinkOAMPortEventDetailedStatisticsTable OBJECT-TYPE
   SYNTAX      SEQUENCE OF SM24DP4XAEthLinkOAMPortEventDetailedStatisticsEntry
   MAX-ACCESS  not-accessible
   STATUS      current
   DESCRIPTION
       "Eth Link OAM Port Event Detailed Statistics Table"
   ::= { sm24dp4xaETHLINKOAM 5 }

sm24dp4xaEthLinkOAMPortEventDetailedStatisticsEntry OBJECT-TYPE
   SYNTAX      SM24DP4XAEthLinkOAMPortEventDetailedStatisticsEntry
   MAX-ACCESS  not-accessible
   STATUS      current
   DESCRIPTION
       "Eth Link OAM Port Event Detailed Statistics Entry"
   INDEX    { sm24dp4xaStatisticsIndex  }
   ::= { sm24dp4xaEthLinkOAMPortEventDetailedStatisticsTable 1 }

SM24DP4XAEthLinkOAMPortEventDetailedStatisticsEntry ::= SEQUENCE {
   sm24dp4xaStatisticsIndex                            Integer32,
   sm24dp4xaStatisticsLocalSequenceNumber              Integer32,
   sm24dp4xaStatisticsLocalFrameErrEvtTimestamp        Integer32,
   sm24dp4xaStatisticsLocalFrameErrEvtWindow           Integer32,
   sm24dp4xaStatisticsLocalFrameErrEvtThreshold        Integer32,
   sm24dp4xaStatisticsLocalFrameErrs                   Integer32,
   sm24dp4xaStatisticsLocalTotalFrameErrs              Counter64,
   sm24dp4xaStatisticsLocalTotalFrameErrEvts           Integer32,
   sm24dp4xaStatisticsLocalFramePeriErrEvtTimestamp    Integer32,
   sm24dp4xaStatisticsLocalFramePeriErrEvtWindow       Integer32,
   sm24dp4xaStatisticsLocalFramePeriErrEvtThreshold    Integer32,
   sm24dp4xaStatisticsLocalFramePeriErrs               Integer32,
   sm24dp4xaStatisticsLocalTotalFramePeriErrs          Counter64,
   sm24dp4xaStatisticsLocalTotalFramePeriErrEvts       Integer32,
   sm24dp4xaStatisticsLocalSymbolPeriErrEvtTimestamp   Integer32,
   sm24dp4xaStatisticsLocalSymbolPeriErrEvtWindow      Counter64,
   sm24dp4xaStatisticsLocalSymbolPeriErrEvtThreshold   Counter64,
   sm24dp4xaStatisticsLocalSymbolPeriErrs              Counter64,
   sm24dp4xaStatisticsLocalSymbolFramePeriErrs         Counter64,
   sm24dp4xaStatisticsLocalSymbolFramePeriErrEvts      Integer32,
   sm24dp4xaStatisticsLocalEvtSecondsSummTimeStamp     Integer32,
   sm24dp4xaStatisticsLocalEvtSecondsSummWindow        Integer32,
   sm24dp4xaStatisticsLocalEvtSecondsSummThreshold     Integer32,
   sm24dp4xaStatisticsLocalEvtSecondsSummEvts          Integer32,
   sm24dp4xaStatisticsLocalEvtSecondsSummErrTotal      Integer32,
   sm24dp4xaStatisticsLocalEvtSecondsSummEvtTotal      Integer32,
   sm24dp4xaStatisticsRemoteFrameErrEvtTimestamp       Integer32,
   sm24dp4xaStatisticsRemoteFrameErrEvtWindow          Integer32,
   sm24dp4xaStatisticsRemoteFrameErrEvtThreshold       Integer32,
   sm24dp4xaStatisticsRemoteFrameErrs                  Integer32,
   sm24dp4xaStatisticsRemoteTotalFrameErrs             Counter64,
   sm24dp4xaStatisticsRemoteTotalFrameErrEvts          Integer32,
   sm24dp4xaStatisticsRemoteFramePeriErrEvtTimestamp   Integer32,
   sm24dp4xaStatisticsRemoteFramePeriErrEvtWindow      Integer32,
   sm24dp4xaStatisticsRemoteFramePeriErrEvtThreshold   Integer32,
   sm24dp4xaStatisticsRemoteFramePeriErrs              Integer32,
   sm24dp4xaStatisticsRemoteTotalFramePeriErrs         Counter64,
   sm24dp4xaStatisticsRemoteTotalFramePeriErrEvts      Integer32,
   sm24dp4xaStatisticsRemoteSymbolPeriErrEvtTimestamp  Integer32,
   sm24dp4xaStatisticsRemoteSymbolPeriErrEvtWindow     Counter64,
   sm24dp4xaStatisticsRemoteSymbolPeriErrEvtThreshold  Counter64,
   sm24dp4xaStatisticsRemoteSymbolPeriErrs             Counter64,
   sm24dp4xaStatisticsRemoteSymbolFramePeriErrs        Counter64,
   sm24dp4xaStatisticsRemoteSymbolFramePeriErrEvts     Integer32,
   sm24dp4xaStatisticsRemoteEvtSecondsSummTimeStamp    Integer32,
   sm24dp4xaStatisticsRemoteEvtSecondsSummWindow       Integer32,
   sm24dp4xaStatisticsRemoteEvtSecondsSummThreshold    Integer32,
   sm24dp4xaStatisticsRemoteEvtSecondsSummEvts         Integer32,
   sm24dp4xaStatisticsRemoteEvtSecondsSummErrTotal     Integer32,
   sm24dp4xaStatisticsRemoteEvtSecondsSummEvtTotal     Integer32
}

sm24dp4xaStatisticsIndex OBJECT-TYPE
   SYNTAX      Integer32 (1..65535)
   MAX-ACCESS  not-accessible
   STATUS      current
   DESCRIPTION
       "Index"
   ::= { sm24dp4xaEthLinkOAMPortEventDetailedStatisticsEntry 1 }

sm24dp4xaStatisticsLocalSequenceNumber OBJECT-TYPE
   SYNTAX      Integer32
   MAX-ACCESS  read-only
   STATUS      current
   DESCRIPTION
       "This two-octet field indicates the total number of events occurred at the remote end."   
   ::= { sm24dp4xaEthLinkOAMPortEventDetailedStatisticsEntry 2 }
   
sm24dp4xaStatisticsLocalFrameErrEvtTimestamp OBJECT-TYPE
   SYNTAX      Integer32
   MAX-ACCESS  read-only
   STATUS      current
   DESCRIPTION
       "This two-octet field indicates the time reference when the event was generated, in terms of 100 ms intervals."   
   ::= { sm24dp4xaEthLinkOAMPortEventDetailedStatisticsEntry 3 }

sm24dp4xaStatisticsLocalFrameErrEvtWindow OBJECT-TYPE
   SYNTAX      Integer32
   MAX-ACCESS  read-only
   STATUS      current
   DESCRIPTION
       "This two-octet field indicates the duration of the period in terms of 100 ms intervals. 1) 
	   The default value is one second. 2) The lower bound is one second. 3) 
	   The upper bound is one minute."   
   ::= { sm24dp4xaEthLinkOAMPortEventDetailedStatisticsEntry 4 }

sm24dp4xaStatisticsLocalFrameErrEvtThreshold OBJECT-TYPE
   SYNTAX      Integer32
   MAX-ACCESS  read-only
   STATUS      current
   DESCRIPTION
       "This four-octet field indicates the number of detected errored frames in the period is required
	   to be equal to or greater than in order for the event to be generated. 1) 
	   The default value is one frame error. 2) 
	   The lower bound is zero frame errors. 3) 
	   The upper bound is unspecified."   
   ::= { sm24dp4xaEthLinkOAMPortEventDetailedStatisticsEntry 5 }

sm24dp4xaStatisticsLocalFrameErrs OBJECT-TYPE
   SYNTAX      Integer32
   MAX-ACCESS  read-only
   STATUS      current
   DESCRIPTION
       "This four-octet field indicates the number of detected errored frames in the period."   
   ::= { sm24dp4xaEthLinkOAMPortEventDetailedStatisticsEntry 6 }

sm24dp4xaStatisticsLocalTotalFrameErrs OBJECT-TYPE
   SYNTAX      Counter64
   MAX-ACCESS  read-only
   STATUS      current
   DESCRIPTION
       "This eight-octet field indicates the sum of errored frames that have been detected since the OAM sublayer was reset."   
   ::= { sm24dp4xaEthLinkOAMPortEventDetailedStatisticsEntry 7 }

sm24dp4xaStatisticsLocalTotalFrameErrEvts OBJECT-TYPE
   SYNTAX      Integer32
   MAX-ACCESS  read-only
   STATUS      current
   DESCRIPTION
       "This four-octet field indicates the number of Errored Frame Event TLVs that 
	   have been generated since the OAM sublayer was reset."   
   ::= { sm24dp4xaEthLinkOAMPortEventDetailedStatisticsEntry 8 }

sm24dp4xaStatisticsLocalFramePeriErrEvtTimestamp OBJECT-TYPE
   SYNTAX      Integer32
   MAX-ACCESS  read-only
   STATUS      current
   DESCRIPTION
       "This two-octet field indicates the time reference when the event was generated, in terms of 100 ms intervals."   
   ::= { sm24dp4xaEthLinkOAMPortEventDetailedStatisticsEntry 9 }

sm24dp4xaStatisticsLocalFramePeriErrEvtWindow OBJECT-TYPE
   SYNTAX      Integer32
   MAX-ACCESS  read-only
   STATUS      current
   DESCRIPTION
       "This four-octet field indicates the duration of period in terms of frames."   
   ::= { sm24dp4xaEthLinkOAMPortEventDetailedStatisticsEntry 10 }

sm24dp4xaStatisticsLocalFramePeriErrEvtThreshold OBJECT-TYPE
   SYNTAX      Integer32
   MAX-ACCESS  read-only
   STATUS      current
   DESCRIPTION
       "This four-octet field indicates the number of errored frames in the period is required
	   to be equal to or greater than in order for the event to be generated."   
   ::= { sm24dp4xaEthLinkOAMPortEventDetailedStatisticsEntry 11 }

sm24dp4xaStatisticsLocalFramePeriErrs OBJECT-TYPE
   SYNTAX      Integer32
   MAX-ACCESS  read-only
   STATUS      current
   DESCRIPTION
       "This four-octet field indicates the number of frame errors in the period."   
   ::= { sm24dp4xaEthLinkOAMPortEventDetailedStatisticsEntry 12 }

sm24dp4xaStatisticsLocalTotalFramePeriErrs OBJECT-TYPE
   SYNTAX      Counter64
   MAX-ACCESS  read-only
   STATUS      current
   DESCRIPTION
       "This eight-octet field indicates the sum of frame errors that have been detected since the OAM sublayer was reset."   
   ::= { sm24dp4xaEthLinkOAMPortEventDetailedStatisticsEntry 13 }

sm24dp4xaStatisticsLocalTotalFramePeriErrEvts OBJECT-TYPE
   SYNTAX      Integer32
   MAX-ACCESS  read-only
   STATUS      current
   DESCRIPTION
       "This four-octet field indicates the number of Errored Frame Period Event TLVs 
	   that have been generated since the OAM sublayer was reset."   
   ::= { sm24dp4xaEthLinkOAMPortEventDetailedStatisticsEntry 14 }

sm24dp4xaStatisticsLocalSymbolPeriErrEvtTimestamp OBJECT-TYPE
   SYNTAX      Integer32
   MAX-ACCESS  read-only
   STATUS      current
   DESCRIPTION
       "This two-octet field indicates the time reference when the event was generated, in terms of 100 ms intervals."   
   ::= { sm24dp4xaEthLinkOAMPortEventDetailedStatisticsEntry 15 }

sm24dp4xaStatisticsLocalSymbolPeriErrEvtWindow OBJECT-TYPE
   SYNTAX      Counter64
   MAX-ACCESS  read-only
   STATUS      current
   DESCRIPTION
       "This eight-octet field indicates the number of symbols in the period."   
   ::= { sm24dp4xaEthLinkOAMPortEventDetailedStatisticsEntry 16 }

sm24dp4xaStatisticsLocalSymbolPeriErrEvtThreshold OBJECT-TYPE
   SYNTAX      Counter64
   MAX-ACCESS  read-only
   STATUS      current
   DESCRIPTION
       "This eight-octet field indicates the number of errored symbols in the period is required to
	   be equal to or greater than in order for the event to be generated."   
   ::= { sm24dp4xaEthLinkOAMPortEventDetailedStatisticsEntry 17 }

sm24dp4xaStatisticsLocalSymbolPeriErrs OBJECT-TYPE
   SYNTAX      Counter64
   MAX-ACCESS  read-only
   STATUS      current
   DESCRIPTION
       "This eight-octet field indicates the number of symbol errors in the period."   
   ::= { sm24dp4xaEthLinkOAMPortEventDetailedStatisticsEntry 18 }

sm24dp4xaStatisticsLocalSymbolFramePeriErrs OBJECT-TYPE
   SYNTAX      Counter64
   MAX-ACCESS  read-only
   STATUS      current
   DESCRIPTION
       "This eight-octet field indicates the sum of symbol errors since the OAM sublayer was reset."   
   ::= { sm24dp4xaEthLinkOAMPortEventDetailedStatisticsEntry 19 }

sm24dp4xaStatisticsLocalSymbolFramePeriErrEvts OBJECT-TYPE
   SYNTAX      Integer32
   MAX-ACCESS  read-only
   STATUS      current
   DESCRIPTION
       "This four-octet field indicates the number of Errored Symbol Period Event TLVs that
	   have been generated since the OAM sublayer was reset."   
   ::= { sm24dp4xaEthLinkOAMPortEventDetailedStatisticsEntry 20 }

sm24dp4xaStatisticsLocalEvtSecondsSummTimeStamp OBJECT-TYPE
   SYNTAX      Integer32
   MAX-ACCESS  read-only
   STATUS      current
   DESCRIPTION
       "This two-octet field indicates the time reference when the event was generated, 
	   in terms of 100 ms intervals, encoded as a 16-bit unsigned integer."   
   ::= { sm24dp4xaEthLinkOAMPortEventDetailedStatisticsEntry 21 }

sm24dp4xaStatisticsLocalEvtSecondsSummWindow OBJECT-TYPE
   SYNTAX      Integer32
   MAX-ACCESS  read-only
   STATUS      current
   DESCRIPTION
       "This two-octet field indicates the duration of the period in terms of 100 ms intervals, encoded as a 16-bit unsigned integer."   
   ::= { sm24dp4xaEthLinkOAMPortEventDetailedStatisticsEntry 22 }

sm24dp4xaStatisticsLocalEvtSecondsSummThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."   
   ::= { sm24dp4xaEthLinkOAMPortEventDetailedStatisticsEntry 23 }

sm24dp4xaStatisticsLocalEvtSecondsSummEvts OBJECT-TYPE
   SYNTAX      Integer32
   MAX-ACCESS  read-only
   STATUS      current
   DESCRIPTION
       "This two-octet field indicates the number of errored frame seconds in the period, encoded as a 16-bit unsigned integer."   
   ::= { sm24dp4xaEthLinkOAMPortEventDetailedStatisticsEntry 24 }

sm24dp4xaStatisticsLocalEvtSecondsSummErrTotal OBJECT-TYPE
   SYNTAX      Integer32
   MAX-ACCESS  read-only
   STATUS      current
   DESCRIPTION
       "This four-octet field indicates the sum of errored frame seconds that have been detected since the OAM sublayer was reset."   
   ::= { sm24dp4xaEthLinkOAMPortEventDetailedStatisticsEntry 25 }

sm24dp4xaStatisticsLocalEvtSecondsSummEvtTotal OBJECT-TYPE
   SYNTAX      Integer32
   MAX-ACCESS  read-only
   STATUS      current
   DESCRIPTION
       "This four-octet field indicates the number of Errored Frame Seconds Summary Event TLVs that 
	   have been generated since the OAM sublayer was reset, encoded as a 32bit unsigned integer."   
   ::= { sm24dp4xaEthLinkOAMPortEventDetailedStatisticsEntry 26 }

sm24dp4xaStatisticsRemoteFrameErrEvtTimestamp OBJECT-TYPE
   SYNTAX      Integer32
   MAX-ACCESS  read-only
   STATUS      current
   DESCRIPTION
       "This two-octet field indicates the time reference when the event was generated, in terms of 100 ms intervals."   
   ::= { sm24dp4xaEthLinkOAMPortEventDetailedStatisticsEntry 27 }
   
sm24dp4xaStatisticsRemoteFrameErrEvtWindow OBJECT-TYPE
   SYNTAX      Integer32
   MAX-ACCESS  read-only
   STATUS      current
   DESCRIPTION
       "This two-octet field indicates the duration of the period in terms of 100 ms intervals. 1) 
	   The default value is one second. 2) The lower bound is one second. 3) 
	   The upper bound is one minute."   
   ::= { sm24dp4xaEthLinkOAMPortEventDetailedStatisticsEntry 28 }   
   
sm24dp4xaStatisticsRemoteFrameErrEvtThreshold OBJECT-TYPE
   SYNTAX      Integer32
   MAX-ACCESS  read-only
   STATUS      current
   DESCRIPTION
       "This four-octet field indicates the number of detected errored frames in the period is required
	   to be equal to or greater than in order for the event to be generated. 1) 
	   The default value is one frame error. 2) 
	   The lower bound is zero frame errors. 3) 
	   The upper bound is unspecified."   
   ::= { sm24dp4xaEthLinkOAMPortEventDetailedStatisticsEntry 29 }

sm24dp4xaStatisticsRemoteFrameErrs OBJECT-TYPE
   SYNTAX      Integer32
   MAX-ACCESS  read-only
   STATUS      current
   DESCRIPTION
       "This four-octet field indicates the number of detected errored frames in the period."   
   ::= { sm24dp4xaEthLinkOAMPortEventDetailedStatisticsEntry 30 }
   
sm24dp4xaStatisticsRemoteTotalFrameErrs OBJECT-TYPE
   SYNTAX      Counter64
   MAX-ACCESS  read-only
   STATUS      current
   DESCRIPTION
       "This eight-octet field indicates the sum of errored frames that have been detected since the OAM sublayer was reset."   
   ::= { sm24dp4xaEthLinkOAMPortEventDetailedStatisticsEntry 31 }
   
sm24dp4xaStatisticsRemoteTotalFrameErrEvts OBJECT-TYPE
   SYNTAX      Integer32
   MAX-ACCESS  read-only
   STATUS      current
   DESCRIPTION
       "This four-octet field indicates the number of Errored Frame Event TLVs that 
	   have been generated since the OAM sublayer was reset."   
   ::= { sm24dp4xaEthLinkOAMPortEventDetailedStatisticsEntry 32 }
   
sm24dp4xaStatisticsRemoteFramePeriErrEvtTimestamp OBJECT-TYPE
   SYNTAX      Integer32
   MAX-ACCESS  read-only
   STATUS      current
   DESCRIPTION
       "This two-octet field indicates the time reference when the event was generated, in terms of 100 ms intervals."   
   ::= { sm24dp4xaEthLinkOAMPortEventDetailedStatisticsEntry 33 }
   
sm24dp4xaStatisticsRemoteFramePeriErrEvtWindow OBJECT-TYPE
   SYNTAX      Integer32
   MAX-ACCESS  read-only
   STATUS      current
   DESCRIPTION
       "This four-octet field indicates the duration of period in terms of frames."   
   ::= { sm24dp4xaEthLinkOAMPortEventDetailedStatisticsEntry 34 }
   
sm24dp4xaStatisticsRemoteFramePeriErrEvtThreshold OBJECT-TYPE
   SYNTAX      Integer32
   MAX-ACCESS  read-only
   STATUS      current
   DESCRIPTION
       "This four-octet field indicates the number of errored frames in the period is required
	   to be equal to or greater than in order for the event to be generated."   
   ::= { sm24dp4xaEthLinkOAMPortEventDetailedStatisticsEntry 35 }
   
sm24dp4xaStatisticsRemoteFramePeriErrs OBJECT-TYPE
   SYNTAX      Integer32
   MAX-ACCESS  read-only
   STATUS      current
   DESCRIPTION
       "This four-octet field indicates the number of frame errors in the period."   
   ::= { sm24dp4xaEthLinkOAMPortEventDetailedStatisticsEntry 36 }
   
sm24dp4xaStatisticsRemoteTotalFramePeriErrs OBJECT-TYPE
   SYNTAX      Counter64
   MAX-ACCESS  read-only
   STATUS      current
   DESCRIPTION
       "This eight-octet field indicates the sum of frame errors that have been detected since the OAM sublayer was reset."   
   ::= { sm24dp4xaEthLinkOAMPortEventDetailedStatisticsEntry 37 }
   
sm24dp4xaStatisticsRemoteTotalFramePeriErrEvts OBJECT-TYPE
   SYNTAX      Integer32
   MAX-ACCESS  read-only
   STATUS      current
   DESCRIPTION
       "This four-octet field indicates the number of Errored Frame Period Event TLVs 
	   that have been generated since the OAM sublayer was reset."   
   ::= { sm24dp4xaEthLinkOAMPortEventDetailedStatisticsEntry 38 }
   
sm24dp4xaStatisticsRemoteSymbolPeriErrEvtTimestamp OBJECT-TYPE
   SYNTAX      Integer32
   MAX-ACCESS  read-only
   STATUS      current
   DESCRIPTION
       "This two-octet field indicates the time reference when the event was generated, in terms of 100 ms intervals."   
   ::= { sm24dp4xaEthLinkOAMPortEventDetailedStatisticsEntry 39 }
   
sm24dp4xaStatisticsRemoteSymbolPeriErrEvtWindow OBJECT-TYPE
   SYNTAX      Counter64
   MAX-ACCESS  read-only
   STATUS      current
   DESCRIPTION
       "This eight-octet field indicates the number of symbols in the period."   
   ::= { sm24dp4xaEthLinkOAMPortEventDetailedStatisticsEntry 40 }
   
sm24dp4xaStatisticsRemoteSymbolPeriErrEvtThreshold OBJECT-TYPE
   SYNTAX      Counter64
   MAX-ACCESS  read-only
   STATUS      current
   DESCRIPTION
       "This eight-octet field indicates the number of errored symbols in the period is required to
	   be equal to or greater than in order for the event to be generated."   
   ::= { sm24dp4xaEthLinkOAMPortEventDetailedStatisticsEntry 41 }
   
sm24dp4xaStatisticsRemoteSymbolPeriErrs OBJECT-TYPE
   SYNTAX      Counter64
   MAX-ACCESS  read-only
   STATUS      current
   DESCRIPTION
       "This eight-octet field indicates the number of symbol errors in the period."   
   ::= { sm24dp4xaEthLinkOAMPortEventDetailedStatisticsEntry 42 }
   
sm24dp4xaStatisticsRemoteSymbolFramePeriErrs OBJECT-TYPE
   SYNTAX      Counter64
   MAX-ACCESS  read-only
   STATUS      current
   DESCRIPTION
       "This eight-octet field indicates the sum of symbol errors since the OAM sublayer was reset."   
   ::= { sm24dp4xaEthLinkOAMPortEventDetailedStatisticsEntry 43 }
   
sm24dp4xaStatisticsRemoteSymbolFramePeriErrEvts OBJECT-TYPE
   SYNTAX      Integer32
   MAX-ACCESS  read-only
   STATUS      current
   DESCRIPTION
       "This four-octet field indicates the number of Errored Symbol Period Event TLVs that
	   have been generated since the OAM sublayer was reset."   
   ::= { sm24dp4xaEthLinkOAMPortEventDetailedStatisticsEntry 44 }
   
sm24dp4xaStatisticsRemoteEvtSecondsSummTimeStamp OBJECT-TYPE
   SYNTAX      Integer32
   MAX-ACCESS  read-only
   STATUS      current
   DESCRIPTION
       "This two-octet field indicates the time reference when the event was generated, 
	   in terms of 100 ms intervals, encoded as a 16-bit unsigned integer."   
   ::= { sm24dp4xaEthLinkOAMPortEventDetailedStatisticsEntry 45 }
   
sm24dp4xaStatisticsRemoteEvtSecondsSummWindow OBJECT-TYPE
   SYNTAX      Integer32
   MAX-ACCESS  read-only
   STATUS      current
   DESCRIPTION
       "This two-octet field indicates the duration of the period in terms of 100 ms intervals, encoded as a 16-bit unsigned integer."   
   ::= { sm24dp4xaEthLinkOAMPortEventDetailedStatisticsEntry 46 }
   
sm24dp4xaStatisticsRemoteEvtSecondsSummThreshold OBJECT-TYPE
   SYNTAX      Integer32
   MAX-ACCESS  read-only
   STATUS      current
   DESCRIPTION
       "This two-octet field indicates the number of errored frame seconds in the period is required
	   to be equal to or greater than in order for the event to be generated, encoded as a 16-bit unsigned integer."   
   ::= { sm24dp4xaEthLinkOAMPortEventDetailedStatisticsEntry 47 }
   
sm24dp4xaStatisticsRemoteEvtSecondsSummEvts OBJECT-TYPE
   SYNTAX      Integer32
   MAX-ACCESS  read-only
   STATUS      current
   DESCRIPTION
       "This two-octet field indicates the number of errored frame seconds in the period, encoded as a 16-bit unsigned integer."   
   ::= { sm24dp4xaEthLinkOAMPortEventDetailedStatisticsEntry 48 }
   
sm24dp4xaStatisticsRemoteEvtSecondsSummErrTotal OBJECT-TYPE
   SYNTAX      Integer32
   MAX-ACCESS  read-only
   STATUS      current
   DESCRIPTION
       "This four-octet field indicates the sum of errored frame seconds that have been detected since the OAM sublayer was reset."   
   ::= { sm24dp4xaEthLinkOAMPortEventDetailedStatisticsEntry 49 }
   
sm24dp4xaStatisticsRemoteEvtSecondsSummEvtTotal OBJECT-TYPE
   SYNTAX      Integer32
   MAX-ACCESS  read-only
   STATUS      current
   DESCRIPTION
       "This four-octet field indicates the number of Errored Frame Seconds Summary Event TLVs that 
	   have been generated since the OAM sublayer was reset, encoded as a 32bit unsigned integer."   
   ::= { sm24dp4xaEthLinkOAMPortEventDetailedStatisticsEntry 50 }
   
   
   
sm24dp4xaEVC    OBJECT IDENTIFIER ::= { sm24dp4xaConfiguration 30 } 

sm24dp4xaEVCPortConfTable OBJECT-TYPE
   SYNTAX      SEQUENCE OF SM24DP4XAEVCPortConfEntry
   MAX-ACCESS  not-accessible
   STATUS      current
   DESCRIPTION
       " "
   ::= { sm24dp4xaEVC 1 }

sm24dp4xaEVCPortConfEntry OBJECT-TYPE
   SYNTAX      SM24DP4XAEVCPortConfEntry
   MAX-ACCESS  not-accessible
   STATUS      current
   DESCRIPTION
       " "
   INDEX    { sm24dp4xaEVCPortConfIndex  }
   ::= { sm24dp4xaEVCPortConfTable 1 }

SM24DP4XAEVCPortConfEntry ::= SEQUENCE {
   sm24dp4xaEVCPortConfIndex           Integer32,
   sm24dp4xaEVCPortConfDEIMode         Integer32,
   sm24dp4xaEVCPortConfTagMode         Integer32,
   sm24dp4xaEVCPortConfAddressMode     Integer32
}

sm24dp4xaEVCPortConfIndex OBJECT-TYPE
   SYNTAX      Integer32 (1..65535)
   MAX-ACCESS  not-accessible
   STATUS      current
   DESCRIPTION
       "Index"
   ::= { sm24dp4xaEVCPortConfEntry 1 }

sm24dp4xaEVCPortConfDEIMode OBJECT-TYPE
   SYNTAX      Integer32
   MAX-ACCESS  read-write
   STATUS      current
   DESCRIPTION
       "The DEI mode for an NNI port determines whether frames transmitted on the port 
	   will have the DEI field in the outer tag marked based on the colour of the frame. 
	   The allowed values are: 
	   0:Fixed: The DEI value is determined by ECE rules.
       1:Coloured: The DEI is 1 for yellow frames and 0 for green frames. 
       "
   ::= { sm24dp4xaEVCPortConfEntry 2 }

sm24dp4xaEVCPortConfTagMode OBJECT-TYPE
   SYNTAX      Integer32
   MAX-ACCESS  read-write
   STATUS      current
   DESCRIPTION
       "The tag mode specifying whether the EVC classification must be based on the outer or inner tag. 
	   This can be used on NNI ports connected to another service provider, 
	   where an outer tunnel tag is added together with the inner tag identifying the EVC. 
	   The allowed values are: 
		0:Inner: Enable inner tag in EVC classification. 
		1:Outer: Enable outer tag in EVC classification."
   ::= { sm24dp4xaEVCPortConfEntry 3 }
   
sm24dp4xaEVCPortConfAddressMode OBJECT-TYPE
   SYNTAX      Integer32
   MAX-ACCESS  read-write
   STATUS      current
   DESCRIPTION
       "The IP/MAC address mode specifying whether the EVC classification must be based on source (SMAC/SIP) or 
	   destination (DMAC/DIP) addresses. 
	   The allowed values are: 
	   0:Source: Enable SMAC/SIP matching. 
	   1:Destination: Enable DMAC/DIP matching."
   ::= { sm24dp4xaEVCPortConfEntry 4 }

   
   
sm24dp4xaEVCBandwidthProfilesConfTable OBJECT-TYPE
   SYNTAX      SEQUENCE OF SM24DP4XAEVCBandwidthProfilesConfEntry
   MAX-ACCESS  not-accessible
   STATUS      current
   DESCRIPTION
       " "
   ::= { sm24dp4xaEVC 2 }

sm24dp4xaEVCBandwidthProfilesConfEntry OBJECT-TYPE
   SYNTAX      SM24DP4XAEVCBandwidthProfilesConfEntry
   MAX-ACCESS  not-accessible
   STATUS      current
   DESCRIPTION
       " "
   INDEX    { sm24dp4xaEVCBandwidthProfilesConfIndex  }
   ::= { sm24dp4xaEVCBandwidthProfilesConfTable 1 }

SM24DP4XAEVCBandwidthProfilesConfEntry ::= SEQUENCE {
   sm24dp4xaEVCBandwidthProfilesConfIndex           Integer32,
   sm24dp4xaEVCBandwidthProfilesConfState           Integer32,
   sm24dp4xaEVCBandwidthProfilesConfType            Integer32,
   sm24dp4xaEVCBandwidthProfilesConfPolicerMode     Integer32,
   sm24dp4xaEVCBandwidthProfilesConfRateType        Integer32,
   sm24dp4xaEVCBandwidthProfilesConfCIRkbps         Integer32,
   sm24dp4xaEVCBandwidthProfilesConfCBSbytes        Integer32,
   sm24dp4xaEVCBandwidthProfilesConfEIRkbps         Integer32,  
   sm24dp4xaEVCBandwidthProfilesConfEBSbytes        Integer32   
}

sm24dp4xaEVCBandwidthProfilesConfIndex OBJECT-TYPE
   SYNTAX      Integer32 (1..65535)
   MAX-ACCESS  not-accessible
   STATUS      current
   DESCRIPTION
       "Index"
   ::= { sm24dp4xaEVCBandwidthProfilesConfEntry 1 }

sm24dp4xaEVCBandwidthProfilesConfState OBJECT-TYPE
   SYNTAX      Integer32
   MAX-ACCESS  read-write
   STATUS      current
   DESCRIPTION
       "The administrative state of the bandwidth profile. The allowed values are: 
		1:Enabled: The bandwidth profile enabled. 
		0:Disabled: The bandwidth profile is disabled.
       "
   ::= { sm24dp4xaEVCBandwidthProfilesConfEntry 2 }

sm24dp4xaEVCBandwidthProfilesConfType OBJECT-TYPE
   SYNTAX      Integer32
   MAX-ACCESS  read-write
   STATUS      current
   DESCRIPTION
       "The policer type of the bandwidth profile. The allowed values are: 
		0:MEF: MEF ingress bandwidth profile. 
		1:Single: Single bucket policer."
   ::= { sm24dp4xaEVCBandwidthProfilesConfEntry 3 }
   
sm24dp4xaEVCBandwidthProfilesConfPolicerMode OBJECT-TYPE
   SYNTAX      Integer32
   MAX-ACCESS  read-write
   STATUS      current
   DESCRIPTION
       "The colour mode of the bandwidth profile. The allowed values are: 
		0:Coupled: Colour-aware mode with coupling enabled. 
		1:Aware: Colour-aware mode with coupling disabled."
   ::= { sm24dp4xaEVCBandwidthProfilesConfEntry 4 }
   
sm24dp4xaEVCBandwidthProfilesConfRateType OBJECT-TYPE
   SYNTAX      Integer32
   MAX-ACCESS  read-write
   STATUS      current
   DESCRIPTION
       "The rate type of the bandwidth profile. The allowed values are: 
		0:Data: Specify that this bandwidth profile operates on data rate. 
		1:Line: Specify that this bandwidth profile operates on line rate."
   ::= { sm24dp4xaEVCBandwidthProfilesConfEntry 5 }

sm24dp4xaEVCBandwidthProfilesConfCIRkbps OBJECT-TYPE
   SYNTAX      Integer32
   MAX-ACCESS  read-write
   STATUS      current
   DESCRIPTION
       "The Committed Information Rate of the bandwidth profile. 
	   The allowed range is from 0 through 10000000 kilobit per second."
   ::= { sm24dp4xaEVCBandwidthProfilesConfEntry 6 }

sm24dp4xaEVCBandwidthProfilesConfCBSbytes OBJECT-TYPE
   SYNTAX      Integer32
   MAX-ACCESS  read-write
   STATUS      current
   DESCRIPTION
       "The Committed Burst Size of the bandwidth profile. 
	   The allowed range is from 0 through 100000 bytes."
   ::= { sm24dp4xaEVCBandwidthProfilesConfEntry 7 }

sm24dp4xaEVCBandwidthProfilesConfEIRkbps OBJECT-TYPE
   SYNTAX      Integer32
   MAX-ACCESS  read-write
   STATUS      current
   DESCRIPTION
       "The Excess Information Rate for MEF type bandwidth profile. 
	   The allowed range is from 0 through 10000000 kilobit per second."
   ::= { sm24dp4xaEVCBandwidthProfilesConfEntry 8 }

sm24dp4xaEVCBandwidthProfilesConfEBSbytes OBJECT-TYPE
   SYNTAX      Integer32
   MAX-ACCESS  read-write
   STATUS      current
   DESCRIPTION
       "The Excess Burst Size for MEF type bandwidth profile. 
	   The allowed range is from 0 through 100000 bytes."
   ::= { sm24dp4xaEVCBandwidthProfilesConfEntry 9 }   


   
sm24dp4xaEVCControlListConfTable  OBJECT-TYPE
   SYNTAX      SEQUENCE OF SM24DP4XAEVCControlListConfEntry
   MAX-ACCESS  not-accessible
   STATUS      current
   DESCRIPTION
       "A table of EVC Control List Conf."
   ::= { sm24dp4xaEVC 3 }

sm24dp4xaEVCControlListConfEntry OBJECT-TYPE
    SYNTAX        SM24DP4XAEVCControlListConfEntry
    MAX-ACCESS    not-accessible
    STATUS        current
    DESCRIPTION
        "An entry of EVC Control List Conf table."
    INDEX        { sm24dp4xaEVCControlListConfIndex }
    ::= { sm24dp4xaEVCControlListConfTable 1 }

SM24DP4XAEVCControlListConfEntry ::=
    SEQUENCE {
        sm24dp4xaEVCControlListConfIndex                       Integer32,
        sm24dp4xaEVCControlListConfEVCID                       Integer32,
        sm24dp4xaEVCControlListConfVID                         Integer32,
        sm24dp4xaEVCControlListConfIVID                        Integer32,
        sm24dp4xaEVCControlListConfLearning                    Integer32,
        sm24dp4xaEVCControlListConfPolicerIDFilter             Integer32,
        sm24dp4xaEVCControlListConfPolicerID                   Integer32,
        sm24dp4xaEVCControlListConfInnerTagType                Integer32,
        sm24dp4xaEVCControlListConfInnerTagVIDMode             Integer32,
        sm24dp4xaEVCControlListConfInnerTagVLANID              Integer32,
        sm24dp4xaEVCControlListConfInnerTagPCPDEIPreservation  Integer32,
        sm24dp4xaEVCControlListConfInnerTagPCP                 Integer32,
        sm24dp4xaEVCControlListConfInnerTagDEI                 Integer32,        
		sm24dp4xaEVCControlListConfOuterTagVLANID              Integer32,
        sm24dp4xaEVCControlListConfNNIPorts                    DisplayString,
		sm24dp4xaEVCControlListConfLeafVID                     Integer32,
        sm24dp4xaEVCControlListConfLeafIVID                    Integer32,
		sm24dp4xaEVCControlListConfLeafPorts                   DisplayString,
        sm24dp4xaEVCControlListConfRowStatus                   RowStatus
    }

sm24dp4xaEVCControlListConfIndex OBJECT-TYPE
   SYNTAX      Integer32 (1..65535)
   MAX-ACCESS  not-accessible
   STATUS      current
   DESCRIPTION
       "index"
   ::= {sm24dp4xaEVCControlListConfEntry 1 }

sm24dp4xaEVCControlListConfEVCID OBJECT-TYPE
   SYNTAX      Integer32
   MAX-ACCESS  read-create
   STATUS      current
   DESCRIPTION
       "The EVC ID identifies the EVC. The allowed range is from 1 through 256."
   ::= {sm24dp4xaEVCControlListConfEntry 2 }

sm24dp4xaEVCControlListConfVID OBJECT-TYPE
   SYNTAX      Integer32
   MAX-ACCESS  read-create
   STATUS      current
   DESCRIPTION
       "The VLAN ID in the PB network. It may be inserted in a C-tag, S-tag or S-custom tag 
	   depending on the NNI port VLAN configuration. 
	   The allowed range is from 1 through 4095."
   ::= {sm24dp4xaEVCControlListConfEntry 3 }
   
sm24dp4xaEVCControlListConfIVID OBJECT-TYPE
   SYNTAX      Integer32
   MAX-ACCESS  read-create
   STATUS      current
   DESCRIPTION
       "The Internal/classified VLAN ID in the PB network. 
	   The allowed range is from 1 through 4095."
   ::= {sm24dp4xaEVCControlListConfEntry 4 }
   
sm24dp4xaEVCControlListConfLearning OBJECT-TYPE
   SYNTAX      Integer32
   MAX-ACCESS  read-create
   STATUS      current
   DESCRIPTION
       "The learning mode for the EVC controls whether source MAC addresses are learned for frames matching the EVC. 
	   Learning may be disabled if the EVC only includes two UNI/NNI ports. The possible values are: 
		1:Enabled: Learning is enabled (MAC addresses are learned). 
		0:Disabled: Learning is disabled (MAC addresses are not learned)."
   ::= {sm24dp4xaEVCControlListConfEntry 5 }
   
sm24dp4xaEVCControlListConfPolicerIDFilter OBJECT-TYPE
   SYNTAX      Integer32
   MAX-ACCESS  read-create
   STATUS      current
   DESCRIPTION
       "The ingress bandwidth profile mode for the EVC. The possible values are:
	   0:Specific.
	   1:Discard: All received frames are discarded for the EVC.
	   2:None: None bandwidth profile for the EVC.
	   "
   ::= {sm24dp4xaEVCControlListConfEntry 6 }   
   
sm24dp4xaEVCControlListConfPolicerID OBJECT-TYPE
   SYNTAX      Integer32
   MAX-ACCESS  read-create
   STATUS      current
   DESCRIPTION
       "The ingress bandwidth profile ID for the EVC."
   ::= {sm24dp4xaEVCControlListConfEntry 7 }    
   
sm24dp4xaEVCControlListConfInnerTagType OBJECT-TYPE
   SYNTAX      Integer32
   MAX-ACCESS  read-create
   STATUS      current
   DESCRIPTION
       "The inner tag type is used to determine whether an inner tag is inserted in frames forwarded to NNI ports. The possible values are: 
		0:None: An inner tag is not inserted. 
		1:C-tag: An inner C-tag is inserted. 
		2:S-tag: An inner S-tag is inserted. 
		3:S-custom-tag: An inner tag is inserted and the tag type is determined by the VLAN port configuration of the NNI."
   ::= {sm24dp4xaEVCControlListConfEntry 8 }     
   
sm24dp4xaEVCControlListConfInnerTagVIDMode OBJECT-TYPE
   SYNTAX      Integer32
   MAX-ACCESS  read-create
   STATUS      current
   DESCRIPTION
       "The inner VID Mode affects the VID in the inner and outer tag. 
	   The possible values are: 
		0:Normal: The VID of the two outer tags aren't swapped. 
		1:Tunnel: The VID of the two outer tags are swapped, 
		so that the VID of the outer tag is taken from the Inner Tag configuration and the VID of the inner tag is the EVC VID. 
		In this mode, the NNI ports are normally configured to do EVC classification based on the inner tag."
   ::= {sm24dp4xaEVCControlListConfEntry 9 }   

sm24dp4xaEVCControlListConfInnerTagVLANID OBJECT-TYPE
   SYNTAX      Integer32
   MAX-ACCESS  read-create
   STATUS      current
   DESCRIPTION
       "The Inner tag VLAN ID. The allowed range is from 1 through 4095."
   ::= {sm24dp4xaEVCControlListConfEntry 10 }    

 sm24dp4xaEVCControlListConfInnerTagPCPDEIPreservation OBJECT-TYPE
   SYNTAX      Integer32
   MAX-ACCESS  read-create
   STATUS      current
   DESCRIPTION
       "The inner tag PCP and DEI preservation. The possible values are: 
		1:Preserved: The inner tag PCP and DEI is preserved. 
		0:Fixed: The inner tag PCP and DEI is fixed."
   ::= {sm24dp4xaEVCControlListConfEntry 11 }  
   
sm24dp4xaEVCControlListConfInnerTagPCP OBJECT-TYPE
   SYNTAX      Integer32
   MAX-ACCESS  read-create
   STATUS      current
   DESCRIPTION
       "The inner tag PCP value. The allowed range is from 0 through 7."
   ::= {sm24dp4xaEVCControlListConfEntry 12 }     
   
sm24dp4xaEVCControlListConfInnerTagDEI OBJECT-TYPE
   SYNTAX      Integer32
   MAX-ACCESS  read-create
   STATUS      current
   DESCRIPTION
       "The inner tag DEI value. The allowed value is 0 or 1."
   ::= {sm24dp4xaEVCControlListConfEntry 13 }     

sm24dp4xaEVCControlListConfOuterTagVLANID OBJECT-TYPE
   SYNTAX      Integer32
   MAX-ACCESS  read-create
   STATUS      current
   DESCRIPTION
       "The EVC outer tag VID for UNI ports. The allowed range is from 1 through 4095."
   ::= {sm24dp4xaEVCControlListConfEntry 14 }    

sm24dp4xaEVCControlListConfNNIPorts OBJECT-TYPE
   SYNTAX      DisplayString
   MAX-ACCESS  read-create
   STATUS      current
   DESCRIPTION
       "The list of Network to Network Interfaces for the EVC."
   ::= {sm24dp4xaEVCControlListConfEntry 15 }     
   
sm24dp4xaEVCControlListConfLeafVID OBJECT-TYPE
   SYNTAX      Integer32
   MAX-ACCESS  read-create
   STATUS      current
   DESCRIPTION
       " The leaf VLAN ID used in the outer tag for the EVC. range:1-4095"
   ::= {sm24dp4xaEVCControlListConfEntry 16 }  

sm24dp4xaEVCControlListConfLeafIVID OBJECT-TYPE
   SYNTAX      Integer32
   MAX-ACCESS  read-create
   STATUS      current
   DESCRIPTION
       "The leaf internal classified VLAN ID for the EVC. range:1-4095"
   ::= {sm24dp4xaEVCControlListConfEntry 17 }      
   
sm24dp4xaEVCControlListConfLeafPorts OBJECT-TYPE
   SYNTAX      DisplayString
   MAX-ACCESS  read-create
   STATUS      current
   DESCRIPTION
       " The list of leaf ports for the EVC."
   ::= {sm24dp4xaEVCControlListConfEntry 18 }    

sm24dp4xaEVCControlListConfRowStatus OBJECT-TYPE
   SYNTAX      RowStatus
   MAX-ACCESS  read-create
   STATUS      current
   DESCRIPTION
       "EVC Control List Conf Row Status."
   ::= {sm24dp4xaEVCControlListConfEntry 19 }

   
   
sm24dp4xaECEControlListConfTable  OBJECT-TYPE
   SYNTAX      SEQUENCE OF SM24DP4XAECEControlListConfEntry
   MAX-ACCESS  not-accessible
   STATUS      current
   DESCRIPTION
       "A table of ECE Control List Conf."
   ::= { sm24dp4xaEVC 4 }

sm24dp4xaECEControlListConfEntry OBJECT-TYPE
    SYNTAX        SM24DP4XAECEControlListConfEntry
    MAX-ACCESS    not-accessible
    STATUS        current
    DESCRIPTION
        "An entry of ECE Control List Conf table."
    INDEX        { sm24dp4xaECECtlListConfIndex }
    ::= { sm24dp4xaECEControlListConfTable 1 }

SM24DP4XAECEControlListConfEntry ::=
    SEQUENCE {
        sm24dp4xaECECtlListConfIndex                               Integer32,
        sm24dp4xaECECtlListConfECEID                               Integer32,
        sm24dp4xaECECtlListConfUNIPorts                            DisplayString,
        sm24dp4xaECECtlListConfIngressMatchingTagType              Integer32,
        sm24dp4xaECECtlListConfIngressMatchingVLANIDFilter         Integer32,
        sm24dp4xaECECtlListConfIngressMatchingVLANIDRangeLow       Integer32,
        sm24dp4xaECECtlListConfIngressMatchingVLANIDRangeHigh      Integer32,
        sm24dp4xaECECtlListConfIngressMatchingPCP                  Integer32,
        sm24dp4xaECECtlListConfIngressMatchingDEI                  Integer32,
        sm24dp4xaECECtlListConfIngressMatchingFrameType            Integer32,
        sm24dp4xaECECtlListConfActionsDirection                    Integer32,
        sm24dp4xaECECtlListConfActionsEVCIDFilter                  Integer32,
        sm24dp4xaECECtlListConfActionsEVCIDValue                   Integer32,
		sm24dp4xaECECtlListConfActionsTagPopCount                  Integer32,
        sm24dp4xaECECtlListConfActionsPolicyID                     Integer32,
		sm24dp4xaECECtlListConfActionsClass                        Integer32,
        sm24dp4xaECECtlListConfMACParametersDMACType               Integer32,
		sm24dp4xaECECtlListConfMACParametersSMACFilter             Integer32,
		sm24dp4xaECECtlListConfMACParametersSMACValue              DisplayString,
		sm24dp4xaECECtlListConfIPv4Protocol                        Integer32,
		sm24dp4xaECECtlListConfIPv4ProtocolValue                   Integer32,
		sm24dp4xaECECtlListConfIPv4SIPDIPFilter                    Integer32,
		sm24dp4xaECECtlListConfIPv4SIPDIPAddress                   IpAddress,
		sm24dp4xaECECtlListConfIPv4SIPDIPMask                      IpAddress,
		sm24dp4xaECECtlListConfIPv4DSCPFilter                      Integer32,
		sm24dp4xaECECtlListConfIPv4DSCPRangeLow                    Integer32,
		sm24dp4xaECECtlListConfIPv4DSCPRangeHigh                   Integer32,
		sm24dp4xaECECtlListConfIPv4Fragment                        Integer32,
		sm24dp4xaECECtlListConfIPv4SourcePortFilter                Integer32,
		sm24dp4xaECECtlListConfIPv4SourceRangeLow                  Integer32,
		sm24dp4xaECECtlListConfIPv4SourceRangeHigh                 Integer32,
		sm24dp4xaECECtlListConfIPv4DestPortFilter                  Integer32,
		sm24dp4xaECECtlListConfIPv4DestRangeLow                    Integer32,
		sm24dp4xaECECtlListConfIPv4DestRangeHigh                   Integer32,
		sm24dp4xaECECtlListConfIPv6Protocol                        Integer32,
		sm24dp4xaECECtlListConfIPv6ProtocolValue                   Integer32,
		sm24dp4xaECECtlListConfIPv6SIPDIPFilter                    Integer32,
		sm24dp4xaECECtlListConfIPv6SIPDIPAddress                   IpAddress,
		sm24dp4xaECECtlListConfIPv6SIPDIPMask                      IpAddress,
		sm24dp4xaECECtlListConfIPv6DSCPFilter                      Integer32,
		sm24dp4xaECECtlListConfIPv6DSCPRangeLow                    Integer32,
		sm24dp4xaECECtlListConfIPv6DSCPRangeHigh                   Integer32,
		sm24dp4xaECECtlListConfIPv6SourcePortFilter                Integer32,
		sm24dp4xaECECtlListConfIPv6SourceRangeLow                  Integer32,
		sm24dp4xaECECtlListConfIPv6SourceRangeHigh                 Integer32,
		sm24dp4xaECECtlListConfIPv6DestPortFilter                  Integer32,
		sm24dp4xaECECtlListConfIPv6DestRangeLow                    Integer32,
		sm24dp4xaECECtlListConfIPv6DestRangeHigh                   Integer32,
		sm24dp4xaECECtlListConfEgressOuterTagMode                  Integer32,
		sm24dp4xaECECtlListConfEgressOuterTagPCPDEIPresv           Integer32,
		sm24dp4xaECECtlListConfEgressOuterTagPCP                   Integer32,
		sm24dp4xaECECtlListConfEgressOuterTagDEI                   Integer32,
		sm24dp4xaECECtlListConfConflict                            Integer32,
        sm24dp4xaECECtlListConfRowStatus                           RowStatus
    }

sm24dp4xaECECtlListConfIndex OBJECT-TYPE
   SYNTAX      Integer32 (1..65535)
   MAX-ACCESS  not-accessible
   STATUS      current
   DESCRIPTION
       "index"
   ::= {sm24dp4xaECEControlListConfEntry 1 }

sm24dp4xaECECtlListConfECEID OBJECT-TYPE
   SYNTAX      Integer32
   MAX-ACCESS  read-create
   STATUS      current
   DESCRIPTION
       "The ECE ID identifies the ECE. Unique ECE IDs are automatically assigned to ECEs added. 
	   The possible range is from 1 through 256."
   ::= {sm24dp4xaECEControlListConfEntry 2 }  
   
sm24dp4xaECECtlListConfUNIPorts OBJECT-TYPE
   SYNTAX      DisplayString
   MAX-ACCESS  read-create
   STATUS      current
   DESCRIPTION
       "The list of User Network Interfaces for the ECE. Ex:1,2 1-5"
   ::= {sm24dp4xaECEControlListConfEntry 3 }  

sm24dp4xaECECtlListConfIngressMatchingTagType OBJECT-TYPE
   SYNTAX      Integer32
   MAX-ACCESS  read-create
   STATUS      current
   DESCRIPTION
       "The tag type for the ECE. The possible values are: 
		0:Any: The ECE will match both tagged and untagged frames. 
		1:Untagged: The ECE will match untagged frames only. 
		2:C-Tagged: The ECE will match custom tagged frames only. 
		3:S-Tagged: The ECE will match service tagged frames only. 
		4:Tagged: The ECE will match tagged frames only."
   ::= {sm24dp4xaECEControlListConfEntry 4 }  

sm24dp4xaECECtlListConfIngressMatchingVLANIDFilter OBJECT-TYPE
   SYNTAX      Integer32
   MAX-ACCESS  read-create
   STATUS      current
   DESCRIPTION
       "The VLAN ID filter for matching the ECE. It only significant if tag type 'Tagged' is selected. The possible values are: 
		0:Any: No VLAN ID filter is specified. (VLAN ID filter status is don't-care.) 
		1:Specific: If you want to filter a specific VLAN ID value with this ECE, choose this value. A field for entering a specific value appears. 
		2:Range: If you want to filter a specific VLAN ID range filter with this ECE, choose this value. A field for entering a range appears."
   ::= {sm24dp4xaECEControlListConfEntry 5 }  
   
sm24dp4xaECECtlListConfIngressMatchingVLANIDRangeLow OBJECT-TYPE
   SYNTAX      Integer32
   MAX-ACCESS  read-create
   STATUS      current
   DESCRIPTION
       "When Specific is selected for the VLAN ID filter, you can enter a specific value. 
	   The allowed value is from 0 through 4095."
   ::= {sm24dp4xaECEControlListConfEntry 6 }     
   
sm24dp4xaECECtlListConfIngressMatchingVLANIDRangeHigh OBJECT-TYPE
   SYNTAX      Integer32
   MAX-ACCESS  read-create
   STATUS      current
   DESCRIPTION
       "When Specific is selected for the VLAN ID filter, you can enter a specific value. 
	   The allowed value is from 0 through 4095."
   ::= {sm24dp4xaECEControlListConfEntry 7 }     
   
sm24dp4xaECECtlListConfIngressMatchingPCP OBJECT-TYPE
   SYNTAX      Integer32
   MAX-ACCESS  read-create
   STATUS      current
   DESCRIPTION
       "The PCP value for matching the ECE. It only significant if tag type 'Tagged' is selected. The possible values are: 
        14:Any: The ECE will match any PCP value. 
		0-7:Specific: The ECE will match a specific PCP in the range 0 through 7. 
		8-13:Range: The ECE will match PCP values in the selected range 0-1, 2-3, 4-5, 6-7, 0-3 or 4-7."
   ::= {sm24dp4xaECEControlListConfEntry 8 }    
   
sm24dp4xaECECtlListConfIngressMatchingDEI OBJECT-TYPE
   SYNTAX      Integer32
   MAX-ACCESS  read-create
   STATUS      current
   DESCRIPTION
       "The DEI value for matching the ECE. It only significant if tag type 'Tagged' is selected. 
	   The allowed value is: 
	   0:Any
	   1:0
	   2:1"
   ::= {sm24dp4xaECEControlListConfEntry 9 }    
   
sm24dp4xaECECtlListConfIngressMatchingFrameType OBJECT-TYPE
   SYNTAX      Integer32
   MAX-ACCESS  read-create
   STATUS      current
   DESCRIPTION
       "The frame type for the ECE. The possible values are: 
		0:Any: The ECE will match any frame type. 
		1:IPv4: The ECE will match IPv4 frames only. 
		2:IPv6: The ECE will match IPv6 frames only."
   ::= {sm24dp4xaECEControlListConfEntry 16 }  
   
sm24dp4xaECECtlListConfActionsDirection OBJECT-TYPE
   SYNTAX      Integer32
   MAX-ACCESS  read-create
   STATUS      current
   DESCRIPTION
       "The EVCs and ECEs are used to setup flows in one or both directions as determined by the ECE Direction parameter. 
	   If the ECE is bidirectional, the ingress rules of the NNI ports will be setup to match the traffic being forwarded to NNI ports. 
	   The possible values are: 
		0:Both: Bidirectional. 
		1:UNI-to-NNI: Unidirectional from UNI to NNI. 
		2:NNI-to-UNI: Unidirectional from NNI to UNI."
   ::= {sm24dp4xaECEControlListConfEntry 17 }  
   
sm24dp4xaECECtlListConfActionsEVCIDFilter OBJECT-TYPE
   SYNTAX      Integer32
   MAX-ACCESS  read-create
   STATUS      current
   DESCRIPTION
       "The EVC ID for the ECE. 
	   The ECE is only active when mapping to an existing EVC. 
	   The possible values are: 
		0:None: No EVC ID filter is specified. (EVC ID filter status is don't-care.) 
		1:Specific: If you want to filter a specific EVC ID with this ECE, choose this value. A field for entering a specific value appears."
   ::= {sm24dp4xaECEControlListConfEntry 18 }     
   
sm24dp4xaECECtlListConfActionsEVCIDValue OBJECT-TYPE
   SYNTAX      Integer32
   MAX-ACCESS  read-create
   STATUS      current
   DESCRIPTION
       "When Specific is selected for the VLAN ID filter, you can enter a specific value. 
	   The allowed value is from 1 through 256."
   ::= {sm24dp4xaECEControlListConfEntry 19 }      
   
sm24dp4xaECECtlListConfActionsTagPopCount OBJECT-TYPE
   SYNTAX      Integer32
   MAX-ACCESS  read-create
   STATUS      current
   DESCRIPTION
       "The ingress tag pop count for the ECE. The allowed range is from 0 through 2."
   ::= {sm24dp4xaECEControlListConfEntry 22 }   

sm24dp4xaECECtlListConfActionsPolicyID OBJECT-TYPE
   SYNTAX      Integer32
   MAX-ACCESS  read-create
   STATUS      current
   DESCRIPTION
       "The ACL Policy ID for the ECE for matching ACL rules. 
	   The allowed range is from 0 through 255."
   ::= {sm24dp4xaECEControlListConfEntry 23 }     
   
sm24dp4xaECECtlListConfActionsClass OBJECT-TYPE
   SYNTAX      Integer32
   MAX-ACCESS  read-create
   STATUS      current
   DESCRIPTION
       "The traffic class for the ECE. The allowed range is from 0 through 7 or disabled(8)."
   ::= {sm24dp4xaECEControlListConfEntry 24 }   

sm24dp4xaECECtlListConfMACParametersDMACType OBJECT-TYPE
   SYNTAX      Integer32
   MAX-ACCESS  read-create
   STATUS      current
   DESCRIPTION
       "The destination MAC address type for matching the ECE. The possible values are: 
		0:Any: No DMAC tyoe is specified. (DMAC filter status is don't-care.) 
		1:Unicast: Frame must be unicast. 
		2:Multicast: Frame must be multicast. 
		3:Broadcast: Frame must be broadcast."
   ::= {sm24dp4xaECEControlListConfEntry 25 }      
   
sm24dp4xaECECtlListConfMACParametersSMACFilter OBJECT-TYPE
   SYNTAX      Integer32
   MAX-ACCESS  read-create
   STATUS      current
   DESCRIPTION
       "The source MAC address for matching the ECE. The possible values are: 
		0:Any: No SMAC filter is specified. (SMAC filter status is don't-care.) 
		1:Specific: If you want to filter a specific SMAC value with this ECE, choose this value. A field for entering a specific value appears."
   ::= {sm24dp4xaECEControlListConfEntry 28 }    
   
sm24dp4xaECECtlListConfMACParametersSMACValue OBJECT-TYPE
   SYNTAX      DisplayString
   MAX-ACCESS  read-create
   STATUS      current
   DESCRIPTION
       "When Specific is selected for the SMAC filter, you can enter a specific value. 
	   The legal format is xx-xx-xx-xx-xx-xx (x is a hexadecimal digit)."
   ::= {sm24dp4xaECEControlListConfEntry 29 }     
   
sm24dp4xaECECtlListConfIPv4Protocol OBJECT-TYPE
   SYNTAX      Integer32
   MAX-ACCESS  read-create
   STATUS      current
   DESCRIPTION
       "The IP protocol for matching the ECE. The possible values are: 
		0:Any: No protocol filter is specified. (Protocol filter status is don't-care.) 
		1:UDP: Specify the UDP for matching the ECE. 
		2:TCP: Specify the TCP for matching the ECE. 
		3:Specific: If you want to filter a specific protocol value with this ECE, choose this value. A field for entering a specific value appears."
   ::= {sm24dp4xaECEControlListConfEntry 30 }
   
sm24dp4xaECECtlListConfIPv4ProtocolValue OBJECT-TYPE
   SYNTAX      Integer32
   MAX-ACCESS  read-create
   STATUS      current
   DESCRIPTION
       "When Specific is selected for the protocol filter, you can enter a specific value. 
	   The allowed value is from 0 through 255."
   ::= {sm24dp4xaECEControlListConfEntry 31 }   
   
sm24dp4xaECECtlListConfIPv4SIPDIPFilter OBJECT-TYPE
   SYNTAX      Integer32
   MAX-ACCESS  read-create
   STATUS      current
   DESCRIPTION
       "The source/destination IP address for matching the ECE. 
	   It depend on by the port address mode, when port address mode is set to 'Source' then the field is used for source address. 
	   Similarly when port address mode is set to 'Destination' then the field is used for destination address. 
	   The possible values are: 
		0:Any: No SIP/DIP filter is specified. (SIP/DIP filter status is don't-care.) 
		1:Host: When IPv4 is selected for the Frame Type, if you want to filter a specific host address with this ECE, choose this value. A field for entering a host address appears. 
		2:Network: When IPv4 is selected for the Frame Type, if you want to filter a specific network address with this ECE, choose this value. Two fields for entering a specific network address and network mask appears. "
   ::= {sm24dp4xaECEControlListConfEntry 32 }    
   
sm24dp4xaECECtlListConfIPv4SIPDIPAddress OBJECT-TYPE
   SYNTAX      IpAddress
   MAX-ACCESS  read-create
   STATUS      current
   DESCRIPTION
       "When IPv4 is selected for the Frame Type and Host or Network is selected for the SIP/DIP filter, 
	   you can enter a specific host or network address. 
	   "
   ::= {sm24dp4xaECEControlListConfEntry 33 }    
   
sm24dp4xaECECtlListConfIPv4SIPDIPMask OBJECT-TYPE
   SYNTAX      IpAddress
   MAX-ACCESS  read-create
   STATUS      current
   DESCRIPTION
       "When IPv4 is selected for the Frame Type and Host or Network is selected for the SIP/DIP filter, 
	   you can enter a specific network mask. "
   ::= {sm24dp4xaECEControlListConfEntry 34 }     
   
sm24dp4xaECECtlListConfIPv4DSCPFilter OBJECT-TYPE
   SYNTAX      Integer32
   MAX-ACCESS  read-create
   STATUS      current
   DESCRIPTION
       "The DSCP filter for matching the ECE. The possible values are: 
		0:Any: No DSCP filter is specified. (DSCP filter status is don't-care.) 
		1:Specific: If you want to filter a specific DSCP value with this ECE, choose this value. A field for entering a specific value appears. 
		2:Range: If you want to filter a specific DSCP range filter with this ECE, choose this value. A field for entering a range appears."
   ::= {sm24dp4xaECEControlListConfEntry 35 }    
   
sm24dp4xaECECtlListConfIPv4DSCPRangeLow OBJECT-TYPE
   SYNTAX      Integer32
   MAX-ACCESS  read-create
   STATUS      current
   DESCRIPTION
       "When Specific is selected for the DSCP filter, you can enter a specific value. 
	   The allowed value is from 0 through 63."
   ::= {sm24dp4xaECEControlListConfEntry 36 }    

sm24dp4xaECECtlListConfIPv4DSCPRangeHigh OBJECT-TYPE
   SYNTAX      Integer32
   MAX-ACCESS  read-create
   STATUS      current
   DESCRIPTION
       "When Range is selected for the DSCP filter, you can enter a specific range. 
	   The allowed range is from 0 through 63."
   ::= {sm24dp4xaECEControlListConfEntry 37 }   

sm24dp4xaECECtlListConfIPv4Fragment OBJECT-TYPE
   SYNTAX      Integer32
   MAX-ACCESS  read-create
   STATUS      current
   DESCRIPTION
       "The IPv4 Fragment for matching the ECE. 
	   This involves the settings for the More Fragments (MF) bit and the Fragment Offset (FRAG OFFSET) field for an IPv4 frame. 
	   The possible values are: 
		0:Any: The ECE will match any MF bit. 
		1:Non-Fragment: IPv4 frames where the MF bit is set or the FRAG OFFSET field is greater than zero must not be able to match this entry. 
		2:Fragment: IPv4 frames where the MF bit is set or the FRAG OFFSET field is greater than zero must be able to match this entry."
   ::= {sm24dp4xaECEControlListConfEntry 38 }    

sm24dp4xaECECtlListConfIPv4SourcePortFilter OBJECT-TYPE
   SYNTAX      Integer32
   MAX-ACCESS  read-create
   STATUS      current
   DESCRIPTION
       "The TCP/UDP source port for matching the ECE. 
	   It only significant if protocol filter 'UDP' or 'TCP' is selected. 
	   The possible values are: 
		0:Any: No TCP/UDP source port filter is specified. (Source port filter status is don't-care.) 
		1:Specific: If you want to filter a specific TCP/UDP source port No. with this ECE, choose this value. A field for entering a specific No. appears. 
		2:Range: If you want to filter a specific TCP/UDP source port range filter with this ECE, choose this value. A field for entering a range appears."
   ::= {sm24dp4xaECEControlListConfEntry 39 }     
   
sm24dp4xaECECtlListConfIPv4SourceRangeLow OBJECT-TYPE
   SYNTAX      Integer32
   MAX-ACCESS  read-create
   STATUS      current
   DESCRIPTION
       "When Range is selected for the source port filter, you can enter a specific range. 
	   The allowed range is from 0 through 65535."
   ::= {sm24dp4xaECEControlListConfEntry 40 }    
   
sm24dp4xaECECtlListConfIPv4SourceRangeHigh OBJECT-TYPE
   SYNTAX      Integer32
   MAX-ACCESS  read-create
   STATUS      current
   DESCRIPTION
       "When Range is selected for the source port filter, you can enter a specific range. 
	   The allowed range is from 0 through 65535."
   ::= {sm24dp4xaECEControlListConfEntry 41 }    
   
sm24dp4xaECECtlListConfIPv4DestPortFilter OBJECT-TYPE
   SYNTAX      Integer32
   MAX-ACCESS  read-create
   STATUS      current
   DESCRIPTION
       "The TCP/UDP destination port for matching the ECE. It only significant if protocol filter 'UDP' or 'TCP' is selected. The possible values are: 
		0:Any: No TCP/UDP destination port filter is specified. (Destination port filter status is don't-care.) 
		1:Specific: If you want to filter a specific TCP/UDP destination port No. with this ECE, choose this value. A field for entering a specific No. appears. 
		2:Range: If you want to filter a specific TCP/UDP destination port range filter with this ECE, choose this value. A field for entering a range appears."
   ::= {sm24dp4xaECEControlListConfEntry 42 }    

sm24dp4xaECECtlListConfIPv4DestRangeLow OBJECT-TYPE
   SYNTAX      Integer32
   MAX-ACCESS  read-create
   STATUS      current
   DESCRIPTION
       "When Range is selected for the destination port filter, you can enter a specific range. 
	   The allowed range is from 0 through 65535."
   ::= {sm24dp4xaECEControlListConfEntry 43 }    

sm24dp4xaECECtlListConfIPv4DestRangeHigh OBJECT-TYPE
   SYNTAX      Integer32
   MAX-ACCESS  read-create
   STATUS      current
   DESCRIPTION
       "When Range is selected for the destination port filter, you can enter a specific range. 
	   The allowed range is from 0 through 65535."
   ::= {sm24dp4xaECEControlListConfEntry 44 }  

sm24dp4xaECECtlListConfIPv6Protocol OBJECT-TYPE
   SYNTAX      Integer32
   MAX-ACCESS  read-create
   STATUS      current
   DESCRIPTION
       "The IP protocol for matching the ECE. The possible values are: 
		0:Any: No protocol filter is specified. (Protocol filter status is don't-care.) 
		1:UDP: Specify the UDP for matching the ECE. 
		2:TCP: Specify the TCP for matching the ECE. 
		3:Specific: If you want to filter a specific protocol value with this ECE, choose this value. A field for entering a specific value appears."
   ::= {sm24dp4xaECEControlListConfEntry 45 }     
   
sm24dp4xaECECtlListConfIPv6ProtocolValue OBJECT-TYPE
   SYNTAX      Integer32
   MAX-ACCESS  read-create
   STATUS      current
   DESCRIPTION
       "When Specific is selected for the protocol filter, you can enter a specific value. 
	   The allowed value is from 0 through 255."
   ::= {sm24dp4xaECEControlListConfEntry 46 }     
   
sm24dp4xaECECtlListConfIPv6SIPDIPFilter OBJECT-TYPE
   SYNTAX      Integer32
   MAX-ACCESS  read-create
   STATUS      current
   DESCRIPTION
       "The source/destination IP address for matching the ECE. 
	   It depend on by the port address mode, when port address mode is set to 'Source' then the field is used for source address. Similarly when port address mode is set to 'Destination' then the field is used for destination address. 
	   The possible values are: 
		0:Any: No SIP/DIP filter is specified. (SIP/DIP filter status is don't-care.) 
		1:Specific: When IPv6 is selected for the Frame Type, if you want to filter a specific network address with this ECE, choose this value. Two fields for entering a specific network address and network mask appears."
   ::= {sm24dp4xaECEControlListConfEntry 47 } 

sm24dp4xaECECtlListConfIPv6SIPDIPAddress OBJECT-TYPE
   SYNTAX      IpAddress
   MAX-ACCESS  read-create
   STATUS      current
   DESCRIPTION
	   "When IPv6 is selected for the Frame Type, the field only supported 32 bits for IPv6 address."
   ::= {sm24dp4xaECEControlListConfEntry 48 }    

sm24dp4xaECECtlListConfIPv6SIPDIPMask OBJECT-TYPE
   SYNTAX      IpAddress
   MAX-ACCESS  read-create
   STATUS      current
   DESCRIPTION
	   "When IPv6 is selected for the Frame Type, the field only supported 32 bits for IPv6 mask."
   ::= {sm24dp4xaECEControlListConfEntry 49 }   

sm24dp4xaECECtlListConfIPv6DSCPFilter OBJECT-TYPE
   SYNTAX      Integer32
   MAX-ACCESS  read-create
   STATUS      current
   DESCRIPTION
       "The DSCP filter for matching the ECE. The possible values are: 
		0:Any: No DSCP filter is specified. (DSCP filter status is don't-care.) 
		1:Specific: If you want to filter a specific DSCP value with this ECE, choose this value. A field for entering a specific value appears. 
		2:Range: If you want to filter a specific DSCP range filter with this ECE, choose this value. A field for entering a range appears."
   ::= {sm24dp4xaECEControlListConfEntry 50 }    
   
sm24dp4xaECECtlListConfIPv6DSCPRangeLow OBJECT-TYPE
   SYNTAX      Integer32
   MAX-ACCESS  read-create
   STATUS      current
   DESCRIPTION
       "When Range is selected for the DSCP filter, you can enter a specific range. The allowed range is from 0 through 63."
   ::= {sm24dp4xaECEControlListConfEntry 51 }     
   
sm24dp4xaECECtlListConfIPv6DSCPRangeHigh OBJECT-TYPE
   SYNTAX      Integer32
   MAX-ACCESS  read-create
   STATUS      current
   DESCRIPTION
       "When Range is selected for the DSCP filter, you can enter a specific range. The allowed range is from 0 through 63."
   ::= {sm24dp4xaECEControlListConfEntry 52 }      
   
sm24dp4xaECECtlListConfIPv6SourcePortFilter OBJECT-TYPE
   SYNTAX      Integer32
   MAX-ACCESS  read-create
   STATUS      current
   DESCRIPTION
       "The TCP/UDP source port for matching the ECE. 
	   It only significant if protocol filter 'UDP' or 'TCP' is selected. The possible values are: 
		0:Any: No TCP/UDP source port filter is specified. (Source port filter status is don't-care.) 
		1:Specific: If you want to filter a specific TCP/UDP source port No. with this ECE, choose this value. A field for entering a specific No. appears. 
		2:Range: If you want to filter a specific TCP/UDP source port range filter with this ECE, choose this value. A field for entering a range appears."
   ::= {sm24dp4xaECEControlListConfEntry 53 }    

sm24dp4xaECECtlListConfIPv6SourceRangeLow OBJECT-TYPE
   SYNTAX      Integer32
   MAX-ACCESS  read-create
   STATUS      current
   DESCRIPTION
       "When Range is selected for the source port filter, you can enter a specific range. 
	   The allowed range is from 0 through 65535."
   ::= {sm24dp4xaECEControlListConfEntry 54 }    

sm24dp4xaECECtlListConfIPv6SourceRangeHigh OBJECT-TYPE
   SYNTAX      Integer32
   MAX-ACCESS  read-create
   STATUS      current
   DESCRIPTION
       "When Range is selected for the source port filter, you can enter a specific range. 
	   The allowed range is from 0 through 65535."
   ::= {sm24dp4xaECEControlListConfEntry 55 }    
   
sm24dp4xaECECtlListConfIPv6DestPortFilter OBJECT-TYPE
   SYNTAX      Integer32
   MAX-ACCESS  read-create
   STATUS      current
   DESCRIPTION
       "The TCP/UDP destination port for matching the ECE. 
	   It only significant if protocol filter 'UDP' or 'TCP' is selected. 
	   The possible values are: 
		0:Any: No TCP/UDP destination port filter is specified. (Destination port filter status is don't-care.) 
		1:Specific: If you want to filter a specific TCP/UDP destination port No. with this ECE, choose this value. A field for entering a specific No. appears. 
		2:Range: If you want to filter a specific TCP/UDP destination port range filter with this ECE, choose this value. A field for entering a range appears."
   ::= {sm24dp4xaECEControlListConfEntry 56 }   
   
sm24dp4xaECECtlListConfIPv6DestRangeLow OBJECT-TYPE
   SYNTAX      Integer32
   MAX-ACCESS  read-create
   STATUS      current
   DESCRIPTION
       "When Range is selected for the destination port filter, you can enter a specific range. 
	   The allowed range is from 0 through 65535."
   ::= {sm24dp4xaECEControlListConfEntry 57 }    
   
sm24dp4xaECECtlListConfIPv6DestRangeHigh OBJECT-TYPE
   SYNTAX      Integer32
   MAX-ACCESS  read-create
   STATUS      current
   DESCRIPTION
       "When Range is selected for the destination port filter, you can enter a specific range. 
	   The allowed range is from 0 through 65535."
   ::= {sm24dp4xaECEControlListConfEntry 58 }    
   
sm24dp4xaECECtlListConfEgressOuterTagMode OBJECT-TYPE
   SYNTAX      Integer32
   MAX-ACCESS  read-create
   STATUS      current
   DESCRIPTION
       "The outer tag for nni-to-uni direction for the ECE. The possible values are: 
		1:Enable: Enable outer tag for nni-to-uni direction for the ECE. 
		0:Disable: Disable outer tag for nni-to-uni direction for the ECE."
   ::= {sm24dp4xaECEControlListConfEntry 59 }    
   
sm24dp4xaECECtlListConfEgressOuterTagPCPDEIPresv OBJECT-TYPE
   SYNTAX      Integer32
   MAX-ACCESS  read-create
   STATUS      current
   DESCRIPTION
       "The outer tag PCP and DEI preservation for the ECE. The possible values are: 
		1:Preserved: The outer tag PCP and DEI is preserved. 
		0:Fixed: The outer tag PCP and DEI is fixed."
   ::= {sm24dp4xaECEControlListConfEntry 61 }    
   
sm24dp4xaECECtlListConfEgressOuterTagPCP OBJECT-TYPE
   SYNTAX      Integer32
   MAX-ACCESS  read-create
   STATUS      current
   DESCRIPTION
       "The outer tag PCP value for the ECE. The allowed range is from 0 through 7."
   ::= {sm24dp4xaECEControlListConfEntry 62 }      

sm24dp4xaECECtlListConfEgressOuterTagDEI OBJECT-TYPE
   SYNTAX      Integer32
   MAX-ACCESS  read-create
   STATUS      current
   DESCRIPTION
       "The outer tag DEI value for the ECE. The allowed value is 0 or 1."
   ::= {sm24dp4xaECEControlListConfEntry 63 }   

sm24dp4xaECECtlListConfConflict OBJECT-TYPE
   SYNTAX      Integer32
   MAX-ACCESS  read-only
   STATUS      current
   DESCRIPTION
       "Indicates the hardware status of the specific ECE. 
	   The specific ECE is not applied to the hardware due to hardware limitations.
	   0:No
	   1:Yes"
   ::= {sm24dp4xaECEControlListConfEntry 69 }      
   
sm24dp4xaECECtlListConfRowStatus OBJECT-TYPE
   SYNTAX      RowStatus
   MAX-ACCESS  read-create
   STATUS      current
   DESCRIPTION
       "ECE Control List Conf Row Status."
   ::= {sm24dp4xaECEControlListConfEntry 70 }
   
   
sm24dp4xaEVCStatisticsTable  OBJECT-TYPE
   SYNTAX      SEQUENCE OF SM24DP4XAEVCStatisticsEntry
   MAX-ACCESS  not-accessible
   STATUS      current
   DESCRIPTION
       "A table of EVC Statistics."
   ::= { sm24dp4xaEVC 5 }

sm24dp4xaEVCStatisticsEntry OBJECT-TYPE
    SYNTAX        SM24DP4XAEVCStatisticsEntry
    MAX-ACCESS    not-accessible
    STATUS        current
    DESCRIPTION
        "An entry of EVC Statistics table."
    INDEX        { sm24dp4xaEVCStatisticsPort, sm24dp4xaEVCStatisticsClass}
    ::= { sm24dp4xaEVCStatisticsTable 1 }

SM24DP4XAEVCStatisticsEntry ::=
    SEQUENCE {
        sm24dp4xaEVCStatisticsPort                                     Integer32,
		sm24dp4xaEVCStatisticsClass                                    Integer32,
        sm24dp4xaEVCStatisticsGreenFramesRx                            Integer32,
		sm24dp4xaEVCStatisticsGreenFramesTx                            Integer32,
		sm24dp4xaEVCStatisticsYellowFramesRx                           Integer32,
		sm24dp4xaEVCStatisticsYellowFramesTx                           Integer32,
		sm24dp4xaEVCStatisticsRedFramesRx                              Integer32,
		sm24dp4xaEVCStatisticsDiscardedFramesGreen                     Integer32,
		sm24dp4xaEVCStatisticsDiscardedFramesYellow                    Integer32
    }

sm24dp4xaEVCStatisticsPort OBJECT-TYPE
   SYNTAX      Integer32 (1..65535)
   MAX-ACCESS  not-accessible
   STATUS      current
   DESCRIPTION
       "Port Index"
   ::= {sm24dp4xaEVCStatisticsEntry 1 }
   
sm24dp4xaEVCStatisticsClass OBJECT-TYPE
   SYNTAX      Integer32 (1..65535)
   MAX-ACCESS  not-accessible
   STATUS      current
   DESCRIPTION
       "Class Index, from 1-8"
   ::= {sm24dp4xaEVCStatisticsEntry 2 }

sm24dp4xaEVCStatisticsGreenFramesRx OBJECT-TYPE
   SYNTAX      Integer32
   MAX-ACCESS  read-only
   STATUS      current
   DESCRIPTION
       "The number of green received."
   ::= {sm24dp4xaEVCStatisticsEntry 3 }  
   
sm24dp4xaEVCStatisticsGreenFramesTx OBJECT-TYPE
   SYNTAX      Integer32
   MAX-ACCESS  read-only
   STATUS      current
   DESCRIPTION
       "The number of green transmitted."
   ::= {sm24dp4xaEVCStatisticsEntry 4 }   

sm24dp4xaEVCStatisticsYellowFramesRx OBJECT-TYPE
   SYNTAX      Integer32
   MAX-ACCESS  read-only
   STATUS      current
   DESCRIPTION
       "The number of yellow received."
   ::= {sm24dp4xaEVCStatisticsEntry 5 }    
   
sm24dp4xaEVCStatisticsYellowFramesTx OBJECT-TYPE
   SYNTAX      Integer32
   MAX-ACCESS  read-only
   STATUS      current
   DESCRIPTION
       "The number of yellow transmitted."
   ::= {sm24dp4xaEVCStatisticsEntry 6 }     
   
sm24dp4xaEVCStatisticsRedFramesRx OBJECT-TYPE
   SYNTAX      Integer32
   MAX-ACCESS  read-only
   STATUS      current
   DESCRIPTION
       "The number of red received."
   ::= {sm24dp4xaEVCStatisticsEntry 7 }    
   
sm24dp4xaEVCStatisticsDiscardedFramesGreen OBJECT-TYPE
   SYNTAX      Integer32
   MAX-ACCESS  read-only
   STATUS      current
   DESCRIPTION
       "The number of discarded in the green color."
   ::= {sm24dp4xaEVCStatisticsEntry 8 }    
  
sm24dp4xaEVCStatisticsDiscardedFramesYellow OBJECT-TYPE
   SYNTAX      Integer32
   MAX-ACCESS  read-only
   STATUS      current
   DESCRIPTION
       "The number of discarded in the yellow color."
   ::= {sm24dp4xaEVCStatisticsEntry 9 }    
   
   
sm24dp4xaEVCStatisticsClearTable  OBJECT-TYPE
   SYNTAX      SEQUENCE OF SM24DP4XAEVCStatisticsClearEntry
   MAX-ACCESS  not-accessible
   STATUS      current
   DESCRIPTION
       "A table of EVC Statistics Clear."
   ::= { sm24dp4xaEVC 6 }

sm24dp4xaEVCStatisticsClearEntry OBJECT-TYPE
    SYNTAX        SM24DP4XAEVCStatisticsClearEntry
    MAX-ACCESS    not-accessible
    STATUS        current
    DESCRIPTION
        "An entry of EVC Statistics Clear table."
    INDEX        { sm24dp4xaEVCStatisticsClearPort}
    ::= { sm24dp4xaEVCStatisticsClearTable 1 }

SM24DP4XAEVCStatisticsClearEntry ::=
    SEQUENCE {
        sm24dp4xaEVCStatisticsClearPort                Integer32,
		sm24dp4xaEVCStatisticsClear                    Integer32
    }


sm24dp4xaEVCStatisticsClearPort OBJECT-TYPE
   SYNTAX      Integer32 (1..65535)
   MAX-ACCESS  not-accessible
   STATUS      current
   DESCRIPTION
       "Port Index"
   ::= {sm24dp4xaEVCStatisticsClearEntry 1 }
   
sm24dp4xaEVCStatisticsClear OBJECT-TYPE
   SYNTAX      Integer32
   MAX-ACCESS  read-write
   STATUS      current
   DESCRIPTION
       "Clears the counters for selected ports."
   ::= {sm24dp4xaEVCStatisticsClearEntry 2 }

-- =======================================================================================================================

sm24dp4xaAggregation    OBJECT IDENTIFIER ::= { sm24dp4xaConfiguration 31 } 
    
sm24dp4xaAggregationStatic    OBJECT IDENTIFIER ::= { sm24dp4xaAggregation 1 } 

sm24dp4xaAggrSourceMACAddress   OBJECT-TYPE
               SYNTAX      Integer32 (0|1)
               MAX-ACCESS  read-write
               STATUS      current
               DESCRIPTION
                   "Source MAC Address"
               ::= { sm24dp4xaAggregationStatic 2 }

sm24dp4xaAggrDestinationMACAddress   OBJECT-TYPE
               SYNTAX      Integer32 (0|1)
               MAX-ACCESS  read-write
               STATUS      current
               DESCRIPTION
                   "Destination MAC Address"
               ::= { sm24dp4xaAggregationStatic 3 }
               
sm24dp4xaAggrIPAddress   OBJECT-TYPE
               SYNTAX      Integer32 (0|1)
               MAX-ACCESS  read-write
               STATUS      current
               DESCRIPTION
                   "IP Address"
               ::= { sm24dp4xaAggregationStatic 4 }

sm24dp4xaAggrTCPUDPPortNumber   OBJECT-TYPE
               SYNTAX      Integer32 (0|1)
               MAX-ACCESS  read-write
               STATUS      current
               DESCRIPTION
                   "TCP/UDP Port Number"
               ::= { sm24dp4xaAggregationStatic 5 }
               
               
sm24dp4xaAggrGroupConfigTable OBJECT-TYPE
   SYNTAX      SEQUENCE OF SM24DP4XAAggrGroupConfigEntry
   MAX-ACCESS  not-accessible
   STATUS      current
   DESCRIPTION
       " "
   ::= { sm24dp4xaAggregationStatic 6 }

sm24dp4xaAggrGroupConfigEntry OBJECT-TYPE
   SYNTAX      SM24DP4XAAggrGroupConfigEntry
   MAX-ACCESS  not-accessible
   STATUS      current
   DESCRIPTION
       " "
   INDEX    { sm24dp4xaAggrGroupConfigPort  }
   ::= { sm24dp4xaAggrGroupConfigTable 1 }

SM24DP4XAAggrGroupConfigEntry ::= SEQUENCE {
   sm24dp4xaAggrGroupConfigPort                 Integer32,
   sm24dp4xaAggrGroupConfigGroup                Integer32,
   sm24dp4xaAggrGroupConfig                     Integer32
}

sm24dp4xaAggrGroupConfigPort OBJECT-TYPE
   SYNTAX      Integer32 (1..65535)
   MAX-ACCESS  not-accessible
   STATUS      current
   DESCRIPTION
       "port index"
   ::= { sm24dp4xaAggrGroupConfigEntry 1 }
      
sm24dp4xaAggrGroupConfigGroup OBJECT-TYPE
   SYNTAX      Integer32
   MAX-ACCESS  not-accessible
   STATUS      current
   DESCRIPTION
       "group index"
   ::= { sm24dp4xaAggrGroupConfigEntry 2 }   

sm24dp4xaAggrGroupConfig OBJECT-TYPE
   SYNTAX      Integer32 (0|1)
   MAX-ACCESS  read-write
   STATUS      current
   DESCRIPTION
       "Aggregation Group Configuration"
   ::= { sm24dp4xaAggrGroupConfigEntry 3 }
   
   
sm24dp4xaAggrGroupStateTable OBJECT-TYPE
   SYNTAX      SEQUENCE OF SM24DP4XAAggrGroupStateEntry
   MAX-ACCESS  not-accessible
   STATUS      current
   DESCRIPTION
       " "
   ::= { sm24dp4xaAggregation 2 }

sm24dp4xaAggrGroupStateEntry OBJECT-TYPE
   SYNTAX      SM24DP4XAAggrGroupStateEntry
   MAX-ACCESS  not-accessible
   STATUS      current
   DESCRIPTION
       " "
   INDEX    { sm24dp4xaAggrGroupStateIndex  }
   ::= { sm24dp4xaAggrGroupStateTable 1 }

SM24DP4XAAggrGroupStateEntry ::= SEQUENCE {
   sm24dp4xaAggrGroupStateIndex             Integer32,
   sm24dp4xaAggrGroupStateAggrID            DisplayString,
   sm24dp4xaAggrGroupStateName              DisplayString,
   sm24dp4xaAggrGroupStateType              DisplayString,
   sm24dp4xaAggrGroupStateSpeed             DisplayString,   
   sm24dp4xaAggrGroupStateConfiguredPorts   DisplayString,
   sm24dp4xaAggrGroupStateAggregatedPorts   DisplayString, 
   sm24dp4xaAggrGroupStateAggregatedBandwidth   DisplayString 
}

sm24dp4xaAggrGroupStateIndex OBJECT-TYPE
   SYNTAX      Integer32 (1..65535)
   MAX-ACCESS  not-accessible
   STATUS      current
   DESCRIPTION
       "index"
   ::= { sm24dp4xaAggrGroupStateEntry 1 }
   
sm24dp4xaAggrGroupStateAggrID OBJECT-TYPE
   SYNTAX      DisplayString
   MAX-ACCESS  read-only
   STATUS      current
   DESCRIPTION
       "AggrID"
   ::= { sm24dp4xaAggrGroupStateEntry 2 }

sm24dp4xaAggrGroupStateName OBJECT-TYPE
   SYNTAX      DisplayString
   MAX-ACCESS  read-only
   STATUS      current
   DESCRIPTION
       "Name"
   ::= { sm24dp4xaAggrGroupStateEntry 3 }
   
sm24dp4xaAggrGroupStateType OBJECT-TYPE
   SYNTAX      DisplayString
   MAX-ACCESS  read-only
   STATUS      current
   DESCRIPTION
       "Type"
   ::= { sm24dp4xaAggrGroupStateEntry 4 }   
   
sm24dp4xaAggrGroupStateSpeed OBJECT-TYPE
   SYNTAX      DisplayString
   MAX-ACCESS  read-only
   STATUS      current
   DESCRIPTION
       "Speed"
   ::= { sm24dp4xaAggrGroupStateEntry 5 }
   
sm24dp4xaAggrGroupStateConfiguredPorts OBJECT-TYPE
   SYNTAX      DisplayString
   MAX-ACCESS  read-only
   STATUS      current
   DESCRIPTION
       "Configured Ports"
   ::= { sm24dp4xaAggrGroupStateEntry 6 }

sm24dp4xaAggrGroupStateAggregatedPorts OBJECT-TYPE
   SYNTAX      DisplayString
   MAX-ACCESS  read-only
   STATUS      current
   DESCRIPTION
       "Aggregated Ports"
   ::= { sm24dp4xaAggrGroupStateEntry 7 }   
   
sm24dp4xaAggrGroupStateAggregatedBandwidth OBJECT-TYPE
   SYNTAX      DisplayString
   MAX-ACCESS  read-only
   STATUS      current
   DESCRIPTION
       "Aggregated Bandwidth"
   ::= { sm24dp4xaAggrGroupStateEntry 8 }   
   
   
-- =======================================================================================================================
sm24dp4xaSecurity                                              OBJECT IDENTIFIER ::= { sm24dp4xaProductId 3 }

sm24dp4xaIPSourceGuard                                         OBJECT IDENTIFIER ::= { sm24dp4xaSecurity 1 }

sm24dp4xaIPSourceGuardConf                                     OBJECT IDENTIFIER ::= { sm24dp4xaIPSourceGuard 1 }

-- RowStatus Info:  createAndGo, notReady not supported.
-- =======================================================================================================================
-- Textual Conventions for the SM24DP4XA IP Source Guard Mib
-- =======================================================================================================================
--
--    sm24dp4xaIPSourceGuard        OBJECT IDENTIFIER  ::= { sm24dp4xaIPSourceGuardMIB 1 }
--    sm24dp4xaIPSourceGuardConf    OBJECT IDENTIFIER  ::= { sm24dp4xaIPSourceGuard 1 }

--
-- =======================================================================================================================
-- Start sm24dp4xaIPSourceGuard group
-- =======================================================================================================================
--sm24dp4xaIPSourceGuardConf

    sm24dp4xaIPSourceGuardMode OBJECT-TYPE
               SYNTAX      AdminMode
               MAX-ACCESS  read-write
               STATUS      current
               DESCRIPTION
                   "Enable the Global IP Source Guard or disable the
                    Global IP Source Guard."
               ::= {     sm24dp4xaIPSourceGuardConf 1 }

    sm24dp4xaIPSourceGuardDynamicToStaticCmd OBJECT-TYPE
               SYNTAX      ActivateCmd
               MAX-ACCESS  read-write
               STATUS      current
               DESCRIPTION
                   "Translate all dynamic entries to static entries."
               DEFVAL  { noAction }
               ::= {     sm24dp4xaIPSourceGuardConf 2 }

--sm24dp4xaIPSourceGuardPortConfigTable

    sm24dp4xaIPSourceGuardPortConfigTable OBJECT-TYPE
               SYNTAX      SEQUENCE OF     SM24DP4XAIPSourceGuardPortConfigEntry
               MAX-ACCESS  not-accessible
               STATUS      current
               DESCRIPTION
                   "The IP Source Guard Port Configuration Table.
                    INDEX for this table is ifIndex which is
                    equivalent to the panel port number."
               ::= {     sm24dp4xaIPSourceGuardConf 3 }

    sm24dp4xaIPSourceGuardPortConfigEntry OBJECT-TYPE
               SYNTAX          SM24DP4XAIPSourceGuardPortConfigEntry
               MAX-ACCESS  not-accessible
               STATUS      current
               DESCRIPTION
                   "The IP Source Guard Port Configuration Entry."
               INDEX    {    ifIndex  }
               ::= {     sm24dp4xaIPSourceGuardPortConfigTable 1 }

    SM24DP4XAIPSourceGuardPortConfigEntry             ::= SEQUENCE {
                 sm24dp4xaIPSourceGuardPortConfigMode            AdminMode,
                 sm24dp4xaIPSourceGuardPortMaxDynamicClients     Integer32
                 }

    sm24dp4xaIPSourceGuardPortConfigMode OBJECT-TYPE
               SYNTAX      AdminMode
               MAX-ACCESS  read-write
               STATUS      current
               DESCRIPTION
                   "Specify IP Source Guard is enabled on which ports."
               ::= {     sm24dp4xaIPSourceGuardPortConfigEntry 2 }

    sm24dp4xaIPSourceGuardPortMaxDynamicClients OBJECT-TYPE
               SYNTAX      Integer32(0..2|99)
               MAX-ACCESS  read-write
               STATUS      current
               DESCRIPTION
                   "Specify the maximum number of dynamic clients that can
                    be learned on given port.
                    default: 99
                    0~2: Max Dynamic clients
                    99:Unlimited "
               ::= {     sm24dp4xaIPSourceGuardPortConfigEntry 3 }

--sm24dp4xaIPSourceGuardStaticTable

    sm24dp4xaIPSourceGuardStaticTable OBJECT-TYPE
               SYNTAX      SEQUENCE OF     SM24DP4XAIPSourceGuardStaticEntry
               MAX-ACCESS  not-accessible
               STATUS      current
               DESCRIPTION
                   "The IP Source Guard Static Table."
               ::= {     sm24dp4xaIPSourceGuard 2 }

    sm24dp4xaIPSourceGuardStaticEntry OBJECT-TYPE
               SYNTAX          SM24DP4XAIPSourceGuardStaticEntry
               MAX-ACCESS  not-accessible
               STATUS      current
               DESCRIPTION
                   "The IP Source Guard Static Entry."
               INDEX    {    sm24dp4xaIPSourceGuardStaticIndex  }
               ::= {     sm24dp4xaIPSourceGuardStaticTable 1 }

    SM24DP4XAIPSourceGuardStaticEntry             ::= SEQUENCE {
                 sm24dp4xaIPSourceGuardStaticSwitchIndex   Integer32,
                 sm24dp4xaIPSourceGuardStaticIndex         Integer32,
                 sm24dp4xaIPSourceGuardStaticPort          Integer32,
                 sm24dp4xaIPSourceGuardStaticVLANId        Integer32,
                 sm24dp4xaIPSourceGuardStaticIPAddress     IpAddress,
                 sm24dp4xaIPSourceGuardStaticIPMask        IpAddress,
                 sm24dp4xaIPSourceGuardStaticMACAddress    DisplayString,
                 sm24dp4xaIPSourceGuardStaticRowStatus     RowStatus
                 }

    sm24dp4xaIPSourceGuardStaticSwitchIndex OBJECT-TYPE
               SYNTAX      Integer32(1..16)
               MAX-ACCESS  not-accessible
               STATUS      current
               DESCRIPTION
                   "Switch Index."
               ::= {     sm24dp4xaIPSourceGuardStaticEntry 1 }

    sm24dp4xaIPSourceGuardStaticIndex OBJECT-TYPE
               SYNTAX      Integer32(1..28)
               MAX-ACCESS  not-accessible
               STATUS      current
               DESCRIPTION
                   "The entry of table."
               ::= {     sm24dp4xaIPSourceGuardStaticEntry 2 }

    sm24dp4xaIPSourceGuardStaticPort OBJECT-TYPE
               SYNTAX      Integer32(1..255)
               MAX-ACCESS  read-create
               STATUS      current
               DESCRIPTION
                   "The port number of table.
                    range: 1 - port number."
               ::= {     sm24dp4xaIPSourceGuardStaticEntry 3 }

    sm24dp4xaIPSourceGuardStaticVLANId OBJECT-TYPE
               SYNTAX      Integer32(1..4095)
               MAX-ACCESS  read-create
               STATUS      current
               DESCRIPTION
                   "VLAN ID, range: 1 - 4095."
               ::= {     sm24dp4xaIPSourceGuardStaticEntry 4 }

    sm24dp4xaIPSourceGuardStaticIPAddress OBJECT-TYPE
               SYNTAX      IpAddress
               MAX-ACCESS  read-create
               STATUS      current
               DESCRIPTION
                   "IP address allowed for doing IP source guard."
               ::= {     sm24dp4xaIPSourceGuardStaticEntry 5 }

    sm24dp4xaIPSourceGuardStaticIPMask OBJECT-TYPE
               SYNTAX      IpAddress
               MAX-ACCESS  read-create
               STATUS      current
               DESCRIPTION
                   "IP Mask allowed for doing IP source guard."
               ::= {     sm24dp4xaIPSourceGuardStaticEntry 6 }

    sm24dp4xaIPSourceGuardStaticMACAddress OBJECT-TYPE
               SYNTAX      DisplayString
               MAX-ACCESS  read-create
               STATUS      current
               DESCRIPTION
                   "Allowed Source MAC address, format: 0a 1b 2c 3d 4e 5f."
               ::= {     sm24dp4xaIPSourceGuardStaticEntry 7 }

    sm24dp4xaIPSourceGuardStaticRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sm24dp4xaIPSourceGuardStaticEntry 8 }

--sm24dp4xaIPSourceGuardDynamicTable

    sm24dp4xaIPSourceGuardDynamicTable OBJECT-TYPE
               SYNTAX      SEQUENCE OF     SM24DP4XAIPSourceGuardDynamicEntry
               MAX-ACCESS  not-accessible
               STATUS      current
               DESCRIPTION
                   "The IP Source Guard Dynamic Table."
               ::= {     sm24dp4xaIPSourceGuard 3 }

    sm24dp4xaIPSourceGuardDynamicEntry OBJECT-TYPE
               SYNTAX          SM24DP4XAIPSourceGuardDynamicEntry
               MAX-ACCESS  not-accessible
               STATUS      current
               DESCRIPTION
                   "The IP Source Guard Dynamic Entry."
               INDEX    {    sm24dp4xaIPSourceGuardDynamicIndex  }
               ::= {     sm24dp4xaIPSourceGuardDynamicTable 1 }

    SM24DP4XAIPSourceGuardDynamicEntry             ::= SEQUENCE {
                 sm24dp4xaIPSourceGuardDynamicSwitchIndex    Integer32,
                 sm24dp4xaIPSourceGuardDynamicIndex          Integer32,
                 sm24dp4xaIPSourceGuardDynamicPort           Integer32,
                 sm24dp4xaIPSourceGuardDynamicVLANId         Integer32,
                 sm24dp4xaIPSourceGuardDynamicIPAddress      IpAddress,
                 sm24dp4xaIPSourceGuardDynamicMACAddress     DisplayString
                 }

    sm24dp4xaIPSourceGuardDynamicSwitchIndex OBJECT-TYPE
               SYNTAX      Integer32(1..16)
               MAX-ACCESS  not-accessible
               STATUS      current
               DESCRIPTION
                   "Switch Index."
               ::= {     sm24dp4xaIPSourceGuardDynamicEntry 1 }

    sm24dp4xaIPSourceGuardDynamicIndex OBJECT-TYPE
               SYNTAX      Integer32(1..4095)
               MAX-ACCESS  not-accessible
               STATUS      current
               DESCRIPTION
                   "The entry of table."
               ::= {     sm24dp4xaIPSourceGuardDynamicEntry 2 }

    sm24dp4xaIPSourceGuardDynamicPort OBJECT-TYPE
               SYNTAX      Integer32(1..255)
               MAX-ACCESS  read-only
               STATUS      current
               DESCRIPTION
                   "The logical port for the settings."
               ::= {     sm24dp4xaIPSourceGuardDynamicEntry 3 }

    sm24dp4xaIPSourceGuardDynamicVLANId OBJECT-TYPE
               SYNTAX      Integer32(1..4094)
               MAX-ACCESS  read-only
               STATUS      current
               DESCRIPTION
                   "The vlan id for the settings."
               ::= {     sm24dp4xaIPSourceGuardDynamicEntry 4 }

    sm24dp4xaIPSourceGuardDynamicIPAddress OBJECT-TYPE
               SYNTAX      IpAddress
               MAX-ACCESS  read-only
               STATUS      current
               DESCRIPTION
                   "Allowed Source IP address."
               ::= {     sm24dp4xaIPSourceGuardDynamicEntry 5 }

    sm24dp4xaIPSourceGuardDynamicMACAddress OBJECT-TYPE
               SYNTAX      DisplayString
               MAX-ACCESS  read-only
               STATUS      current
               DESCRIPTION
                   "Allowed Source MAC address."
               ::= {     sm24dp4xaIPSourceGuardDynamicEntry 6 }
-- =======================================================================================================================
sm24dp4xaARPInspection                                          OBJECT IDENTIFIER ::= { sm24dp4xaSecurity 2 }
-- RowStatus Info:  createAndGo, notReady not supported.
-- =======================================================================================================================
-- Textual Conventions for the sm24dp4xa Arp Mib
-- =======================================================================================================================
--
    sm24dp4xaARP                  OBJECT IDENTIFIER  ::= { sm24dp4xaARPInspection 1 }
    sm24dp4xaARPConfig            OBJECT IDENTIFIER  ::= { sm24dp4xaARP 1 }

--
-- =======================================================================================================================
-- Start sm24dp4xaARP group
-- =======================================================================================================================
--sm24dp4xaARPConfig

    sm24dp4xaARPConfMode OBJECT-TYPE
               SYNTAX      AdminMode
               MAX-ACCESS  read-write
               STATUS      current
               DESCRIPTION
                   "Enable the Global ARP Inspection or disable the Global
                    ARP Inspection."
               ::= {     sm24dp4xaARPConfig 1 }

--sm24dp4xaARPPortConfTable

    sm24dp4xaARPPortConfTable OBJECT-TYPE
               SYNTAX      SEQUENCE OF     SM24DP4XAARPPortConfEntry
               MAX-ACCESS  not-accessible
               STATUS      current
               DESCRIPTION
                   "The ARP Port Configuration Table."
               ::= {     sm24dp4xaARPConfig 3 }

    sm24dp4xaARPPortConfEntry OBJECT-TYPE
               SYNTAX          SM24DP4XAARPPortConfEntry
               MAX-ACCESS  not-accessible
               STATUS      current
               DESCRIPTION
                   "The ARP Port Configuration Entry."
               INDEX    {    sm24dp4xaARPPortConfPort  }
               ::= {     sm24dp4xaARPPortConfTable 1 }

    SM24DP4XAARPPortConfEntry             ::= SEQUENCE {
                 sm24dp4xaARPPortConfPort            Integer32,
                 sm24dp4xaARPPortConfMode            AdminMode,
                 sm24dp4xaARPPortConfCheckVLAN       AdminMode,
                 sm24dp4xaARPPortConfLogType         INTEGER
                 }

    sm24dp4xaARPPortConfPort OBJECT-TYPE
               SYNTAX      Integer32(1..255)
               MAX-ACCESS  not-accessible
               STATUS      current
               DESCRIPTION
                   "The port number for which the configuration below applies.
                    range: 1 - port number."
               ::= {     sm24dp4xaARPPortConfEntry 1 }

    sm24dp4xaARPPortConfMode OBJECT-TYPE
               SYNTAX      AdminMode
               MAX-ACCESS  read-write
               STATUS      current
               DESCRIPTION
                   "Specify ARP Inspection is enabled on which ports."
               ::= {     sm24dp4xaARPPortConfEntry 2 }

    sm24dp4xaARPPortConfCheckVLAN OBJECT-TYPE
               SYNTAX      AdminMode
               MAX-ACCESS  read-write
               STATUS      current
               DESCRIPTION
                   "When the setting of 'Check VLAN' is disabled, the log
                   type of ARP Inspection will refer to the port setting.
                   And the setting of 'Check VLAN' is enabled, the log type
                   of ARP Inspection will refer to the VLAN setting."
               ::= {     sm24dp4xaARPPortConfEntry 3 }

    sm24dp4xaARPPortConfLogType OBJECT-TYPE
               SYNTAX      INTEGER{none(0),deny(1),permit(2),all(3)}
               MAX-ACCESS  read-write
               STATUS      current
               DESCRIPTION
                   "The log type of ARP Inspection will refer to the
                    port setting.
                    0: none,
                    1: deny,
                    2: permit,
                    3: all,
                    range: 0-3."
               ::= {     sm24dp4xaARPPortConfEntry 4 }

--sm24dp4xaARPVlanConfig

    sm24dp4xaARPVlanConfigTable OBJECT-TYPE
               SYNTAX      SEQUENCE OF     SM24DP4XAARPVlanConfigEntry
               MAX-ACCESS  not-accessible
               STATUS      current
               DESCRIPTION
                   "The ARP Vlan Configuration Table."
               ::= {     sm24dp4xaARP 2 }

    sm24dp4xaARPVlanConfigEntry OBJECT-TYPE
               SYNTAX          SM24DP4XAARPVlanConfigEntry
               MAX-ACCESS  not-accessible
               STATUS      current
               DESCRIPTION
                   "The ARP Vlan Configuration Entry."
               INDEX    {    sm24dp4xaARPVlanConfigVlan  }
               ::= {     sm24dp4xaARPVlanConfigTable 1 }

    SM24DP4XAARPVlanConfigEntry             ::= SEQUENCE {
                 sm24dp4xaARPVlanConfigVlan       Integer32,
                 sm24dp4xaARPVlanConfigLogType    INTEGER,
                 sm24dp4xaARPVlanConfigRowStatus  RowStatus
                 }

    sm24dp4xaARPVlanConfigVlan OBJECT-TYPE
               SYNTAX      Integer32(1..4095)
               MAX-ACCESS  not-accessible
               STATUS      current
               DESCRIPTION
                   "Specify ARP Inspection is enabled on which VLANs.
                    range: 1 - 4095."
               ::= {     sm24dp4xaARPVlanConfigEntry 1 }

    sm24dp4xaARPVlanConfigLogType OBJECT-TYPE
               SYNTAX      INTEGER{none(0),deny(1),permit(2),all(3)}
               MAX-ACCESS  read-create
               STATUS      current
               DESCRIPTION
                   "The log type also can be configured on per VLAN setting.
                    0: none,
                    1: deny,
                    2: permit,
                    3: all,
                    range: 0-3."
               ::= {     sm24dp4xaARPVlanConfigEntry 2 }

    sm24dp4xaARPVlanConfigRowStatus OBJECT-TYPE
               SYNTAX      RowStatus
               MAX-ACCESS  read-create
               STATUS      current
               DESCRIPTION
                   "This object indicates the status of this entry, and is
                    used to create/delete entries.  Any object in an entry of
                    this table may be modified while the value of the
                    corresponding instance of this object is active(1).
                    createAndGo, notReady not supported."
               ::= {     sm24dp4xaARPVlanConfigEntry 3 }

--sm24dp4xaARPStaticTable

    sm24dp4xaARPStaticTable OBJECT-TYPE
               SYNTAX      SEQUENCE OF     SM24DP4XAARPStaticEntry
               MAX-ACCESS  not-accessible
               STATUS      current
               DESCRIPTION
                   "The ARP Static Table."
               ::= {     sm24dp4xaARP 3 }

    sm24dp4xaARPStaticEntry OBJECT-TYPE
               SYNTAX          SM24DP4XAARPStaticEntry
               MAX-ACCESS  not-accessible
               STATUS      current
               DESCRIPTION
                   "The ARP Static Entry."
               INDEX    {    sm24dp4xaARPStaticIndex  }
               ::= {     sm24dp4xaARPStaticTable 1 }

    SM24DP4XAARPStaticEntry             ::= SEQUENCE {
                 sm24dp4xaARPStaticSwitchIndex   Integer32,
                 sm24dp4xaARPStaticIndex         Integer32,
                 sm24dp4xaARPStaticPort          Integer32,
                 sm24dp4xaARPStaticVlanID        Integer32,
                 sm24dp4xaARPStaticMACAddress    DisplayString,
                 sm24dp4xaARPStaticIPAddress     IpAddress,
                 sm24dp4xaARPStaticRowStatus     RowStatus
                 }


    sm24dp4xaARPStaticSwitchIndex OBJECT-TYPE
               SYNTAX      Integer32(1..16)
               MAX-ACCESS  not-accessible
               STATUS      current
               DESCRIPTION
                   "Switch Index."
               ::= {     sm24dp4xaARPStaticEntry 1 }

    sm24dp4xaARPStaticIndex OBJECT-TYPE
               SYNTAX      Integer32(1..255)
               MAX-ACCESS  not-accessible
               STATUS      current
               DESCRIPTION
                   "The entry of table."
               ::= {     sm24dp4xaARPStaticEntry 2 }

    sm24dp4xaARPStaticPort OBJECT-TYPE
               SYNTAX      Integer32(1..255)
               MAX-ACCESS  read-create
               STATUS      current
               DESCRIPTION
                   "The logical port for the settings.
                    range: 1 - port number."
               ::= {     sm24dp4xaARPStaticEntry 3 }

    sm24dp4xaARPStaticVlanID OBJECT-TYPE
               SYNTAX      Integer32(1..4095)
               MAX-ACCESS  read-create
               STATUS      current
               DESCRIPTION
                   "The vlan id for the settings.
                    range: 1-4095."
               ::= {     sm24dp4xaARPStaticEntry 4 }

    sm24dp4xaARPStaticMACAddress OBJECT-TYPE
               SYNTAX      DisplayString
               MAX-ACCESS  read-create
               STATUS      current
               DESCRIPTION
                   "Allowed Source MAC address in ARP request packets."
               ::= {     sm24dp4xaARPStaticEntry 5 }

    sm24dp4xaARPStaticIPAddress OBJECT-TYPE
               SYNTAX      IpAddress
               MAX-ACCESS  read-create
               STATUS      current
               DESCRIPTION
                   "Allowed Source IP address in ARP request packets."
               ::= {     sm24dp4xaARPStaticEntry 6 }

    sm24dp4xaARPStaticRowStatus OBJECT-TYPE
               SYNTAX      RowStatus
               MAX-ACCESS  read-create
               STATUS      current
               DESCRIPTION
                   "This object indicates the status of this entry, and is
                   used to create/delete entries.  Any object in an entry of
                   this table may be modified while the value of the
                   corresponding instance of this object is active(1).
                   createAndGo, notReady not supported."
               ::= {     sm24dp4xaARPStaticEntry 7 }

--sm24dp4xaARPDynamicTable

    sm24dp4xaARPDynamicTable OBJECT-TYPE
               SYNTAX      SEQUENCE OF     SM24DP4XAARPDynamicEntry
               MAX-ACCESS  not-accessible
               STATUS      current
               DESCRIPTION
                   "The ARP Dynamic Table."
               ::= {    sm24dp4xaARP 4 }

    sm24dp4xaARPDynamicEntry OBJECT-TYPE
               SYNTAX          SM24DP4XAARPDynamicEntry
               MAX-ACCESS  not-accessible
               STATUS      current
               DESCRIPTION
                   "The ARP Dynamic Entry."
               INDEX    {   sm24dp4xaARPDynamicIndex  }
               ::= {    sm24dp4xaARPDynamicTable 1 }

    SM24DP4XAARPDynamicEntry             ::= SEQUENCE {
                 sm24dp4xaARPDynamicIndex          Integer32,
                 sm24dp4xaARPDynamicPort           Integer32,
                 sm24dp4xaARPDynamicVLANId         Integer32,
                 sm24dp4xaARPDynamicMACAddress     MacAddress,
                 sm24dp4xaARPDynamicIPAddress      IpAddress,
                 sm24dp4xaARPDynamicToStaticCmd    INTEGER
                 }

    sm24dp4xaARPDynamicIndex OBJECT-TYPE
               SYNTAX      Integer32(1..4095)
               MAX-ACCESS  not-accessible
               STATUS      current
               DESCRIPTION
                   "The entry of table."
               ::= {    sm24dp4xaARPDynamicEntry 1 }

    sm24dp4xaARPDynamicPort OBJECT-TYPE
               SYNTAX      Integer32(1..255)
               MAX-ACCESS  read-only
               STATUS      current
               DESCRIPTION
                   "Switch Port Number for which the entries are displayed."
               ::= {    sm24dp4xaARPDynamicEntry 2 }

    sm24dp4xaARPDynamicVLANId OBJECT-TYPE
               SYNTAX      Integer32(1..4095)
               MAX-ACCESS  read-only
               STATUS      current
               DESCRIPTION
                   "VLAN-ID in which the ARP traffic is permitted."
               ::= {    sm24dp4xaARPDynamicEntry 3 }

    sm24dp4xaARPDynamicMACAddress OBJECT-TYPE
               SYNTAX      MacAddress
               MAX-ACCESS  read-only
               STATUS      current
               DESCRIPTION
                   "User MAC address of the entry."
               ::= {    sm24dp4xaARPDynamicEntry 4 }

    sm24dp4xaARPDynamicIPAddress OBJECT-TYPE
               SYNTAX      IpAddress
               MAX-ACCESS  read-only
               STATUS      current
               DESCRIPTION
                   "User IP address of the entry."
               ::= {    sm24dp4xaARPDynamicEntry 5 }

    sm24dp4xaARPDynamicToStaticCmd OBJECT-TYPE
               SYNTAX      ActivateCmd
               MAX-ACCESS  read-write
               STATUS      current
               DESCRIPTION
                   "Enable the Global ARP Inspection or disable the Global
                    ARP Inspection."
               ::= {     sm24dp4xaARPDynamicEntry 6 }


-- =======================================================================================================================
-- sm24dp4xaARPConformance
-- =======================================================================================================================
sm24dp4xaARPConformance OBJECT IDENTIFIER ::= { sm24dp4xaARPInspection 200 }

sm24dp4xaARPCompliances OBJECT IDENTIFIER ::= { sm24dp4xaARPConformance 1 }

sm24dp4xaARPGroups      OBJECT IDENTIFIER ::= { sm24dp4xaARPConformance 2 }

sm24dp4xaARPGroup OBJECT-GROUP
    OBJECTS {
                -- sm24dp4xaARPConfig
                sm24dp4xaARPConfMode,

                --sm24dp4xaARPPortConfTable
                sm24dp4xaARPPortConfMode,
                sm24dp4xaARPPortConfCheckVLAN,
                sm24dp4xaARPPortConfLogType,

                --sm24dp4xaARPVlanConfig
                sm24dp4xaARPVlanConfigLogType,
                sm24dp4xaARPVlanConfigRowStatus,

                --sm24dp4xaARPStaticTable
                sm24dp4xaARPStaticPort,
                sm24dp4xaARPStaticVlanID,
                sm24dp4xaARPStaticMACAddress,
                sm24dp4xaARPStaticIPAddress,
                sm24dp4xaARPStaticRowStatus,

                --sm24dp4xaARPDynamicTable
                sm24dp4xaARPDynamicPort,
                sm24dp4xaARPDynamicVLANId,
                sm24dp4xaARPDynamicMACAddress,
                sm24dp4xaARPDynamicIPAddress,
                sm24dp4xaARPDynamicToStaticCmd
            }
     STATUS  current
     DESCRIPTION
            "The collection of objects which are used to indicate
            sm24dp4xa ARP information."
    ::= { sm24dp4xaARPGroups 1 }

-- =======================================================================================================================
sm24dp4xaDHCPSnooping                                          OBJECT IDENTIFIER ::= { sm24dp4xaSecurity 3 }

sm24dp4xaDHCPSnoopingConf                                          OBJECT IDENTIFIER ::= { sm24dp4xaDHCPSnooping 1 }

sm24dp4xaDHCPSnoopingMode OBJECT-TYPE
   SYNTAX      Integer32(0|1)
   MAX-ACCESS  read-write
   STATUS      current
   DESCRIPTION
       "default: 0
       0: disable
       1: enable"
   ::= { sm24dp4xaDHCPSnoopingConf 1 }

sm24dp4xaDHCPSnoopingPortModeConfigurationTable OBJECT-TYPE
   SYNTAX      SEQUENCE OF SM24DP4XADHCPSnoopingPortModeConfigurationEntry
   MAX-ACCESS  not-accessible
   STATUS      current
   DESCRIPTION
       " "
   ::= { sm24dp4xaDHCPSnoopingConf 2 }

sm24dp4xaDHCPSnoopingPortModeConfigurationEntry OBJECT-TYPE
   SYNTAX      SM24DP4XADHCPSnoopingPortModeConfigurationEntry
   MAX-ACCESS  not-accessible
   STATUS      current
   DESCRIPTION
       " "
   INDEX    { sm24dp4xaDHCPSnoopingPortModeConfigurationPort  }
   ::= { sm24dp4xaDHCPSnoopingPortModeConfigurationTable 1 }

SM24DP4XADHCPSnoopingPortModeConfigurationEntry ::= SEQUENCE {
   sm24dp4xaDHCPSnoopingPortModeConfigurationPort	Integer32,
   sm24dp4xaDHCPSnoopingPortModeConfigurationMode	Integer32
}

sm24dp4xaDHCPSnoopingPortModeConfigurationPort OBJECT-TYPE
   SYNTAX      Integer32(1..4095)
   MAX-ACCESS  not-accessible
   STATUS      current
   DESCRIPTION
       " "
   ::= { sm24dp4xaDHCPSnoopingPortModeConfigurationEntry 1 }

sm24dp4xaDHCPSnoopingPortModeConfigurationMode OBJECT-TYPE
   SYNTAX      Integer32 (0|1)
   MAX-ACCESS  read-write
   STATUS      current
   DESCRIPTION
       "default: 1
       0: trust port mode
       1: untrust port mode"
   ::= { sm24dp4xaDHCPSnoopingPortModeConfigurationEntry 2 }

sm24dp4xaDHCPSnoopingStatisticsTable OBJECT-TYPE
   SYNTAX      SEQUENCE OF SM24DP4XADHCPSnoopingStatisticsEntry
   MAX-ACCESS  not-accessible
   STATUS      current
   DESCRIPTION
       " "
   ::= { sm24dp4xaDHCPSnooping 2 }

sm24dp4xaDHCPSnoopingStatisticsEntry OBJECT-TYPE
   SYNTAX      SM24DP4XADHCPSnoopingStatisticsEntry
   MAX-ACCESS  not-accessible
   STATUS      current
   DESCRIPTION
       " "
   INDEX    { sm24dp4xaDHCPSnoopingStatisticsPort  }
   ::= { sm24dp4xaDHCPSnoopingStatisticsTable 1 }

SM24DP4XADHCPSnoopingStatisticsEntry ::= SEQUENCE {
   sm24dp4xaDHCPSnoopingStatisticsPort         Integer32,
   sm24dp4xaDHCPSnoopingStatisticsClear        Integer32,
   sm24dp4xaDHCPSnoopingRxDiscover             Counter32,
   sm24dp4xaDHCPSnoopingRxOffer                Counter32,
   sm24dp4xaDHCPSnoopingRxRequest              Counter32,
   sm24dp4xaDHCPSnoopingRxDecline              Counter32,
   sm24dp4xaDHCPSnoopingRxACK                  Counter32,
   sm24dp4xaDHCPSnoopingRxNAK                  Counter32,
   sm24dp4xaDHCPSnoopingRxRelease              Counter32,
   sm24dp4xaDHCPSnoopingRxInform               Counter32,
   sm24dp4xaDHCPSnoopingRxLeaseQuery           Counter32,
   sm24dp4xaDHCPSnoopingRxLeaseUnassigned      Counter32,
   sm24dp4xaDHCPSnoopingRxLeaseUnknown         Counter32,
   sm24dp4xaDHCPSnoopingRxLeaseActive          Counter32,
   sm24dp4xaDHCPSnoopingTxDiscover             Counter32,
   sm24dp4xaDHCPSnoopingTxOffer                Counter32,
   sm24dp4xaDHCPSnoopingTxRequest              Counter32,
   sm24dp4xaDHCPSnoopingTxDecline              Counter32,
   sm24dp4xaDHCPSnoopingTxACK                  Counter32,
   sm24dp4xaDHCPSnoopingTxNAK                  Counter32,
   sm24dp4xaDHCPSnoopingTxRelease              Counter32,
   sm24dp4xaDHCPSnoopingTxInform               Counter32,
   sm24dp4xaDHCPSnoopingTxLeaseQuery           Counter32,
   sm24dp4xaDHCPSnoopingTxLeaseUnassigned      Counter32,
   sm24dp4xaDHCPSnoopingTxLeaseUnknown         Counter32,
   sm24dp4xaDHCPSnoopingTxLeaseActive          Counter32,
   sm24dp4xaDHCPSnoopingRxDiscardedChecksumError  Counter32,
   sm24dp4xaDHCPSnoopingRxDiscardedFromUntrusted  Counter32
}

sm24dp4xaDHCPSnoopingStatisticsPort OBJECT-TYPE
   SYNTAX      Integer32(1..4095)
   MAX-ACCESS  not-accessible
   STATUS      current
   DESCRIPTION
       " "
   ::= { sm24dp4xaDHCPSnoopingStatisticsEntry 1 }

sm24dp4xaDHCPSnoopingStatisticsClear OBJECT-TYPE
   SYNTAX      Integer32 (0|1)
   MAX-ACCESS  read-write
   STATUS      current
   DESCRIPTION
       "default: 0
       0: none
       1: clear"
   ::= { sm24dp4xaDHCPSnoopingStatisticsEntry 2 }

sm24dp4xaDHCPSnoopingRxDiscover OBJECT-TYPE
   SYNTAX      Counter32
   MAX-ACCESS  read-only
   STATUS      current
   DESCRIPTION
       " "
   ::= { sm24dp4xaDHCPSnoopingStatisticsEntry 3 }

sm24dp4xaDHCPSnoopingRxOffer OBJECT-TYPE
   SYNTAX      Counter32
   MAX-ACCESS  read-only
   STATUS      current
   DESCRIPTION
       " "
   ::= { sm24dp4xaDHCPSnoopingStatisticsEntry 4 }

sm24dp4xaDHCPSnoopingRxRequest OBJECT-TYPE
   SYNTAX      Counter32
   MAX-ACCESS  read-only
   STATUS      current
   DESCRIPTION
       " "
   ::= { sm24dp4xaDHCPSnoopingStatisticsEntry 5 }

sm24dp4xaDHCPSnoopingRxDecline OBJECT-TYPE
   SYNTAX      Counter32
   MAX-ACCESS  read-only
   STATUS      current
   DESCRIPTION
       " "
   ::= { sm24dp4xaDHCPSnoopingStatisticsEntry 6 }

sm24dp4xaDHCPSnoopingRxACK OBJECT-TYPE
   SYNTAX      Counter32
   MAX-ACCESS  read-only
   STATUS      current
   DESCRIPTION
       " "
   ::= { sm24dp4xaDHCPSnoopingStatisticsEntry 7 }

sm24dp4xaDHCPSnoopingRxNAK OBJECT-TYPE
   SYNTAX      Counter32
   MAX-ACCESS  read-only
   STATUS      current
   DESCRIPTION
       " "
   ::= { sm24dp4xaDHCPSnoopingStatisticsEntry 8 }

sm24dp4xaDHCPSnoopingRxRelease OBJECT-TYPE
   SYNTAX      Counter32
   MAX-ACCESS  read-only
   STATUS      current
   DESCRIPTION
       " "
   ::= { sm24dp4xaDHCPSnoopingStatisticsEntry 9 }

sm24dp4xaDHCPSnoopingRxInform OBJECT-TYPE
   SYNTAX      Counter32
   MAX-ACCESS  read-only
   STATUS      current
   DESCRIPTION
       " "
   ::= { sm24dp4xaDHCPSnoopingStatisticsEntry 10 }

sm24dp4xaDHCPSnoopingRxLeaseQuery OBJECT-TYPE
   SYNTAX      Counter32
   MAX-ACCESS  read-only
   STATUS      current
   DESCRIPTION
       " "
   ::= { sm24dp4xaDHCPSnoopingStatisticsEntry 11 }

sm24dp4xaDHCPSnoopingRxLeaseUnassigned OBJECT-TYPE
   SYNTAX      Counter32
   MAX-ACCESS  read-only
   STATUS      current
   DESCRIPTION
       " "
   ::= { sm24dp4xaDHCPSnoopingStatisticsEntry 12 }

sm24dp4xaDHCPSnoopingRxLeaseUnknown OBJECT-TYPE
   SYNTAX      Counter32
   MAX-ACCESS  read-only
   STATUS      current
   DESCRIPTION
       " "
   ::= { sm24dp4xaDHCPSnoopingStatisticsEntry 13 }

sm24dp4xaDHCPSnoopingRxLeaseActive OBJECT-TYPE
   SYNTAX      Counter32
   MAX-ACCESS  read-only
   STATUS      current
   DESCRIPTION
       " "
   ::= { sm24dp4xaDHCPSnoopingStatisticsEntry 14 }

sm24dp4xaDHCPSnoopingTxDiscover OBJECT-TYPE
   SYNTAX      Counter32
   MAX-ACCESS  read-only
   STATUS      current
   DESCRIPTION
       " "
   ::= { sm24dp4xaDHCPSnoopingStatisticsEntry 15 }

sm24dp4xaDHCPSnoopingTxOffer OBJECT-TYPE
   SYNTAX      Counter32
   MAX-ACCESS  read-only
   STATUS      current
   DESCRIPTION
       " "
   ::= { sm24dp4xaDHCPSnoopingStatisticsEntry 16 }

sm24dp4xaDHCPSnoopingTxRequest OBJECT-TYPE
   SYNTAX      Counter32
   MAX-ACCESS  read-only
   STATUS      current
   DESCRIPTION
       " "
   ::= { sm24dp4xaDHCPSnoopingStatisticsEntry 17 }

sm24dp4xaDHCPSnoopingTxDecline OBJECT-TYPE
   SYNTAX      Counter32
   MAX-ACCESS  read-only
   STATUS      current
   DESCRIPTION
       " "
   ::= { sm24dp4xaDHCPSnoopingStatisticsEntry 18 }

sm24dp4xaDHCPSnoopingTxACK OBJECT-TYPE
   SYNTAX      Counter32
   MAX-ACCESS  read-only
   STATUS      current
   DESCRIPTION
       " "
   ::= { sm24dp4xaDHCPSnoopingStatisticsEntry 19 }

sm24dp4xaDHCPSnoopingTxNAK OBJECT-TYPE
   SYNTAX      Counter32
   MAX-ACCESS  read-only
   STATUS      current
   DESCRIPTION
       " "
   ::= { sm24dp4xaDHCPSnoopingStatisticsEntry 20 }

sm24dp4xaDHCPSnoopingTxRelease OBJECT-TYPE
   SYNTAX      Counter32
   MAX-ACCESS  read-only
   STATUS      current
   DESCRIPTION
       " "
   ::= { sm24dp4xaDHCPSnoopingStatisticsEntry 21 }

sm24dp4xaDHCPSnoopingTxInform OBJECT-TYPE
   SYNTAX      Counter32
   MAX-ACCESS  read-only
   STATUS      current
   DESCRIPTION
       " "
   ::= { sm24dp4xaDHCPSnoopingStatisticsEntry 22 }

sm24dp4xaDHCPSnoopingTxLeaseQuery OBJECT-TYPE
   SYNTAX      Counter32
   MAX-ACCESS  read-only
   STATUS      current
   DESCRIPTION
       " "
   ::= { sm24dp4xaDHCPSnoopingStatisticsEntry 23 }

sm24dp4xaDHCPSnoopingTxLeaseUnassigned OBJECT-TYPE
   SYNTAX      Counter32
   MAX-ACCESS  read-only
   STATUS      current
   DESCRIPTION
       " "
   ::= { sm24dp4xaDHCPSnoopingStatisticsEntry 24 }

sm24dp4xaDHCPSnoopingTxLeaseUnknown OBJECT-TYPE
   SYNTAX      Counter32
   MAX-ACCESS  read-only
   STATUS      current
   DESCRIPTION
       " "
   ::= { sm24dp4xaDHCPSnoopingStatisticsEntry 25 }

sm24dp4xaDHCPSnoopingTxLeaseActive OBJECT-TYPE
   SYNTAX      Counter32
   MAX-ACCESS  read-only
   STATUS      current
   DESCRIPTION
       " "
   ::= { sm24dp4xaDHCPSnoopingStatisticsEntry 26 }

sm24dp4xaDHCPSnoopingRxDiscardedChecksumError OBJECT-TYPE
   SYNTAX      Counter32
   MAX-ACCESS  read-only
   STATUS      current
   DESCRIPTION
       " "
   ::= { sm24dp4xaDHCPSnoopingStatisticsEntry 27 }

sm24dp4xaDHCPSnoopingRxDiscardedFromUntrusted OBJECT-TYPE
   SYNTAX      Counter32
   MAX-ACCESS  read-only
   STATUS      current
   DESCRIPTION
       " "
   ::= { sm24dp4xaDHCPSnoopingStatisticsEntry 28 }

sm24dp4xaDHCPRelay                                             OBJECT IDENTIFIER ::= { sm24dp4xaSecurity 4 }

sm24dp4xaDHCPRelayConfiguration                                         OBJECT IDENTIFIER ::= { sm24dp4xaDHCPRelay 1 }

sm24dp4xaDHCPRelayMode OBJECT-TYPE
   SYNTAX      Integer32(0|1)
   MAX-ACCESS  read-write
   STATUS      current
   DESCRIPTION
       "default: 0
       0: disable
       1: enable
       We need at least one server"
   ::= { sm24dp4xaDHCPRelayConfiguration 1 }

sm24dp4xaDHCPRelayServer OBJECT-TYPE
   SYNTAX      IpAddress
   MAX-ACCESS  read-write
   STATUS      current
   DESCRIPTION
       " "
   ::= { sm24dp4xaDHCPRelayConfiguration 2 }

sm24dp4xaDHCPRelayInformationMode OBJECT-TYPE
   SYNTAX      Integer32(0|1)
   MAX-ACCESS  read-write
   STATUS      current
   DESCRIPTION
       "default: 0
       0: disable
       1: enable "
   ::= { sm24dp4xaDHCPRelayConfiguration 3 }

sm24dp4xaDHCPRelayInformationPolicy OBJECT-TYPE
   SYNTAX      Integer32(0..2)
   MAX-ACCESS  read-write
   STATUS      current
   DESCRIPTION
       "default: 0
       0: replace
       1: keep
       2: drop "
   ::= { sm24dp4xaDHCPRelayConfiguration 4 }

sm24dp4xaDHCPRelayStatistics                                   OBJECT IDENTIFIER ::= { sm24dp4xaDHCPRelay 2 }

sm24dp4xaDHCPRelayServerStatistics                                   OBJECT IDENTIFIER ::= { sm24dp4xaDHCPRelayStatistics 1 }

sm24dp4xaServerStatTransmitToServer OBJECT-TYPE
   SYNTAX      Counter32
   MAX-ACCESS  read-only
   STATUS      current
   DESCRIPTION
       " "
   ::= { sm24dp4xaDHCPRelayServerStatistics 1 }

sm24dp4xaServerStatTransmitError OBJECT-TYPE
   SYNTAX      Counter32
   MAX-ACCESS  read-only
   STATUS      current
   DESCRIPTION
       " "
   ::= { sm24dp4xaDHCPRelayServerStatistics 2 }

sm24dp4xaServerStatReceiveFromServer OBJECT-TYPE
   SYNTAX      Counter32
   MAX-ACCESS  read-only
   STATUS      current
   DESCRIPTION
       " "
   ::= { sm24dp4xaDHCPRelayServerStatistics 3 }

sm24dp4xaServerStatReceiveMissingAgentOption OBJECT-TYPE
   SYNTAX      Counter32
   MAX-ACCESS  read-only
   STATUS      current
   DESCRIPTION
       " "
   ::= { sm24dp4xaDHCPRelayServerStatistics 4 }

sm24dp4xaServerStatReceiveMissingCircuitID OBJECT-TYPE
   SYNTAX      Counter32
   MAX-ACCESS  read-only
   STATUS      current
   DESCRIPTION
       " "
   ::= { sm24dp4xaDHCPRelayServerStatistics 5 }

sm24dp4xaServerStatReceiveMissingRemoteID OBJECT-TYPE
   SYNTAX      Counter32
   MAX-ACCESS  read-only
   STATUS      current
   DESCRIPTION
       " "
   ::= { sm24dp4xaDHCPRelayServerStatistics 6 }

sm24dp4xaServerStatReceiveBadCircuitID OBJECT-TYPE
   SYNTAX      Counter32
   MAX-ACCESS  read-only
   STATUS      current
   DESCRIPTION
       " "
   ::= { sm24dp4xaDHCPRelayServerStatistics 7 }

sm24dp4xaServerStatReceiveBadRemoteID OBJECT-TYPE
   SYNTAX      Counter32
   MAX-ACCESS  read-only
   STATUS      current
   DESCRIPTION
       " "
   ::= { sm24dp4xaDHCPRelayServerStatistics 8 }

sm24dp4xaDHCPRelayClientStatistics                                   OBJECT IDENTIFIER ::= { sm24dp4xaDHCPRelayStatistics 2 }

sm24dp4xaClientStatTransmitToClient OBJECT-TYPE
   SYNTAX      Counter32
   MAX-ACCESS  read-only
   STATUS      current
   DESCRIPTION
       " "
   ::= { sm24dp4xaDHCPRelayClientStatistics 1 }

sm24dp4xaClientStatTransmitError OBJECT-TYPE
   SYNTAX      Counter32
   MAX-ACCESS  read-only
   STATUS      current
   DESCRIPTION
       " "
   ::= { sm24dp4xaDHCPRelayClientStatistics 2 }

sm24dp4xaClientStatReceivefromClient OBJECT-TYPE
   SYNTAX      Counter32
   MAX-ACCESS  read-only
   STATUS      current
   DESCRIPTION
       " "
   ::= { sm24dp4xaDHCPRelayClientStatistics 3 }

sm24dp4xaClientStatReceiveAgentOption OBJECT-TYPE
   SYNTAX      Counter32
   MAX-ACCESS  read-only
   STATUS      current
   DESCRIPTION
       " "
   ::= { sm24dp4xaDHCPRelayClientStatistics 4 }

sm24dp4xaClientStatReplaceAgentOption OBJECT-TYPE
   SYNTAX      Counter32
   MAX-ACCESS  read-only
   STATUS      current
   DESCRIPTION
       " "
   ::= { sm24dp4xaDHCPRelayClientStatistics 5 }

sm24dp4xaClientStatKeepAgentOption OBJECT-TYPE
   SYNTAX      Counter32
   MAX-ACCESS  read-only
   STATUS      current
   DESCRIPTION
       " "
   ::= { sm24dp4xaDHCPRelayClientStatistics 6 }

sm24dp4xaClientStatDropAgentOption OBJECT-TYPE
   SYNTAX      Counter32
   MAX-ACCESS  read-only
   STATUS      current
   DESCRIPTION
       " "
   ::= { sm24dp4xaDHCPRelayClientStatistics 7 }

sm24dp4xaPortSecurity                                          OBJECT IDENTIFIER ::= { sm24dp4xaSecurity 5 }

sm24dp4xaPortSecLimitCtrl                                      OBJECT IDENTIFIER ::= { sm24dp4xaPortSecurity 1 }

sm24dp4xaPortSecLimitCtrlSystemConf                                      OBJECT IDENTIFIER ::= { sm24dp4xaPortSecLimitCtrl 1 }

sm24dp4xaPortSecurityMode OBJECT-TYPE
   SYNTAX      Integer32(0|1)
   MAX-ACCESS  read-write
   STATUS      current
   DESCRIPTION
       "default: 0
       0: disable
       1: enable "
   ::= { sm24dp4xaPortSecLimitCtrlSystemConf 1 }

sm24dp4xaPortSecurityAging OBJECT-TYPE
   SYNTAX      Integer32(0|1)
   MAX-ACCESS  read-write
   STATUS      current
   DESCRIPTION
       "default: 0
       0: disable
       1: enable "
   ::= { sm24dp4xaPortSecLimitCtrlSystemConf 2 }

sm24dp4xaPortSecurityAgingPeriod OBJECT-TYPE
   SYNTAX      Integer32(10..10000000)
   MAX-ACCESS  read-write
   STATUS      current
   DESCRIPTION
       "default: 3600, range: 10-10000000 "
   ::= { sm24dp4xaPortSecLimitCtrlSystemConf 3 }

sm24dp4xaPortSecLimitCtrlTable OBJECT-TYPE
   SYNTAX      SEQUENCE OF SM24DP4XAPortSecLimitCtrlEntry
   MAX-ACCESS  not-accessible
   STATUS      current
   DESCRIPTION
       " "
   ::= { sm24dp4xaPortSecLimitCtrl 2 }

sm24dp4xaPortSecLimitCtrlEntry OBJECT-TYPE
   SYNTAX      SM24DP4XAPortSecLimitCtrlEntry
   MAX-ACCESS  not-accessible
   STATUS      current
   DESCRIPTION
       " "
   INDEX    { sm24dp4xaPortSecLimitCtrlPort  }
   ::= { sm24dp4xaPortSecLimitCtrlTable 1 }

SM24DP4XAPortSecLimitCtrlEntry ::= SEQUENCE {
   sm24dp4xaPortSecLimitCtrlPort           Integer32,
   sm24dp4xaPortSecLimitCtrlPortMode       Integer32,
   sm24dp4xaPortSecLimitCtrlPortLimit      Integer32,
   sm24dp4xaPortSecLimitCtrlPortAction     Integer32,
   sm24dp4xaPortSecLimitCtrlPortState      DisplayString,
   sm24dp4xaPortSecLimitCtrlPortReOpen     Integer32,
   sm24dp4xaPortSecLimitCtrlPortSticky     Integer32,
   sm24dp4xaPortSecLimitCtrlPortClear      Integer32
}

sm24dp4xaPortSecLimitCtrlPort OBJECT-TYPE
   SYNTAX      Integer32 (1..4095)
   MAX-ACCESS  not-accessible
   STATUS      current
   DESCRIPTION
       " "
   ::= { sm24dp4xaPortSecLimitCtrlEntry 1 }

sm24dp4xaPortSecLimitCtrlPortMode OBJECT-TYPE
   SYNTAX      Integer32 (0|1)
   MAX-ACCESS  read-write
   STATUS      current
   DESCRIPTION
       "default: 0
       0: disable
       1: enable"
   ::= { sm24dp4xaPortSecLimitCtrlEntry 2 }

sm24dp4xaPortSecLimitCtrlPortLimit OBJECT-TYPE
   SYNTAX      Integer32(1..1024)
   MAX-ACCESS  read-write
   STATUS      current
   DESCRIPTION
       "default: 4, range: 1-1024"
   ::= { sm24dp4xaPortSecLimitCtrlEntry 3 }

sm24dp4xaPortSecLimitCtrlPortAction OBJECT-TYPE
   SYNTAX      Integer32(0..3)
   MAX-ACCESS  read-write
   STATUS      current
   DESCRIPTION
       "default: 0
       0: none
       1: trap
       2: shutdown
       3: trap&shutdown"
   ::= { sm24dp4xaPortSecLimitCtrlEntry 4 }

sm24dp4xaPortSecLimitCtrlPortState OBJECT-TYPE
   SYNTAX      DisplayString
   MAX-ACCESS  read-only
   STATUS      current
   DESCRIPTION
       " "
   ::= { sm24dp4xaPortSecLimitCtrlEntry 5 }

sm24dp4xaPortSecLimitCtrlPortReOpen OBJECT-TYPE
   SYNTAX      Integer32 (0|1)
   MAX-ACCESS  read-write
   STATUS      current
   DESCRIPTION
       "default: 0
       0: none
       1: reopen"
   ::= { sm24dp4xaPortSecLimitCtrlEntry 6 }

sm24dp4xaPortSecLimitCtrlPortSticky OBJECT-TYPE
   SYNTAX      Integer32 (0|1)
   MAX-ACCESS  read-write
   STATUS      current
   DESCRIPTION
       "default: 0
       0: disable
       1: enable"
   ::= { sm24dp4xaPortSecLimitCtrlEntry 7 }

sm24dp4xaPortSecLimitCtrlPortClear OBJECT-TYPE
   SYNTAX      Integer32 (0|1)
   MAX-ACCESS  read-write
   STATUS      current
   DESCRIPTION
       "default: 0
       1: clear"
   ::= { sm24dp4xaPortSecLimitCtrlEntry 8 }
   
sm24dp4xaPortSecSwitchStatusTable OBJECT-TYPE
   SYNTAX      SEQUENCE OF SM24DP4XAPortSecSwitchStatusEntry
   MAX-ACCESS  not-accessible
   STATUS      current
   DESCRIPTION
       " "
   ::= { sm24dp4xaPortSecurity 2 }

sm24dp4xaPortSecSwitchStatusEntry OBJECT-TYPE
   SYNTAX      SM24DP4XAPortSecSwitchStatusEntry
   MAX-ACCESS  not-accessible
   STATUS      current
   DESCRIPTION
       " "
   INDEX    { sm24dp4xaPortSecSwitchStatusPort  }
   ::= { sm24dp4xaPortSecSwitchStatusTable 1 }

SM24DP4XAPortSecSwitchStatusEntry ::= SEQUENCE {
   sm24dp4xaPortSecSwitchStatusPort                Integer32,
   sm24dp4xaPortSecSwitchStatusUsers               DisplayString,
   sm24dp4xaPortSecSwitchStatusState               DisplayString,
   sm24dp4xaPortSecSwitchStatusMACCountCurrent     Integer32,
   sm24dp4xaPortSecSwitchStatusMACCountLimit       Integer32
}

sm24dp4xaPortSecSwitchStatusPort OBJECT-TYPE
   SYNTAX      Integer32 (1..4095)
   MAX-ACCESS  not-accessible
   STATUS      current
   DESCRIPTION
       " "
   ::= { sm24dp4xaPortSecSwitchStatusEntry 1 }

sm24dp4xaPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { sm24dp4xaPortSecSwitchStatusEntry 2 }

sm24dp4xaPortSecSwitchStatusState OBJECT-TYPE
   SYNTAX      DisplayString
   MAX-ACCESS  read-only
   STATUS      current
   DESCRIPTION
       " Shows the current state of the port : Disabled, Ready, Limit Reached, Shutdown. "
   ::= { sm24dp4xaPortSecSwitchStatusEntry 3 }

sm24dp4xaPortSecSwitchStatusMACCountCurrent OBJECT-TYPE
   SYNTAX      Integer32 (1..4095)
   MAX-ACCESS  read-only
   STATUS      current
   DESCRIPTION
       " "
   ::= { sm24dp4xaPortSecSwitchStatusEntry 4 }

sm24dp4xaPortSecSwitchStatusMACCountLimit OBJECT-TYPE
   SYNTAX      Integer32(1..4095)
   MAX-ACCESS  read-only
   STATUS      current
   DESCRIPTION
       " "
   ::= { sm24dp4xaPortSecSwitchStatusEntry 5 }

sm24dp4xaPortSecPortStatus                                      OBJECT IDENTIFIER ::= { sm24dp4xaPortSecurity 3 }

sm24dp4xaPortSecPortStatusPort OBJECT-TYPE
   SYNTAX       Integer32 (1..4095)
   MAX-ACCESS   read-write
   STATUS       current
   DESCRIPTION
       "port number
        default: 1
        range: 1 - port number."
   ::= { sm24dp4xaPortSecPortStatus 1 }

sm24dp4xaPortSecPortStatusTable OBJECT-TYPE
   SYNTAX      SEQUENCE OF SM24DP4XAPortSecPortStatusEntry
   MAX-ACCESS  not-accessible
   STATUS      current
   DESCRIPTION
      " "
   ::= { sm24dp4xaPortSecPortStatus 2 }

sm24dp4xaPortSecPortStatusEntry OBJECT-TYPE
   SYNTAX      SM24DP4XAPortSecPortStatusEntry
   MAX-ACCESS  not-accessible
   STATUS      current
   DESCRIPTION
       " "
   INDEX    { sm24dp4xaPortSecPortStatusIndex  }
   ::= { sm24dp4xaPortSecPortStatusTable 1 }

SM24DP4XAPortSecPortStatusEntry ::= SEQUENCE {
   sm24dp4xaPortSecPortStatusIndex              Integer32,
   sm24dp4xaPortSecPortStatusMACAddress         MacAddress,
   sm24dp4xaPortSecPortStatusVLANId             Integer32,
   sm24dp4xaPortSecPortStatusState              DisplayString,
   sm24dp4xaPortSecPortStatusTimeOfAddition     DisplayString,
   sm24dp4xaPortSecPortStatusAgeAndHold         DisplayString
}

sm24dp4xaPortSecPortStatusIndex OBJECT-TYPE
   SYNTAX      Integer32(1..4095)
   MAX-ACCESS  not-accessible
   STATUS      current
   DESCRIPTION
       " "
   ::= { sm24dp4xaPortSecPortStatusEntry 1 }

sm24dp4xaPortSecPortStatusMACAddress OBJECT-TYPE
   SYNTAX      MacAddress
   MAX-ACCESS  read-only
   STATUS      current
   DESCRIPTION
       " "
   ::= { sm24dp4xaPortSecPortStatusEntry 2 }

sm24dp4xaPortSecPortStatusVLANId OBJECT-TYPE
   SYNTAX      Integer32(1..4094)
   MAX-ACCESS  read-only
   STATUS      current
   DESCRIPTION
       " "
   ::= { sm24dp4xaPortSecPortStatusEntry 3 }

sm24dp4xaPortSecPortStatusState OBJECT-TYPE
   SYNTAX      DisplayString
   MAX-ACCESS  read-only
   STATUS      current
   DESCRIPTION
       "Blocked / Forwarding "
   ::= { sm24dp4xaPortSecPortStatusEntry 4 }

sm24dp4xaPortSecPortStatusTimeOfAddition OBJECT-TYPE
   SYNTAX      DisplayString
   MAX-ACCESS  read-only
   STATUS      current
   DESCRIPTION
       " "
   ::= { sm24dp4xaPortSecPortStatusEntry 5 }

sm24dp4xaPortSecPortStatusAgeAndHold OBJECT-TYPE
   SYNTAX      DisplayString
   MAX-ACCESS  read-only
   STATUS      current
   DESCRIPTION
       " "
   ::= { sm24dp4xaPortSecPortStatusEntry 6 }


sm24dp4xaAccessManagement                                      OBJECT IDENTIFIER ::= { sm24dp4xaSecurity 6 }

sm24dp4xaAccessMgmtConf                                         OBJECT IDENTIFIER ::= { sm24dp4xaAccessManagement 1 }

sm24dp4xaAccessMgmtStatistics                                   OBJECT IDENTIFIER ::= { sm24dp4xaAccessManagement 2 }
--
-- =======================================================================================================================
-- Start sm24dp4xaAccessManagement group
-- =======================================================================================================================
--sm24dp4xaAccessMgmtConf

    sm24dp4xaAccessMgmtConfMode OBJECT-TYPE
               SYNTAX      AdminMode
               MAX-ACCESS  read-write
               STATUS      current
               DESCRIPTION
                   "Indicates the access management mode operation."
               DEFVAL  { disable }
               ::= {     sm24dp4xaAccessMgmtConf 1 }

--sm24dp4xaAccessMgmtConfTable

    sm24dp4xaAccessMgmtConfTable OBJECT-TYPE
               SYNTAX      SEQUENCE OF     SM24DP4XAAccessMgmtConfEntry
               MAX-ACCESS  not-accessible
               STATUS      current
               DESCRIPTION
                   "The Access Mgmt Conf Table. "
               ::= {     sm24dp4xaAccessMgmtConf 2 }

    sm24dp4xaAccessMgmtConfEntry OBJECT-TYPE
               SYNTAX          SM24DP4XAAccessMgmtConfEntry
               MAX-ACCESS  not-accessible
               STATUS      current
               DESCRIPTION
                   "The Access Mgmt Conf Entry "
               INDEX    {    sm24dp4xaAccessMgmtIndex  }
               ::= {     sm24dp4xaAccessMgmtConfTable 1 }

    SM24DP4XAAccessMgmtConfEntry             ::= SEQUENCE {
                 sm24dp4xaAccessMgmtIndex            Integer32,
                 sm24dp4xaAccessMgmtVlanID           Integer32,
                 sm24dp4xaAccessMgmtStartIpAddress   IpAddress,
                 sm24dp4xaAccessMgmtEndIpAddress     IpAddress,
                 sm24dp4xaAccessMgmtHttpHttps        AdminMode,
                 sm24dp4xaAccessMgmtSNMP             AdminMode,
                 sm24dp4xaAccessMgmtTelnetSSH        AdminMode,
                 sm24dp4xaAccessMgmtRowStatus        RowStatus
                 }

    sm24dp4xaAccessMgmtIndex OBJECT-TYPE
               SYNTAX      Integer32(1..16)
               MAX-ACCESS  not-accessible
               STATUS      current
               DESCRIPTION
                   "The Access Management config index.
                    range : 1-16."
               ::= {     sm24dp4xaAccessMgmtConfEntry 1 }

    sm24dp4xaAccessMgmtVlanID OBJECT-TYPE
               SYNTAX      Integer32 (1..4095)
               MAX-ACCESS  read-create
               STATUS      current
               DESCRIPTION
                   "The VLAN ID for the access management entry.
                    range: 1-4095."
               ::= {     sm24dp4xaAccessMgmtConfEntry 2 }

    sm24dp4xaAccessMgmtStartIpAddress OBJECT-TYPE
               SYNTAX      IpAddress
               MAX-ACCESS  read-create
               STATUS      current
               DESCRIPTION
                   "The start IP address for the access management
                    entry."
               ::= {     sm24dp4xaAccessMgmtConfEntry 3 }

    sm24dp4xaAccessMgmtEndIpAddress OBJECT-TYPE
               SYNTAX      IpAddress
               MAX-ACCESS  read-create
               STATUS      current
               DESCRIPTION
                   "The end IP address for the access management
                    entry. "
               ::= {     sm24dp4xaAccessMgmtConfEntry 4 }

    sm24dp4xaAccessMgmtHttpHttps OBJECT-TYPE
               SYNTAX      AdminMode
               MAX-ACCESS  read-create
               STATUS      current
               DESCRIPTION
                   "Indicates that the host can access the switch from
                    HTTP/HTTPS interface if the host IP address matches the IP
                    address range provided in the entry."
               DEFVAL  { disable }
               ::= {     sm24dp4xaAccessMgmtConfEntry 5 }

    sm24dp4xaAccessMgmtSNMP OBJECT-TYPE
               SYNTAX      AdminMode
               MAX-ACCESS  read-create
               STATUS      current
               DESCRIPTION
                   "Indicates that the host can access the switch from SNMP
                    interface if the host IP address matches the IP address
                    range provided in the entry."
               DEFVAL  { disable }
               ::= {     sm24dp4xaAccessMgmtConfEntry 6 }

    sm24dp4xaAccessMgmtTelnetSSH OBJECT-TYPE
               SYNTAX      AdminMode
               MAX-ACCESS  read-create
               STATUS      current
               DESCRIPTION
                   "Indicates that the host can access the switch from
                    TELNET/SSH interface if the host IP address matches
                    the IP address range provided in the entry."
               DEFVAL  { disable }
               ::= {     sm24dp4xaAccessMgmtConfEntry 7 }

    sm24dp4xaAccessMgmtRowStatus OBJECT-TYPE
               SYNTAX      RowStatus
               MAX-ACCESS  read-create
               STATUS      current
               DESCRIPTION
                   "This object indicates the status of this entry, and is used
                    to create/delete entries.  Any object in an entry of this
                    table may be modified while the value of the corresponding
                    instance of this object is active(1).
                    createAndGo, notReady not supported."
               ::= {     sm24dp4xaAccessMgmtConfEntry 8 }

--sm24dp4xaAccessMgmtStatistics

    sm24dp4xaAccessMgmtStatisticsClear OBJECT-TYPE
               SYNTAX      ActivateCmd
               MAX-ACCESS  read-write
               STATUS      current
               DESCRIPTION
                   "Clear all statistics."
               ::= {     sm24dp4xaAccessMgmtStatistics 1 }

--sm24dp4xaAccessMgmtStatisticsTable

    sm24dp4xaAccessMgmtStatisticsTable OBJECT-TYPE
               SYNTAX      SEQUENCE OF     SM24DP4XAAccessMgmtStatisticsEntry
               MAX-ACCESS  not-accessible
               STATUS      current
               DESCRIPTION
                   "The Access Mgmt Statistics Table. "
               ::= {     sm24dp4xaAccessMgmtStatistics 2 }

    sm24dp4xaAccessMgmtStatisticsEntry OBJECT-TYPE
               SYNTAX          SM24DP4XAAccessMgmtStatisticsEntry
               MAX-ACCESS  not-accessible
               STATUS      current
               DESCRIPTION
                   "The Access Mgmt Statistics Entry. "
               INDEX    {    sm24dp4xaAccessMgmtStatisticsInterface  }
               ::= {     sm24dp4xaAccessMgmtStatisticsTable 1 }

    SM24DP4XAAccessMgmtStatisticsEntry ::= SEQUENCE {
                 sm24dp4xaAccessMgmtStatisticsInterface         INTEGER,
                 sm24dp4xaAccessMgmtStatisticsReceivedPackets   Integer32,
                 sm24dp4xaAccessMgmtStatisticsAllowedPackets    Integer32,
                 sm24dp4xaAccessMgmtStatisticsDiscardedPackets  Integer32
                 }

    sm24dp4xaAccessMgmtStatisticsInterface OBJECT-TYPE
               SYNTAX      INTEGER { http(1), https(2), snmp(3), telnet(4), ssh (5) }
               MAX-ACCESS  not-accessible
               STATUS      current
               DESCRIPTION
                   "The interface type through which the remote host can
                    access the switch.
                    1: HTTP,
                    2: HTTPs,
                    3: SNMP,
                    4: TELNET,
                    5: SSH"
               ::= {     sm24dp4xaAccessMgmtStatisticsEntry 1 }

    sm24dp4xaAccessMgmtStatisticsReceivedPackets OBJECT-TYPE
               SYNTAX      Integer32(1..10000000)
               MAX-ACCESS  read-only
               STATUS      current
               DESCRIPTION
                   "Number of received packets from the interface when
                    access management mode is enabled. "
               ::= {     sm24dp4xaAccessMgmtStatisticsEntry 2 }

    sm24dp4xaAccessMgmtStatisticsAllowedPackets OBJECT-TYPE
               SYNTAX      Integer32(1..10000000)
               MAX-ACCESS  read-only
               STATUS      current
               DESCRIPTION
                   "Number of allowed packets from the interface when
                    access management mode is enabled. "
               ::= {     sm24dp4xaAccessMgmtStatisticsEntry 3 }

    sm24dp4xaAccessMgmtStatisticsDiscardedPackets OBJECT-TYPE
               SYNTAX      Integer32(1..10000000)
               MAX-ACCESS  read-only
               STATUS      current
               DESCRIPTION
                   "Number of discarded packets from the interface when
                    access management mode is enabled. "
               ::= {     sm24dp4xaAccessMgmtStatisticsEntry 4 }

-- =======================================================================================================================

--sm24dp4xaSSH                                                   OBJECT IDENTIFIER ::= { sm24dp4xaSecurity 7 }
--
--sm24dp4xaSSHMode OBJECT-TYPE
--   SYNTAX      Integer32(0|1)
--   MAX-ACCESS  read-write
--   STATUS      current
--   DESCRIPTION
--       "default: 1
--        0: disable
--        1: enable"
--   ::= { sm24dp4xaSSH 1 }
--
--sm24dp4xaSSHPort OBJECT-TYPE
--   SYNTAX      Integer32(1..65534)
--   MAX-ACCESS  read-write
--   STATUS      current
--   DESCRIPTION
--       "SSH service port number.
--        range : 1-65534, default : 22."
--   ::= { sm24dp4xaSSH 2 }

sm24dp4xaHTTPS                                                 OBJECT IDENTIFIER ::= { sm24dp4xaSecurity 8 }

--sm24dp4xaHTTPSMode OBJECT-TYPE
--   SYNTAX      Integer32(0|1)
--   MAX-ACCESS  read-write
--   STATUS      current
--   DESCRIPTION
--       "default: 1
--        0: disable
--        1: enable"
--   ::= { sm24dp4xaHTTPS 1 }
--
--sm24dp4xaHTTPSAutoRedirect OBJECT-TYPE
--   SYNTAX      Integer32(0|1)
--   MAX-ACCESS  read-write
--   STATUS      current
--   DESCRIPTION
--       "default: 0
--        0: disable
--        1: enable"
--   ::= { sm24dp4xaHTTPS 2 }
--
--sm24dp4xaHTTPSPort OBJECT-TYPE
--   SYNTAX      Integer32(1..65534)
--   MAX-ACCESS  read-write
--   STATUS      current
--   DESCRIPTION
--       "HTTPS service port number.
--        range : 1-65534, default : 443."
--   ::= { sm24dp4xaHTTPS 3 }

sm24dp4xaHTTPSCertificateMaintain OBJECT-TYPE
   SYNTAX      Integer32(2..3)
   MAX-ACCESS  read-write
   STATUS      current
   DESCRIPTION
       "2: Upload
		3: Generate"
   ::= { sm24dp4xaHTTPS 4 }

sm24dp4xaHTTPSCertificatePassPhrase OBJECT-TYPE
   SYNTAX      DisplayString
   MAX-ACCESS  read-write
   STATUS      current
   DESCRIPTION
       "Enter the pass phrase in this field if your uploading certificate is protected by a specific passphrase."
   ::= { sm24dp4xaHTTPS 5 }
   
sm24dp4xaHTTPSCertificateUpload OBJECT-TYPE
   SYNTAX      Integer32(0|1)
   MAX-ACCESS  read-write
   STATUS      current
   DESCRIPTION
       "default: 0
        0: TFTP
        1: URL"
   ::= { sm24dp4xaHTTPS 6 }
   
sm24dp4xaHTTPSFileUploadFileURL OBJECT-TYPE
   SYNTAX      DisplayString
   MAX-ACCESS  read-write
   STATUS      current
   DESCRIPTION
       "TFTP: filename
	    URL: URL"
   ::= { sm24dp4xaHTTPS 7 }
   
sm24dp4xaHTTPSFileUploadTFTPServer OBJECT-TYPE
   SYNTAX       IpAddress
   MAX-ACCESS   read-write
   STATUS       current
   DESCRIPTION
		"TFTP server IP address"
   ::= { sm24dp4xaHTTPS 8 }
   
sm24dp4xaHTTPSApply OBJECT-TYPE
   SYNTAX      Integer32(0|1)
   MAX-ACCESS  read-write
   STATUS      current
   DESCRIPTION
       "1: apply the above https settings"
   ::= { sm24dp4xaHTTPS 9 }
   
sm24dp4xaHTTPSCertificateStatus OBJECT-TYPE
   SYNTAX      DisplayString
   MAX-ACCESS  read-only
   STATUS      current
   DESCRIPTION
       "Display the current status of certificate on the switch."
   ::= { sm24dp4xaHTTPS 10 }   

sm24dp4xaAuthMethod                                            OBJECT IDENTIFIER ::= { sm24dp4xaSecurity 9 }

--
-- =======================================================================================================================
-- Start sm24dp4xaAuthMethodConfig group
-- =======================================================================================================================
--sm24dp4xaAuthMethodConfigTable

    sm24dp4xaAuthMethodConfigTable OBJECT-TYPE
               SYNTAX      SEQUENCE OF     SM24DP4XAAuthMethodConfigEntry
               MAX-ACCESS  not-accessible
               STATUS      current
               DESCRIPTION
                   "The Auth Method Config Table."
               ::= {     sm24dp4xaAuthMethod 1 }

    sm24dp4xaAuthMethodConfigEntry OBJECT-TYPE
               SYNTAX          SM24DP4XAAuthMethodConfigEntry
               MAX-ACCESS  not-accessible
               STATUS      current
               DESCRIPTION
                   "The Auth Method Config Entry."
               INDEX    {    sm24dp4xaAuthMethodConfigClient  }
               ::= {     sm24dp4xaAuthMethodConfigTable 1 }

    SM24DP4XAAuthMethodConfigEntry             ::= SEQUENCE {
                 sm24dp4xaAuthMethodConfigClient        INTEGER,
                 sm24dp4xaAuthMethodConfigMethod1       INTEGER,
                 sm24dp4xaAuthMethodConfigMethod2       INTEGER,
                 sm24dp4xaAuthMethodConfigMethod3       INTEGER,
                 sm24dp4xaAuthMethodConfigMethod4       INTEGER,
                 sm24dp4xaAuthMethodConfigServicePort   Integer32,
                 sm24dp4xaAuthMethodConfigFallback      Integer32
                 }

    sm24dp4xaAuthMethodConfigClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sm24dp4xaAuthMethodConfigEntry 1 }

    sm24dp4xaAuthMethodConfigMethod1 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sm24dp4xaAuthMethodConfigEntry 2 }

    sm24dp4xaAuthMethodConfigMethod2 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sm24dp4xaAuthMethodConfigEntry 3 }

    sm24dp4xaAuthMethodConfigMethod3 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sm24dp4xaAuthMethodConfigEntry 4 }

    sm24dp4xaAuthMethodConfigMethod4 OBJECT-TYPE
               SYNTAX      INTEGER {no(0) ,redirect(1) ,local(2) ,radius(3) ,tacacs(4)}
               MAX-ACCESS  read-write
               STATUS      current
               DESCRIPTION
                   "Methods that involves remote servers are timed out if the
                    remote servers are offline.Each method is tried from left to
                    right and continues until a method either approves or
                    rejects a user.
                    0: no, Authentication is disabled and login is not possible.
                    1: redirect, When HTTPS is enabled, enable HTTPS automatic redirect on the switch.
                    2: local, Use the local user database on the switch for
                    authentication.
                    3: radius, Use remote RADIUS server(s) for authentication.
                    4: tacacs+, Use remote TACACS+ server(s) for authentication."
               ::= {     sm24dp4xaAuthMethodConfigEntry 5 }
               
    sm24dp4xaAuthMethodConfigServicePort OBJECT-TYPE
               SYNTAX      Integer32 (1..65535)
               MAX-ACCESS  read-write
               STATUS      current
               DESCRIPTION
                   "The network port number this client bound to provide service."
               ::= {     sm24dp4xaAuthMethodConfigEntry 6 }   

    sm24dp4xaAuthMethodConfigFallback OBJECT-TYPE
               SYNTAX      Integer32 (0..1)
               MAX-ACCESS  read-write
               STATUS      current
               DESCRIPTION
                   "Enable/Disable fallback to local authentication
                   0:Disable
                   1:Enable"
               ::= {     sm24dp4xaAuthMethodConfigEntry 7 }                 

               
    sm24dp4xaCommandAuthorizationMethodTable OBJECT-TYPE
               SYNTAX      SEQUENCE OF     SM24DP4XACommandAuthorizationMethodEntry
               MAX-ACCESS  not-accessible
               STATUS      current
               DESCRIPTION
                   "The Command Authorized Method Config Table."
               ::= {     sm24dp4xaAuthMethod 2 }

    sm24dp4xaCommandAuthorizationMethodEntry OBJECT-TYPE
               SYNTAX          SM24DP4XACommandAuthorizationMethodEntry
               MAX-ACCESS  not-accessible
               STATUS      current
               DESCRIPTION
                   "The Command Authorized Method Config Entry."
               INDEX    {    sm24dp4xaCommandAuthorizationMethodClient  }
               ::= {     sm24dp4xaCommandAuthorizationMethodTable 1 }

    SM24DP4XACommandAuthorizationMethodEntry             ::= SEQUENCE {
                 sm24dp4xaCommandAuthorizationMethodClient       INTEGER,
                 sm24dp4xaCommandAuthorizationMethodMethod       Integer32,
                 sm24dp4xaCommandAuthorizationMethodCmdLvl       Integer32,
                 sm24dp4xaCommandAuthorizationMethodCfgCmd       Integer32,
                 sm24dp4xaCommandAuthorizationMethodFallback     Integer32
                 }

    sm24dp4xaCommandAuthorizationMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sm24dp4xaCommandAuthorizationMethodEntry 1 }

    sm24dp4xaCommandAuthorizationMethodMethod OBJECT-TYPE
               SYNTAX      Integer32
               MAX-ACCESS  read-write
               STATUS      current
               DESCRIPTION
                   "Method can be set to one of the following values:
                    0:no: Command authorization is disabled. 
					  User is granted access to CLI commands according to his privilege level.
                    3:tacacs: Use remote TACACS+ server(s) for command authorization. 
					  If all remote servers are offline, the user is granted access to CLI commands
					  according to his privilege level."
               ::= {     sm24dp4xaCommandAuthorizationMethodEntry 2 }

    sm24dp4xaCommandAuthorizationMethodCmdLvl OBJECT-TYPE
               SYNTAX      Integer32
               MAX-ACCESS  read-write
               STATUS      current
               DESCRIPTION
                   "Authorize all commands with a privilege level higher than or equal to this level.
                    Valid values are in the range 0 to 15."
               ::= {     sm24dp4xaCommandAuthorizationMethodEntry 3 }

    sm24dp4xaCommandAuthorizationMethodCfgCmd OBJECT-TYPE
               SYNTAX      Integer32
               MAX-ACCESS  read-write
               STATUS      current
               DESCRIPTION
                   "Also authorize configuration commands.
				   0:Disable
				   1:Enable"
               ::= {     sm24dp4xaCommandAuthorizationMethodEntry 4 }

    sm24dp4xaCommandAuthorizationMethodFallback OBJECT-TYPE
               SYNTAX      Integer32
               MAX-ACCESS  read-write
               STATUS      current
               DESCRIPTION
                   "This function is an auxiliary function of Authorization.
				   0:Disable
				   1:Enable"
               ::= {     sm24dp4xaCommandAuthorizationMethodEntry 5 }		   
               
    sm24dp4xaAccountingMethodTable OBJECT-TYPE
               SYNTAX      SEQUENCE OF     SM24DP4XAAccountingMethodEntry
               MAX-ACCESS  not-accessible
               STATUS      current
               DESCRIPTION
                   "The Accounting Method Config Table."
               ::= {     sm24dp4xaAuthMethod 3 }

    sm24dp4xaAccountingMethodEntry OBJECT-TYPE
               SYNTAX          SM24DP4XAAccountingMethodEntry
               MAX-ACCESS  not-accessible
               STATUS      current
               DESCRIPTION
                   "The Accounting Method Config Entry."
               INDEX    {    sm24dp4xaAccountingMethodClient  }
               ::= {     sm24dp4xaAccountingMethodTable 1 }

    SM24DP4XAAccountingMethodEntry             ::= SEQUENCE {
                 sm24dp4xaAccountingMethodClient       INTEGER,
                 sm24dp4xaAccountingMethodMethod       Integer32,
                 sm24dp4xaAccountingMethodCmdLvl       Integer32,
                 sm24dp4xaAccountingMethodCfgCmd       Integer32
                 }

    sm24dp4xaAccountingMethodClient OBJECT-TYPE
               SYNTAX      INTEGER  {  console ( 1 ),
                                       telnet ( 2 ),
                                       ssh ( 3 ),
                                       http ( 4 ),
                                       https ( 5 )
                                    }
               MAX-ACCESS  not-accessible
               STATUS      current
               DESCRIPTION
                   "1: console.
                    2: telnet.
                    3: ssh.
                    4: http.
                    5: https. "
               ::= {     sm24dp4xaAccountingMethodEntry 1 }

    sm24dp4xaAccountingMethodMethod OBJECT-TYPE
               SYNTAX      Integer32
               MAX-ACCESS  read-write
               STATUS      current
               DESCRIPTION
                   "Method can be set to one of the following values:
                    0:no: Accounting is disabled.
                    3:tacacs: Use remote TACACS+ server(s) for accounting."
               ::= {     sm24dp4xaAccountingMethodEntry 2 }

    sm24dp4xaAccountingMethodCmdLvl OBJECT-TYPE
               SYNTAX      Integer32
               MAX-ACCESS  read-write
               STATUS      current
               DESCRIPTION
                   "Enable accounting of all commands with a privilege level higher than or equal to this level.
                    Valid values are in the range 0 to 15. Leave the field empty to disable command accounting."
               ::= {     sm24dp4xaAccountingMethodEntry 3 }

    sm24dp4xaAccountingMethodCfgCmd OBJECT-TYPE
               SYNTAX      Integer32
               MAX-ACCESS  read-write
               STATUS      current
               DESCRIPTION
                   "Enable exec (login) accounting.
				   0:Disable
				   1:Enable"
               ::= {     sm24dp4xaAccountingMethodEntry 4 }			          

--sm24dp4xaTELNET                                                 OBJECT IDENTIFIER ::= { sm24dp4xaSecurity 10 }
--
--sm24dp4xaTELNETPort OBJECT-TYPE
--   SYNTAX      Integer32(1..65534)
--   MAX-ACCESS  read-write
--   STATUS      current
--   DESCRIPTION
--       "TELNET service port number.
--        range : 1-65534, default : 23."
--   ::= { sm24dp4xaTELNET 1 }
--
--sm24dp4xaHTTP                                                   OBJECT IDENTIFIER ::= { sm24dp4xaSecurity 11 }
--
--sm24dp4xaHTTPPort OBJECT-TYPE
--   SYNTAX      Integer32(1..65534)
--   MAX-ACCESS  read-write
--   STATUS      current
--   DESCRIPTION
--       "HTTP service port number.
--        range : 1-65534, default : 80."
--   ::= { sm24dp4xaHTTP 1 }

-- =======================================================================================================================
sm24dp4xaMaintenance                                           OBJECT IDENTIFIER ::= { sm24dp4xaProductId 4 }

sm24dp4xaSoftware                      OBJECT IDENTIFIER   ::= {  sm24dp4xaMaintenance 3 }
sm24dp4xaConfig                        OBJECT IDENTIFIER   ::= {  sm24dp4xaMaintenance 4 }

--
-- =======================================================================================================================
-- Objects in the sm24dp4xaMaintenance Group
-- =======================================================================================================================
    sm24dp4xaRestartDevice OBJECT-TYPE
               SYNTAX      ActivateCmd
               MAX-ACCESS  read-write
               STATUS      current
               DESCRIPTION
                   "Command to restart the device."
               DEFVAL  { noAction }
               ::= {     sm24dp4xaMaintenance 1 }

    sm24dp4xaFactoryDefaults OBJECT-TYPE
               SYNTAX      ActivateCmd
               MAX-ACCESS  read-write
               STATUS      current
               DESCRIPTION
                   "Reset the configuration to Factory Defaults keep-ip."
               DEFVAL  { noAction }
               ::= {     sm24dp4xaMaintenance 2 }

--sm24dp4xaSoftware

    sm24dp4xaSoftwareUsername OBJECT-TYPE
               SYNTAX       DisplayString
               MAX-ACCESS   read-write
               STATUS       current
               DESCRIPTION
                    "Get/Set the username for 'tftp' firmware upgrading."
               ::= {     sm24dp4xaSoftware 1 }

    sm24dp4xaSoftwarePassword OBJECT-TYPE
               SYNTAX       DisplayString
               MAX-ACCESS   read-write
               STATUS       current
               DESCRIPTION
                    "Get/Set the password for 'tftp' firmware upgrading."
               ::= {     sm24dp4xaSoftware 2 }

    sm24dp4xaSoftwareIpAddress OBJECT-TYPE
               SYNTAX       IpAddress
               MAX-ACCESS   read-write
               STATUS       current
               DESCRIPTION
                    "Get/Set the firmware tftp server."
               ::= {     sm24dp4xaSoftware 3 }

    sm24dp4xaSoftwareFileName OBJECT-TYPE
               SYNTAX       DisplayString
               MAX-ACCESS   read-write
               STATUS       current
               DESCRIPTION
                    "Get/Set the path and filename for firmware upgrading."
               ::= {     sm24dp4xaSoftware 4 }

    sm24dp4xaSoftwareUpgradeCmd OBJECT-TYPE
               SYNTAX       INTEGER  {  noAction ( 0 ),
                                        tftpUpgrade ( 1 ),
                                        ftpUpgrade ( 2 )
                                     }
               MAX-ACCESS   read-write
               STATUS       current
               DESCRIPTION
                    "Firmware upgrade command.
                     noAction(0) - do nothing   (read only).
                     tftpUpgrade(1) - activate 'tftp' firmware upgrade
                     ftpUpgrade(2) - activate 'ftp' firmware upgrade"

               DEFVAL  { noAction }
               ::= {     sm24dp4xaSoftware 5 }

    sm24dp4xaSoftwareImageSelectionCmd OBJECT-TYPE
               SYNTAX       ActivateCmd
               MAX-ACCESS   read-write
               STATUS       current
               DESCRIPTION
                    "Activate firmware image selection.
                     noAction(0) - do nothing - returned upon get.
                     activate(1) - activate firmware image selection."
               DEFVAL  { noAction }
               ::= {     sm24dp4xaSoftware 6 }

    sm24dp4xaSaveStartCmd OBJECT-TYPE
               SYNTAX      ActivateCmd
               MAX-ACCESS  read-write
               STATUS      current
               DESCRIPTION
                   "This copies running-config to startup-config,
                   thereby ensuring that the currently active
                   configuration will be used at the next reboot. "
               DEFVAL  { noAction }
               ::= {     sm24dp4xaConfig 1 }

    sm24dp4xaConfigUsername OBJECT-TYPE
               SYNTAX       DisplayString
               MAX-ACCESS   read-write
               STATUS       current
               DESCRIPTION
                    "Get/Set the username for 'tftp' 'upload config' or 'download config'."
               ::= {     sm24dp4xaConfig 2 }

    sm24dp4xaConfigPassword OBJECT-TYPE
               SYNTAX       DisplayString
               MAX-ACCESS   read-write
               STATUS       current
               DESCRIPTION
                    "Get/Set the password for 'tftp' 'upload config' or 'download config'."
               ::= {     sm24dp4xaConfig 3 }

    sm24dp4xaConfigIpAddress OBJECT-TYPE
               SYNTAX       IpAddress
               MAX-ACCESS   read-write
               STATUS       current
               DESCRIPTION
                    "Get/Set the IP address for 'tftp' 'upload config'
                    or 'download config'."
               ::= {     sm24dp4xaConfig 4 }

    sm24dp4xaConfigFilename OBJECT-TYPE
               SYNTAX       DisplayString
               MAX-ACCESS   read-write
               STATUS       current
               DESCRIPTION
                    "Get/Set the filename in switch for 'tftp'
                    'upload config' or 'download config'."
               ::= {     sm24dp4xaConfig 5 }

    sm24dp4xaConfigFileTable OBJECT-TYPE
               SYNTAX      SEQUENCE OF     SM24DP4XAConfigFileEntry
               MAX-ACCESS  not-accessible
               STATUS      current
               DESCRIPTION
                   "The config file tabe."
               ::= {     sm24dp4xaConfig 6 }

    sm24dp4xaConfigFileEntry OBJECT-TYPE
               SYNTAX          SM24DP4XAConfigFileEntry
               MAX-ACCESS  not-accessible
               STATUS      current
               DESCRIPTION
                   "an entry in the config file tabe."
               INDEX    {     sm24dp4xaConfigFileIndex }
               ::= {     sm24dp4xaConfigFileTable 1 }

    SM24DP4XAConfigFileEntry             ::= SEQUENCE {
                sm24dp4xaConfigFileIndex         Integer32,
                sm24dp4xaShowConfigFileName      DisplayString,
                sm24dp4xaActivateConfigCmd       ActivateCmd,
                sm24dp4xaDeleteConfigCmd         ActivateCmd,
                sm24dp4xaUploadConfigCmd         INTEGER,
                sm24dp4xaDownloadConfigCmd       INTEGER
                }

    sm24dp4xaConfigFileIndex OBJECT-TYPE
               SYNTAX      Integer32(1..255)
               MAX-ACCESS  not-accessible
               STATUS      current
               DESCRIPTION
                   "The config file index."
               ::= {     sm24dp4xaConfigFileEntry 1 }

    sm24dp4xaShowConfigFileName OBJECT-TYPE
               SYNTAX      DisplayString
               MAX-ACCESS  read-write
               STATUS      current
               DESCRIPTION
                   "Shows the config file name. Without config filename:'NewConfig'
                   is temp file when 'activate upload
                   config' can 'create new file' and 'change create filename'."
               ::= {     sm24dp4xaConfigFileEntry 2 }

    sm24dp4xaActivateConfigCmd OBJECT-TYPE
               SYNTAX       ActivateCmd
               MAX-ACCESS   read-write
               STATUS       current
               DESCRIPTION
                    "Activate config command.
                     noAction(0) : do nothing  (read only).
                     activate(1) : activate the config"
               DEFVAL  { noAction }
               ::= {     sm24dp4xaConfigFileEntry 3 }

    sm24dp4xaDeleteConfigCmd OBJECT-TYPE
               SYNTAX       ActivateCmd
               MAX-ACCESS   read-write
               STATUS       current
               DESCRIPTION
                    "Delete config command.
                     noAction(0) : do nothing  (read only).
                     activate(1) : delete the config"
               DEFVAL  { noAction }
               ::= {     sm24dp4xaConfigFileEntry 4 }

    sm24dp4xaDownloadConfigCmd OBJECT-TYPE
               SYNTAX       INTEGER  {  noAction ( 0 ),
                                        tftpDownload ( 1 )
                                        --ftpDownload ( 2 )
                                     }
               MAX-ACCESS   read-write
               STATUS       current
               DESCRIPTION
                    "Download config command.
                     noAction   (0) - do nothing   (read only).
                     tftpDownload (1) - activate 'tftp' config download."
               DEFVAL  { noAction }
               ::= {     sm24dp4xaConfigFileEntry 5 }

    sm24dp4xaUploadConfigCmd OBJECT-TYPE
               SYNTAX       INTEGER  {  noAction ( 0 ),
                                        tftpUpload ( 1 )
                                        --ftpUpload ( 2 )
                                     }
               MAX-ACCESS   read-write
               STATUS       current
               DESCRIPTION
                    "Upload config command.
                     noAction   (0) - do nothing   (read only).
                     tftpUpload (1) - activate 'tftp' config upload.
					 For merge/replace running-config:
					 1:merge
					 3:replace"
               DEFVAL  { noAction }
               ::= {     sm24dp4xaConfigFileEntry 6 }

-- =======================================================================================================================
sm24dp4xaDiagnostics                                           OBJECT IDENTIFIER ::= { sm24dp4xaMaintenance 5 }

sm24dp4xaPingIpAddress OBJECT-TYPE
   SYNTAX      IpAddress
   MAX-ACCESS  read-write
   STATUS      current
   DESCRIPTION
       " The destination IP Address. "
   ::= { sm24dp4xaDiagnostics 1 }

sm24dp4xaPingSize OBJECT-TYPE
   SYNTAX      Integer32(60..1400)
   MAX-ACCESS  read-write
   STATUS      current
   DESCRIPTION
       " Size of ICMP echo packet.
         range : 60-1400, default : 64. "
   ::= { sm24dp4xaDiagnostics 2 }

sm24dp4xaDoPingConfig OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sm24dp4xaDiagnostics 3 }

sm24dp4xaPingResult OBJECT-TYPE
   SYNTAX      DisplayString
   MAX-ACCESS  read-only
   STATUS      current
   DESCRIPTION
       " Show ping result. "
   ::= { sm24dp4xaDiagnostics 4 }

sm24dp4xaPing6IpAddress OBJECT-TYPE
   SYNTAX      DisplayString
   MAX-ACCESS  read-write
   STATUS      current
   DESCRIPTION
       " The destination IPv6 Address. "
   ::= { sm24dp4xaDiagnostics 5 }

sm24dp4xaPing6Size OBJECT-TYPE
   SYNTAX      Integer32(60..1400)
   MAX-ACCESS  read-write
   STATUS      current
   DESCRIPTION
       " Size of ICMP echo packet.
         range : 60-1400. "
   ::= { sm24dp4xaDiagnostics 6 }

sm24dp4xaPing6EgressInterface OBJECT-TYPE
   SYNTAX      Integer32(1..4095)
   MAX-ACCESS  read-write
   STATUS      current
   DESCRIPTION
       "The VLAN ID (VID) of the specific egress IPv6 interface which ICMP packet goes."
   ::= { sm24dp4xaDiagnostics 7 }
   
sm24dp4xaDoPing6Config OBJECT-TYPE
   SYNTAX      Integer32(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { sm24dp4xaDiagnostics 8 }

sm24dp4xaPing6Result OBJECT-TYPE
   SYNTAX      DisplayString
   MAX-ACCESS  read-only
   STATUS      current
   DESCRIPTION
       " Show ping result. "
   ::= { sm24dp4xaDiagnostics 9 }

sm24dp4xatracerouteIpAddress OBJECT-TYPE
   SYNTAX      DisplayString
   MAX-ACCESS  read-write
   STATUS      current
   DESCRIPTION
       " The destination IP Address. "
   ::= { sm24dp4xaDiagnostics 10 }

sm24dp4xatracerouteProtocol OBJECT-TYPE
   SYNTAX      Integer32(0..2)
   MAX-ACCESS  read-write
   STATUS      current
   DESCRIPTION
       " Specify protocol including icmp=0, udp=1 and tcp=2.
         range : 0-2, default : 0. "
   ::= { sm24dp4xaDiagnostics 11 }

sm24dp4xatracerouteWaittime OBJECT-TYPE
   SYNTAX      Integer32(1..60)
   MAX-ACCESS  read-write
   STATUS      current
   DESCRIPTION
       " Specify wait time for waiting probe packets come back.
         range : 1-60(sec), default : 5(sec). "
   ::= { sm24dp4xaDiagnostics 12 }

sm24dp4xatracerouteMaxTTL OBJECT-TYPE
   SYNTAX      Integer32(1..255)
   MAX-ACCESS  read-write
   STATUS      current
   DESCRIPTION
       " Specify max TTL.
         range : 1-255, default : 30. "
   ::= { sm24dp4xaDiagnostics 13 }

sm24dp4xatracerouteNqueries OBJECT-TYPE
   SYNTAX      Integer32(1..10)
   MAX-ACCESS  read-write
   STATUS      current
   DESCRIPTION
       " Specify number of probe packets.
         range : 1-10, default : 3. "
   ::= { sm24dp4xaDiagnostics 14 }

sm24dp4xaDotracerouteConfig OBJECT-TYPE
   SYNTAX      Integer32(1)
   MAX-ACCESS  read-write
   STATUS      current
   DESCRIPTION
       "Do traceroute-config.
         Get this OID always return zero.
         1 - ping. Uses the traceroute program to get
         ip address of the middle gateway. "
   ::= { sm24dp4xaDiagnostics 15 }

sm24dp4xatracerouteResult OBJECT-TYPE
   SYNTAX      DisplayString
   MAX-ACCESS  read-only
   STATUS      current
   DESCRIPTION
       " Show traceroute result. "
   ::= { sm24dp4xaDiagnostics 16 }

sm24dp4xaCableDiagnostics                                           OBJECT IDENTIFIER ::= { sm24dp4xaDiagnostics 17 }

sm24dp4xaCableDiagnosticsTest OBJECT-TYPE
   SYNTAX      Integer32
   MAX-ACCESS  read-write
   STATUS      current
   DESCRIPTION
       "Run Cable Diagnostics.
        port, range : 1 - port number."
   ::= { sm24dp4xaCableDiagnostics 1 }

sm24dp4xaCableDiagnosticsTable OBJECT-TYPE
   SYNTAX      SEQUENCE OF SM24DP4XACableDiagnosticsEntry
   MAX-ACCESS  not-accessible
   STATUS      current
   DESCRIPTION
       " "
   ::= { sm24dp4xaCableDiagnostics 2 }

sm24dp4xaCableDiagnosticsEntry OBJECT-TYPE
   SYNTAX      SM24DP4XACableDiagnosticsEntry
   MAX-ACCESS  not-accessible
   STATUS      current
   DESCRIPTION
       " "
   INDEX    { sm24dp4xaCableDiagnosticsPort  }
   ::= { sm24dp4xaCableDiagnosticsTable 1 }

SM24DP4XACableDiagnosticsEntry ::= SEQUENCE {
   sm24dp4xaCableDiagnosticsPort        Integer32,
   sm24dp4xaCableDiagnosticsLinkStatus  DisplayString,
   sm24dp4xaCableDiagnosticsTestResult  DisplayString,
   sm24dp4xaCableDiagnosticsLength      DisplayString
}

sm24dp4xaCableDiagnosticsPort OBJECT-TYPE
   SYNTAX      Integer32 (1..65535)
   MAX-ACCESS  not-accessible
   STATUS      current
   DESCRIPTION
       "port index"
   ::= { sm24dp4xaCableDiagnosticsEntry 1 }

sm24dp4xaCableDiagnosticsLinkStatus OBJECT-TYPE
   SYNTAX      DisplayString
   MAX-ACCESS  read-only
   STATUS      current
   DESCRIPTION
       "The status of the cable."
   ::= { sm24dp4xaCableDiagnosticsEntry 2 }

sm24dp4xaCableDiagnosticsTestResult OBJECT-TYPE
   SYNTAX      DisplayString
   MAX-ACCESS  read-only
   STATUS      current
   DESCRIPTION
       "Test Result of the cable."
   ::= { sm24dp4xaCableDiagnosticsEntry 3 }

sm24dp4xaCableDiagnosticsLength OBJECT-TYPE
   SYNTAX      DisplayString
   MAX-ACCESS  read-only
   STATUS      current
   DESCRIPTION
       "The length (in meters) of the cable."
   ::= { sm24dp4xaCableDiagnosticsEntry 4 }

sm24dp4xaSwitchRebootSchedule OBJECT IDENTIFIER ::= { sm24dp4xaMaintenance 6 }   

sm24dp4xaSwitchRebootMode OBJECT-TYPE
   SYNTAX      Integer32
   MAX-ACCESS  read-write
   STATUS      current
   DESCRIPTION
       "Switch Reboot Mode.
	    0:disable
		1:enable"
   ::= { sm24dp4xaSwitchRebootSchedule 1 }

sm24dp4xaSwitchRebootTimeTable OBJECT-TYPE
   SYNTAX      SEQUENCE OF SM24DP4XASwitchRebootTimeEntry
   MAX-ACCESS  not-accessible
   STATUS      current
   DESCRIPTION
       " Configure the Switch reboot time. "
   ::= { sm24dp4xaSwitchRebootSchedule 2 }

sm24dp4xaSwitchRebootTimeEntry OBJECT-TYPE
   SYNTAX      SM24DP4XASwitchRebootTimeEntry
   MAX-ACCESS  not-accessible
   STATUS      current
   DESCRIPTION
       " "
   INDEX    { sm24dp4xaSwitchRebootWeekIndex  }
   ::= { sm24dp4xaSwitchRebootTimeTable 1 }

SM24DP4XASwitchRebootTimeEntry ::= SEQUENCE {
   sm24dp4xaSwitchRebootWeekIndex	       Integer32,
   sm24dp4xaSwitchRebootTimeHour           Integer32,
   sm24dp4xaSwitchRebootTimeMinute         Integer32
}

sm24dp4xaSwitchRebootWeekIndex OBJECT-TYPE
   SYNTAX      Integer32 (1..7)
   MAX-ACCESS  not-accessible
   STATUS      current
   DESCRIPTION
       "Switch reboot week index.
	   1: Sun, 2: Mon, 3:Tue, 4: Wed, 5: Thu, 6: Fri, 7: Sat"
   ::= { sm24dp4xaSwitchRebootTimeEntry 1 }

sm24dp4xaSwitchRebootTimeHour OBJECT-TYPE
   SYNTAX      Integer32 (-1..23)
   MAX-ACCESS  read-write
   STATUS      current
   DESCRIPTION
       "Switch Reboot Time (Hour). Range: 0-23. 
	   -1:disable"
   ::= { sm24dp4xaSwitchRebootTimeEntry 2 }

sm24dp4xaSwitchRebootTimeMinute OBJECT-TYPE
   SYNTAX      Integer32 (-1..55)
   MAX-ACCESS  read-write
   STATUS      current
   DESCRIPTION
       "Switch Reboot Time (Minute). Range:0,5,10,...,55. 
	   -1:disable"
   ::= { sm24dp4xaSwitchRebootTimeEntry 3 }    
   
-- =======================================================================================================================
sm24dp4xaTrap                                                  OBJECT IDENTIFIER ::= { sm24dp4xaProductId 5 }

sm24dp4xaTrapEvent                                             OBJECT IDENTIFIER ::= { sm24dp4xaTrap 1 }

sm24dp4xaTrapEventNotifications                                OBJECT IDENTIFIER ::= { sm24dp4xaTrapEvent 0 }

sm24dp4xaEmergency NOTIFICATION-TYPE
  OBJECTS   { sm24dp4xaInformation }
  STATUS        current
    DESCRIPTION
        "The severity level is Emergency. Emergency conditions."
    ::= { sm24dp4xaTrapEventNotifications 1 }

sm24dp4xaAlert NOTIFICATION-TYPE
  OBJECTS   { sm24dp4xaInformation }
  STATUS        current
    DESCRIPTION
        "The severity level is Alert. Alert conditions."
    ::= { sm24dp4xaTrapEventNotifications 2 }

sm24dp4xaCritical NOTIFICATION-TYPE
  OBJECTS   { sm24dp4xaInformation }
  STATUS        current
    DESCRIPTION
        "The severity level is Critical. Critical conditions."
    ::= { sm24dp4xaTrapEventNotifications 3 }

sm24dp4xaError NOTIFICATION-TYPE
  OBJECTS   { sm24dp4xaInformation }
  STATUS        current
    DESCRIPTION
        "The severity level is Error. Error conditions."
    ::= { sm24dp4xaTrapEventNotifications 4 }

sm24dp4xaWarning NOTIFICATION-TYPE
  OBJECTS   { sm24dp4xaInformation }
  STATUS        current
    DESCRIPTION
        "The severity level is Warning. Warning conditions."
    ::= { sm24dp4xaTrapEventNotifications 5 }

sm24dp4xaNotice NOTIFICATION-TYPE
  OBJECTS   { sm24dp4xaInformation }
  STATUS        current
    DESCRIPTION
        "The severity level is Notice. Notice conditions."
    ::= { sm24dp4xaTrapEventNotifications 6 }

sm24dp4xaInformational NOTIFICATION-TYPE
  OBJECTS   { sm24dp4xaInformation }
  STATUS        current
    DESCRIPTION
        "The severity level is Informational. Informational conditions."
    ::= { sm24dp4xaTrapEventNotifications 7 }

sm24dp4xaDebug NOTIFICATION-TYPE
  OBJECTS   { sm24dp4xaInformation }
  STATUS        current
    DESCRIPTION
        "The severity level is Debug. Debug conditions."
    ::= { sm24dp4xaTrapEventNotifications 8 }

sm24dp4xaTrapVariable                                          OBJECT IDENTIFIER ::= { sm24dp4xaTrap 2 }

sm24dp4xaInformation OBJECT-TYPE
    SYNTAX      DisplayString
    MAX-ACCESS  read-only
    STATUS      current
    DESCRIPTION
        "Trap information."
    ::= { sm24dp4xaTrapVariable 1 }


END
