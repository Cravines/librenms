-- *****************************************************************
-- SM24TAT4XB-MIB
-- *****************************************************************

SM24TAT4XB-MIB DEFINITIONS ::= BEGIN

IMPORTS
    DisplayString, MacAddress, TEXTUAL-CONVENTION, RowStatus 
        FROM SNMPv2-TC

    MODULE-COMPLIANCE, OBJECT-GROUP, NOTIFICATION-GROUP 
        FROM SNMPv2-CONF

    ifIndex 
        FROM IF-MIB

    enterprises, MODULE-IDENTITY, OBJECT-TYPE, NOTIFICATION-TYPE, Unsigned32, Integer32, Counter32, Counter64, IpAddress
        FROM SNMPv2-SMI

    InetAddress, InetAddressType 
        FROM INET-ADDRESS-MIB

    OwnerString 
        FROM RMON-MIB

    sysObjectID 
        FROM SNMPv2-MIB

    SnmpAdminString 
        FROM SNMP-FRAMEWORK-MIB;
--  PortList 
--      FROM Q-BRIDGE-MIB

--  MacAddress
--      FROM BRIDGE-MIB;

transition MODULE-IDENTITY
    LAST-UPDATED "202112300217Z"
    ORGANIZATION "Corp."
    CONTACT-INFO
        " "
    DESCRIPTION "Managed PoE+ Switch, 24-port 10/100/1000Base-T PoE Plus + (4) 1G/10G SFP+ slots"
    REVISION      "202112300217Z"
    DESCRIPTION    "Rev 1.0 Initial version."
    ::= { enterprises 868 }


-- =======================================================================================================================

    OperState ::= TEXTUAL-CONVENTION
        STATUS current
        DESCRIPTION
            "Oper state."
        SYNTAX INTEGER { up ( 1 ), down ( 2 ) }

    AdminMode ::= TEXTUAL-CONVENTION
        STATUS current
        DESCRIPTION
            "The Admin state - default: disable(0)."
        SYNTAX INTEGER { disable(0), enable(1) }

    AdminMode2 ::= TEXTUAL-CONVENTION
        STATUS current
        DESCRIPTION
            "The Admin state - default: disable(0)."
        SYNTAX INTEGER  { disable(0), enable(1), notSupported(2) }

    ActivateCmd ::= TEXTUAL-CONVENTION
        STATUS current
        DESCRIPTION
            "Used to activate commands. default: noAction(0). "
        SYNTAX INTEGER { noAction ( 0 ), activate ( 1 ) }

    KeyType ::= TEXTUAL-CONVENTION
        STATUS current
        DESCRIPTION
            "The key type specifying the key generated for frames received
            on the port.
            0 : Normal,
            1 : Double Tag,
            2 : IP Address,
            3 : MAC and IP Address."
        SYNTAX INTEGER { normal  ( 0 ), doubleTag ( 1 ), ipAddr ( 2 ), macAndIpAddr ( 3 ) }

    FrameRate ::= TEXTUAL-CONVENTION
        STATUS current
        DESCRIPTION
            "The values for frame rate"
        SYNTAX INTEGER {
                        threeHundredFramesPerSec (0),
                        oneHundredFramesPerSec (1),
                        tenFramesPerSec (2),
                        oneFramePerSec (3),
                        sixFramesPerMin (4),
                        oneFramePerMin  (5),
                        sixFramesPerHour (6)
                        }

    DayOfWeek ::= TEXTUAL-CONVENTION
        STATUS current
        DESCRIPTION
            "Used to set the days of the week."
        SYNTAX INTEGER {
                        mon(1),
                        tue(2),
                        wed(3),
                        thur(4),
                        fri(5),
                        sat(6),
                        sun(7)
                        }

    Month ::= TEXTUAL-CONVENTION
        STATUS current
        DESCRIPTION
            "Used to set the month."
        SYNTAX INTEGER {
            jan(1),
            feb(2),
            march(3),
            april(4),
            may(5),
            june(6),
            july(7),
            aug(8),
            sept(9),
            oct(10),
            nov(11),
            dec(12)
            }


switch                                      OBJECT IDENTIFIER ::= { transition 2 }

sm24tat4xbProductLevel1                     OBJECT IDENTIFIER ::= { switch 77 }
sm24tat4xbProductId                         OBJECT IDENTIFIER ::= { sm24tat4xbProductLevel1 2 }

sm24tat4xbSystem                            OBJECT IDENTIFIER ::= { sm24tat4xbProductId 1 }

sm24tat4xbSystemInformation                 OBJECT IDENTIFIER ::= { sm24tat4xbSystem 1 }

sm24tat4xbSystemInfo                        OBJECT IDENTIFIER ::= { sm24tat4xbSystemInformation 1 }

sm24tat4xbSystemInfoModelName OBJECT-TYPE
    SYNTAX    DisplayString
    MAX-ACCESS    read-only
    STATUS    current
    DESCRIPTION
        " "
    ::= { sm24tat4xbSystemInfo 2 }

sm24tat4xbSystemInfoSystemDescript OBJECT-TYPE
    SYNTAX    DisplayString
    MAX-ACCESS    read-only
    STATUS    current
    DESCRIPTION
        " "
    ::= { sm24tat4xbSystemInfo 3 }

sm24tat4xbSystemInfoLocation OBJECT-TYPE
    SYNTAX    DisplayString
    MAX-ACCESS    read-write
    STATUS    current
    DESCRIPTION
        " "
    ::= { sm24tat4xbSystemInfo 4 }

sm24tat4xbSystemInfoContact OBJECT-TYPE
    SYNTAX    DisplayString
    MAX-ACCESS    read-write
    STATUS    current
    DESCRIPTION
        " "
    ::= { sm24tat4xbSystemInfo 5 }

sm24tat4xbSystemInfoSystemName OBJECT-TYPE
    SYNTAX    DisplayString
    MAX-ACCESS    read-write
    STATUS    current
    DESCRIPTION
        " "
    ::= { sm24tat4xbSystemInfo 6 }

sm24tat4xbSystemInfoSystemDate OBJECT-TYPE
    SYNTAX    DisplayString
    MAX-ACCESS    read-only
    STATUS    current
    DESCRIPTION
        " "
    ::= { sm24tat4xbSystemInfo 7 }

sm24tat4xbSystemInfoSystemUptime OBJECT-TYPE
    SYNTAX    DisplayString
    MAX-ACCESS    read-only
    STATUS    current
    DESCRIPTION
        " "
    ::= { sm24tat4xbSystemInfo 8 }

sm24tat4xbSystemInfoBootloaderVersion OBJECT-TYPE
    SYNTAX    DisplayString
    MAX-ACCESS    read-only
    STATUS    current
    DESCRIPTION
        " "
    ::= { sm24tat4xbSystemInfo 9 }

sm24tat4xbSystemInfoFirmwareVersion OBJECT-TYPE
    SYNTAX    DisplayString
    MAX-ACCESS    read-only
    STATUS    current
    DESCRIPTION
        " "
    ::= { sm24tat4xbSystemInfo 10 }

sm24tat4xbSystemInfoHardwareVersion OBJECT-TYPE
    SYNTAX    DisplayString
    MAX-ACCESS    read-only
    STATUS    current
    DESCRIPTION
        " "
    ::= { sm24tat4xbSystemInfo 11 }

sm24tat4xbSystemInfoMechanicalVersion OBJECT-TYPE
    SYNTAX    DisplayString
    MAX-ACCESS    read-only
    STATUS    current
    DESCRIPTION
        " "
    ::= { sm24tat4xbSystemInfo 12 }

sm24tat4xbSystemInfoSeriesNumber OBJECT-TYPE
    SYNTAX    DisplayString
    MAX-ACCESS    read-only
    STATUS    current
    DESCRIPTION
        " "
    ::= { sm24tat4xbSystemInfo 13 }

sm24tat4xbSystemInfoHostMACAddress OBJECT-TYPE
    SYNTAX    DisplayString
    MAX-ACCESS    read-only
    STATUS    current
    DESCRIPTION
        " "
    ::= { sm24tat4xbSystemInfo 14 }

-- sm24tat4xbSystemInfoMemory OBJECT-TYPE
--    SYNTAX    DisplayString
--    MAX-ACCESS    read-only
--    STATUS    current
--    DESCRIPTION
--        " "
--    ::= { sm24tat4xbSystemInfo 15 }

-- sm24tat4xbSystemInfoFlash OBJECT-TYPE
--    SYNTAX    DisplayString
--    MAX-ACCESS    read-only
--    STATUS    current
--    DESCRIPTION
--        " "
--    ::= { sm24tat4xbSystemInfo 16 }

sm24tat4xbSystemInfoFanSpeed OBJECT-TYPE
    SYNTAX    DisplayString
    MAX-ACCESS    read-only
    STATUS    current
    DESCRIPTION
        "Fan Speed"
    ::= { sm24tat4xbSystemInfo 17 }

-- sm24tat4xbSystemInfoPowerStatus OBJECT-TYPE
--    SYNTAX    DisplayString
--    MAX-ACCESS    read-only
--    STATUS    current
--    DESCRIPTION
--        " "
--    ::= { sm24tat4xbSystemInfo 19 }

-- sm24tat4xbSystemInfoPowers OBJECT-TYPE
--    SYNTAX    DisplayString
--    MAX-ACCESS    read-only
--    STATUS    current
--    DESCRIPTION
--        " "
--    ::= { sm24tat4xbSystemInfo 20 }

-- sm24tat4xbSystemInfoTemperatureStatus OBJECT-TYPE
--    SYNTAX    DisplayString
--    MAX-ACCESS    read-only
--    STATUS    current
--    DESCRIPTION
--        " "
--    ::= { sm24tat4xbSystemInfo 21 }

sm24tat4xbSystemInfoTemperature1 OBJECT-TYPE
    SYNTAX    DisplayString
    MAX-ACCESS    read-only
    STATUS    current
    DESCRIPTION
        " "
    ::= { sm24tat4xbSystemInfo 22 }

sm24tat4xbSystemInfoTemperature2 OBJECT-TYPE
    SYNTAX    DisplayString
    MAX-ACCESS    read-only
    STATUS    current
    DESCRIPTION
        " "
    ::= { sm24tat4xbSystemInfo 23 }

sm24tat4xbSystemInfoCPULoad OBJECT-TYPE
    SYNTAX    DisplayString
    MAX-ACCESS    read-only
    STATUS    current
    DESCRIPTION
        "CPU Utilization."
    ::= { sm24tat4xbSystemInfo 24 }

sm24tat4xbSystemInfoPoEFirmwareVersion OBJECT-TYPE
    SYNTAX    DisplayString
    MAX-ACCESS    read-only
    STATUS    current
    DESCRIPTION
        " "
    ::= { sm24tat4xbSystemInfo 32 }

-- sm24tat4xbSystemInfoProductionDate OBJECT-TYPE
--    SYNTAX    DisplayString
--    MAX-ACCESS    read-only
--    STATUS    current
--    DESCRIPTION
--    "Production Date."
--    ::= { sm24tat4xbSystemInfo 33 }

sm24tat4xbSystemTimeConf                    OBJECT IDENTIFIER ::= { sm24tat4xbSystem 2 }

-- sm24tat4xbSystemNTP                      OBJECT IDENTIFIER ::= { sm24tat4xbSystemTimeConf  1 }

sm24tat4xbSystemTime                      OBJECT IDENTIFIER ::= { sm24tat4xbSystemTimeConf  2 }
sm24tat4xbSystemTimeZone                  OBJECT IDENTIFIER ::= { sm24tat4xbSystemTime 1 }
sm24tat4xbSystemTimeDaylightSaving         OBJECT IDENTIFIER ::= { sm24tat4xbSystemTime 2 }
sm24tat4xbSystemTimeConfiguration          OBJECT IDENTIFIER ::= { sm24tat4xbSystemTime 3 }

    --
-- =======================================================================================================================
-- Objects in the sm24tat4xbSystemNTP Group
-- =======================================================================================================================
--    sm24tat4xbSystemNTPMode OBJECT-TYPE
--        SYNTAX    INTEGER {useLocal(0),useNTP(1)}
--        MAX-ACCESS    read-write
--        STATUS    current
--        DESCRIPTION
--            "The system NTP Mode.
--            useLocal(0) : Use Local Settings,
--            useNTP(1)    : Use NTP Server."
--        DEFVAL  { useLocal }
--        ::= {     sm24tat4xbSystemNTP 1 }
--
--    sm24tat4xbSystemNTPServer1    OBJECT-TYPE
--        SYNTAX        DisplayString
--        MAX-ACCESS    read-write
--        STATUS        current
--        DESCRIPTION
--            "Get/Set the NTP Time Server1.
--            You can use the IP address or domain name."
--        ::= {     sm24tat4xbSystemNTP 2 }
--
--    sm24tat4xbSystemNTPServer2    OBJECT-TYPE
--        SYNTAX        DisplayString
--        MAX-ACCESS    read-write
--        STATUS        current
--        DESCRIPTION
--            "Get/Set the NTP Time Server2.
--            You can use the IP address or domain name."
--        ::= {     sm24tat4xbSystemNTP 3 }
--
--    sm24tat4xbSystemNTPServer3    OBJECT-TYPE
--        SYNTAX        DisplayString
--        MAX-ACCESS    read-write
--        STATUS        current
--        DESCRIPTION
--            "Get/Set the NTP Time Server3.
--            You can use the IP address or domain name."
--        ::= {     sm24tat4xbSystemNTP 4 }
--
--    sm24tat4xbSystemNTPServer4    OBJECT-TYPE
--        SYNTAX        DisplayString
--        MAX-ACCESS    read-write
--        STATUS        current
--        DESCRIPTION
--            "Get/Set the NTP Time Server4.
--            You can use the IP address or domain name."
--        ::= {     sm24tat4xbSystemNTP 5 }
--
--    sm24tat4xbSystemNTPServer5    OBJECT-TYPE
--        SYNTAX        DisplayString
--        MAX-ACCESS    read-write
--        STATUS        current
--        DESCRIPTION
--            "Get/Set the NTP Time Server5.
--            You can use the IP address or domain name."
--        ::= {     sm24tat4xbSystemNTP 6 }


--
-- =======================================================================================================================
-- Objects in the sm24tat4xbSystemTime Group
-- =======================================================================================================================
--sm24tat4xbSystemTimeZone

    sm24tat4xbSystemTimeZoneConf OBJECT-TYPE
        SYNTAX    Integer32(-7200..7201)
        MAX-ACCESS    read-write
        STATUS    current
        DESCRIPTION
            "Get/Set the NTP Time Zone.
            The value range is between -7200 and 7201 (minutes).
            0 : None.
            -7200 : (GMT-12:00).
            -6600 : (GMT-11:00).
            -6000 : (GMT-10:00).
            -5400 : (GMT-09:00).
            -4800 : (GMT-08:00)Pacific Time.
            -4801 : (GMT-08:00)Tijuana, Baja California.
            -4200 : (GMT-07:00)Arizona.
            -4201 : (GMT-07:00)Chihuahua, La Paz, Mazatlan - New.
            -4202 : (GMT-07:00)Chihuahua, La Paz, Mazatlan - Old.
            -4203 : (GMT-07:00)Mountain Time.
            -3600 : (GMT-06:00)Central America.
            -3601 : (GMT-06:00)Central Time.
            -3602 : (GMT-06:00)Guadalajara, Mexico City, Monterrey - New.
            -3603 : (GMT-06:00)Guadalajara, Mexico City, Monterrey - Old.
            -3604 : (GMT-06:00)Saskatchewan.
            -3000 : (GMT-05:00)Bogota, Lima, Quito, Rio Branco.
            -3001 : (GMT-05:00)Eastern Time.
            -3002 : (GMT-05:00)Indiana.
            -2700 : (GMT-04:30).
            -2400 : (GMT-04:00)Atlantic Time.
            -2401 : (GMT-04:00)La Paz.
            -2402 : (GMT-04:00)Manaus.
            -2403 : (GMT-04:00)Santiago.
            -2100 : (GMT-03:30).
            -1800 : (GMT-03:00)Brasilia.
            -1801 : (GMT-03:00)Buenos Aires.
            -1802 : (GMT-03:00)Georgetown.
            -1803 : (GMT-03:00)Greenland.
            -1804 : (GMT-03:00)Montevideo.
            -1805 : (GMT-02:00).
            -600 : (GMT-01:00)Azores.
            -601 : (GMT-01:00)Cape Verde Is.
            1 : (GMT) Casablanca.
            2 : (GMT) Greenwich Mean Time.
            3 : (GMT) Monrovia, Reykjavik.
            600 : (GMT+01:00) Amsterdam, Berlin, Bern, Rome, Stockholm, Vienna.
            601 : (GMT+01:00) Belgrade, Bratislava, Budapest, Ljubljana, Prague.
            602 : (GMT+01:00) Brussels, Copenhagen, Madrid, Paris.
            603 : (GMT+01:00) Sarajevo, Skopje, Warsaw, Zagreb.
            604 : (GMT+01:00) West Central Africa.
            1200 : (GMT+02:00) Amman.
            1201 : (GMT+02:00) Athens, Bucharest, Istanbul.
            1202 : (GMT+02:00) Beirut.
            1203 : (GMT+02:00) Cairo.
            1204 : (GMT+02:00) Harare, Pretoria.
            1205 : (GMT+02:00) Helsinki, Kyiv, Riga, Sofia, Tallinn, Vilnius.
            1206 : (GMT+02:00) Jerusalem.
            1207 : (GMT+02:00) Minsk.
            1208 : (GMT+02:00) Windhoek.
            1800 : (GMT+03:00) Baghdad.
            1801 : (GMT+03:00) Kuwait, Riyadh.
            1802 : (GMT+03:00) Moscow, St. Petersburg, Volgograd.
            1803 : (GMT+03:00) Nairobi.
            1804 : (GMT+03:00) Tbilisi.
            2100 : (GMT+03:30) Tehran.
            2400 : (GMT+04:00) Abu Dhabi, Muscat.
            2401 : (GMT+04:00) Baku.
            2402 : (GMT+04:00) Caucasus Standard Time.
            2403 : (GMT+04:00) Port Louis.
            2404 : (GMT+04:00) Yerevan.
            2700 : (GMT+04:30) Kabul.
            3000 : (GMT+05:00) Ekaterinburg.
            3001 : (GMT+05:00) Islamabad, Karachi.
            3002 : (GMT+05:00) Tashkent.
            3300 : (GMT+05:30) Chennai, Kolkata, Mumbai, New Delhi.
            3301 : (GMT+05:30) Sri Jayawardenepura.
            3455 : (GMT+05:45) Kathmandu.
            3600 : (GMT+06:00) Almaty, Novosibirsk.
            3601 : (GMT+06:00) Astana, Dhaka.
            3600 : (GMT+06:30) Yangon (Rangoon).
            4200 : (GMT+07:00) Bangkok, Hanoi, Jakarta.
            4201 : (GMT+07:00) Krasnoyarsk.
            4800 : (GMT+08:00) Beijing, Chongqing, Hong Kong, Urumqi.
            4801 : (GMT+08:00) Irkutsk, Ulaan Bataar.
            4802 : (GMT+08:00) Kuala Lumpur, Singapore.
            4803 : (GMT+08:00) Perth.
            4804 : (GMT+08:00) Taipei.
            5400 : (GMT+09:00) Osaka, Sapporo, Tokyo.
            5401 : (GMT+09:00) Seoul.
            5402 : (GMT+09:00) Yakutsk.
            5700 : (GMT+09:30) Adelaide.
            5701 : (GMT+09:30) Darwin.
            6000 : (GMT+10:00) Brisbane.
            6001 : (GMT+10:00) Canberra, Melbourne, Sydney.
            6002 : (GMT+10:00) Guam, Port Moresby.
            6003 : (GMT+10:00) Hobart.
            6004 : (GMT+10:00) Vladivostok.
            6600 : (GMT+11:00) Magadan, Solomon Is., New Caledonia.
            7200 : (GMT+12:00) Auckland, Wellington.
            7201 : (GMT+12:00) Fiji, Kamchatka, Marshall Is."
        ::= {     sm24tat4xbSystemTimeZone 1 }

    sm24tat4xbSystemTimeZoneAcronym OBJECT-TYPE
        SYNTAX    DisplayString
        MAX-ACCESS    read-write
        STATUS    current
        DESCRIPTION
            "Acronym - User can set the acronym of the time zone.
            This is a User configurable acronym to identify the time zone.
            Range : 0 - 16 characters."
        ::= {     sm24tat4xbSystemTimeZone 2 }

--sm24tat4xbSystemTimeDaylightSaving

    sm24tat4xbSystemTimeDaylightSavingMode OBJECT-TYPE
        SYNTAX    INTEGER { disable(0), recurring(1), nonRecurring(2) }
        MAX-ACCESS    read-write
        STATUS    current
        DESCRIPTION
            "The system Daylight Savings Mode.
            disable(0)    : Disable.
            recurring(1) : Recurring
            - configure the Daylight Saving Time duration
            to repeat the configuration every year.
            nonRecurring(2): Non-Recurring - configure the Daylight Saving Time
            duration for single time configuration."
        DEFVAL  { disable }
        ::= {     sm24tat4xbSystemTimeDaylightSaving 1 }

    sm24tat4xbSystemTimeDaylightSavingStartWeek OBJECT-TYPE
        SYNTAX    DisplayString
        MAX-ACCESS    read-write
        STATUS    current
        DESCRIPTION
            "Start time Week. Use in Recurring Mode.
            Range : 1 - 5.
            Default : 1."
        ::= {     sm24tat4xbSystemTimeDaylightSaving 2 }

    sm24tat4xbSystemTimeDaylightSavingStartDay OBJECT-TYPE
        SYNTAX    DayOfWeek
        MAX-ACCESS    read-write
        STATUS    current
        DESCRIPTION
            "Start time Day. Use in Recurring Mode."
        DEFVAL  { mon }
        ::= {     sm24tat4xbSystemTimeDaylightSaving 3 }

    sm24tat4xbSystemTimeDaylightSavingStartMonth OBJECT-TYPE
        SYNTAX    Month
        MAX-ACCESS    read-write
        STATUS    current
        DESCRIPTION
            "Start time Month."
        DEFVAL  { jan }
        ::= {     sm24tat4xbSystemTimeDaylightSaving 4 }

    sm24tat4xbSystemTimeDaylightSavingStartDate OBJECT-TYPE
        SYNTAX    Integer32 (1..31)
        MAX-ACCESS    read-write
        STATUS    current
        DESCRIPTION
            "Start time Date. Use in Non-Recurring Mode.
            Range : 1 - 31.
            Default : 1."
        ::= {     sm24tat4xbSystemTimeDaylightSaving 5 }

    sm24tat4xbSystemTimeDaylightSavingStartYear OBJECT-TYPE
        SYNTAX    Integer32 (2000..2097)
        MAX-ACCESS    read-write
        STATUS    current
        DESCRIPTION
            "Start time Year. Use in Non-Recurring Mode.
            Range : 2000 - 2097.
            Default : 2000."
        ::= {     sm24tat4xbSystemTimeDaylightSaving 6 }

    sm24tat4xbSystemTimeDaylightSavingStartHours OBJECT-TYPE
        SYNTAX    Integer32 (0..23)
        MAX-ACCESS    read-write
        STATUS    current
        DESCRIPTION
            "Start time Hours.
             Range : 0 - 23.
             Default : 0."
        ::= {     sm24tat4xbSystemTimeDaylightSaving 7 }

    sm24tat4xbSystemTimeDaylightSavingStartMinutes OBJECT-TYPE
        SYNTAX    Integer32 (0..59)
        MAX-ACCESS    read-write
        STATUS    current
        DESCRIPTION
            "Start time Minutes.
            Range : 0 - 59.
            Default : 0."
        ::= {     sm24tat4xbSystemTimeDaylightSaving 8 }

    sm24tat4xbSystemTimeDaylightSavingEndWeek OBJECT-TYPE
        SYNTAX    DisplayString
        MAX-ACCESS    read-write
        STATUS    current
        DESCRIPTION
            "End time Week. Use in Recurring Mode.
            Range : 1 - 5.
            Default : 1."
        ::= {     sm24tat4xbSystemTimeDaylightSaving 9 }

    sm24tat4xbSystemTimeDaylightSavingEndDay OBJECT-TYPE
        SYNTAX    DayOfWeek
        MAX-ACCESS    read-write
        STATUS    current
        DESCRIPTION
            "End time Day. Use in Recurring Mode."
        DEFVAL  { mon }
        ::= {     sm24tat4xbSystemTimeDaylightSaving 10 }

    sm24tat4xbSystemTimeDaylightSavingEndMonth OBJECT-TYPE
        SYNTAX    Month
        MAX-ACCESS    read-write
        STATUS    current
        DESCRIPTION
            "End time Month."
          DEFVAL  { jan }
          ::= {     sm24tat4xbSystemTimeDaylightSaving 11 }

    sm24tat4xbSystemTimeDaylightSavingEndDate OBJECT-TYPE
        SYNTAX    Integer32 (1..31)
        MAX-ACCESS    read-write
        STATUS    current
        DESCRIPTION
            "End time Date. Use in Non-Recurring Mode.
            Range : 1 - 31.
            Default : 1."
        ::= {     sm24tat4xbSystemTimeDaylightSaving 12 }

    sm24tat4xbSystemTimeDaylightSavingEndYear OBJECT-TYPE
        SYNTAX    Integer32 (2000..2097)
        MAX-ACCESS    read-write
        STATUS    current
        DESCRIPTION
            "End time Year. Use in Non-Recurring Mode.
            Range : 2000 - 2097.
            Default : 2000."
        ::= {     sm24tat4xbSystemTimeDaylightSaving 13 }

    sm24tat4xbSystemTimeDaylightSavingEndHours OBJECT-TYPE
        SYNTAX    Integer32 (0..23)
        MAX-ACCESS    read-write
        STATUS    current
        DESCRIPTION
            "End time Hours.
            Range : 0 - 23.
            Default : 0."
        ::= {     sm24tat4xbSystemTimeDaylightSaving 14 }

    sm24tat4xbSystemTimeDaylightSavingEndMinutes OBJECT-TYPE
        SYNTAX    Integer32 (0..59)
        MAX-ACCESS    read-write
        STATUS    current
        DESCRIPTION
            "End time Minutes.
            Range : 0 - 59.
            Default : 0."
        ::= {     sm24tat4xbSystemTimeDaylightSaving 15 }

    sm24tat4xbSystemTimeDaylightSavingOffset OBJECT-TYPE
        SYNTAX    Integer32 (1..1440)
        MAX-ACCESS    read-write
        STATUS    current
        DESCRIPTION
            "Offset - the number of minutes to add during Daylight Saving Time.
            Range : 1 - 1440(Minutes).
            Default : 1."
        ::= {     sm24tat4xbSystemTimeDaylightSaving 16 }

    sm24tat4xbSystemTimeConfigurationClockSource OBJECT-TYPE
        SYNTAX    Integer32
        MAX-ACCESS    read-write
        STATUS    current
        DESCRIPTION
            "0:Use Local Settings.
            1:Use NTP Server."
	        ::= {     sm24tat4xbSystemTimeConfiguration 1}

    sm24tat4xbSystemTimeConfigurationSystemDate OBJECT-TYPE
        SYNTAX    DisplayString
        MAX-ACCESS    read-write
        STATUS    current
        DESCRIPTION
            "System date. Default format:yyyy-mm-dd.
            When ClockSource is Use Local Settings, you can set this field."
	        ::= {     sm24tat4xbSystemTimeConfiguration 2}

    sm24tat4xbSystemTimeConfigurationDateFormat OBJECT-TYPE
        SYNTAX    Integer32 (0|1|2)
        MAX-ACCESS    read-write
        STATUS    current
        DESCRIPTION
            "The date format of the system.
				    0:yyyy-mm-dd
				    1:mm-dd-yyyy
				    2:dd-mm-yyyy"
	        ::= {     sm24tat4xbSystemTimeConfiguration 3}

    sm24tat4xbSystemTimeConfigurationTimeFormat OBJECT-TYPE
        SYNTAX    Integer32 (0|1)
        MAX-ACCESS    read-write
        STATUS    current
        DESCRIPTION
            "The time format of the system.
				    0:24-hr, format:hh:mm:ss
				    1:12-hr, format:hh:mm:ss am/pm"
	        ::= {     sm24tat4xbSystemTimeConfiguration 4}

    sm24tat4xbSystemTimeConfigurationSystemTime OBJECT-TYPE
        SYNTAX    DisplayString
        MAX-ACCESS    read-write
        STATUS    current
        DESCRIPTION
            "System date.
				    24-hr, format:hh:mm:ss
				    12-hr, format:hh:mm:ss am/pm
            When ClockSource is Use Local Settings, you can set this field."
	        ::= {     sm24tat4xbSystemTimeConfiguration 5}

-- =======================================================================================================================
sm24tat4xbSystemAccount                     OBJECT IDENTIFIER ::= { sm24tat4xbSystem 3 }

sm24tat4xbSystemAccountUsers                     OBJECT IDENTIFIER  ::= { sm24tat4xbSystemAccount 1 }

--
-- =======================================================================================================================
-- Start sm24tat4xbUserConfig group
-- =======================================================================================================================
--sm24tat4xbUserConfigTable

    sm24tat4xbUserConfigTable OBJECT-TYPE
        SYNTAX      SEQUENCE OF     SM24TAT4XBUserConfigEntry
        MAX-ACCESS  not-accessible
        STATUS      current
        DESCRIPTION
            "The User Config Table. "
        ::= {     sm24tat4xbSystemAccountUsers 1 }

    sm24tat4xbUserConfigEntry OBJECT-TYPE
        SYNTAX      SM24TAT4XBUserConfigEntry
        MAX-ACCESS  not-accessible
        STATUS      current
        DESCRIPTION
            "The User Config Entry."
        INDEX    {    sm24tat4xbUserConfigIndex  }
        ::= {     sm24tat4xbUserConfigTable 1 }

    SM24TAT4XBUserConfigEntry         ::= SEQUENCE {
         sm24tat4xbUserConfigIndex        Integer32,
         sm24tat4xbUserConfigUserName     DisplayString,
         sm24tat4xbUserConfigPassword     DisplayString,
         sm24tat4xbUserConfigPrivilegeLevel    Integer32,
         sm24tat4xbUserConfigRowStatus    RowStatus
        }

    sm24tat4xbUserConfigIndex OBJECT-TYPE
        SYNTAX      Integer32 (1..4095)
        MAX-ACCESS  not-accessible
        STATUS      current
        DESCRIPTION
            "The user Config Index. "
        ::= {     sm24tat4xbUserConfigEntry 1 }

    sm24tat4xbUserConfigUserName OBJECT-TYPE
        SYNTAX      DisplayString(SIZE (1..31))
        MAX-ACCESS  read-create
        STATUS      current
        DESCRIPTION
            "A string identifying the user name for the entry.
            string length: 1-31. "
        ::= {     sm24tat4xbUserConfigEntry 2 }

    sm24tat4xbUserConfigPassword OBJECT-TYPE
        SYNTAX      DisplayString(SIZE (0..31))
        MAX-ACCESS  read-create
        STATUS      current
        DESCRIPTION
            "The password of the user.
            string length: 0-31. "
        ::= {     sm24tat4xbUserConfigEntry 3 }

    sm24tat4xbUserConfigPrivilegeLevel OBJECT-TYPE
        SYNTAX      Integer32(1..15)
        MAX-ACCESS  read-create
        STATUS      current
        DESCRIPTION
            "The privilege level of the user.If the privilege level
            value is 15, it can access all groups.range: 1-15. "
        ::= {     sm24tat4xbUserConfigEntry 4 }

    sm24tat4xbUserConfigRowStatus OBJECT-TYPE
        SYNTAX      RowStatus
        MAX-ACCESS  read-create
        STATUS      current
        DESCRIPTION
            "This object indicates the status of this entry, and is used
            to create/delete entries.  Any object in an entry of this
            table may be modified while the value of the corresponding
            instance of this object is active(1).
            createAndGo, notReady not supported."
        ::= {     sm24tat4xbUserConfigEntry 5 }


--
-- =======================================================================================================================
-- Start sm24tat4xbPrivilegeLevelConfig group
-- =======================================================================================================================
--sm24tat4xbPrivilegeLevelConfigTable

    sm24tat4xbPrivilegeLevelConfigTable OBJECT-TYPE
        SYNTAX      SEQUENCE OF     SM24TAT4XBPrivilegeLevelConfigEntry
        MAX-ACCESS  not-accessible
        STATUS      current
        DESCRIPTION
            "The Privilege Level Config Table. "
        ::= {     sm24tat4xbSystemAccountUsers 2 }

    sm24tat4xbPrivilegeLevelConfigEntry OBJECT-TYPE
        SYNTAX      SM24TAT4XBPrivilegeLevelConfigEntry
        MAX-ACCESS  not-accessible
        STATUS      current
        DESCRIPTION
            "The Privilege Level Config Entry."
        INDEX    {    sm24tat4xbPrivilegeLevelIndex  }
        ::= {     sm24tat4xbPrivilegeLevelConfigTable 1 }

    SM24TAT4XBPrivilegeLevelConfigEntry         ::= SEQUENCE {
         sm24tat4xbPrivilegeLevelIndex        Integer32,
         sm24tat4xbPrivilegeLevelGroupName        DisplayString,
         sm24tat4xbPrivilegeLevelConfigReadOnly    Integer32,
         sm24tat4xbPrivilegeLevelConfigReadWrite      Integer32,
         sm24tat4xbPrivilegeLevelStatusReadOnly    Integer32,
         sm24tat4xbPrivilegeLevelStatusReadWrite      Integer32
         }

    sm24tat4xbPrivilegeLevelIndex OBJECT-TYPE
        SYNTAX      Integer32 (1..4095)
        MAX-ACCESS  not-accessible
        STATUS      current
        DESCRIPTION
            "The Privilege Level Index. "
        ::= {     sm24tat4xbPrivilegeLevelConfigEntry 1 }

    sm24tat4xbPrivilegeLevelGroupName OBJECT-TYPE
        SYNTAX      DisplayString
        MAX-ACCESS  read-only
        STATUS      current
        DESCRIPTION
            "The name identifying the privilege group."
        ::= {     sm24tat4xbPrivilegeLevelConfigEntry 2 }

    sm24tat4xbPrivilegeLevelConfigReadOnly OBJECT-TYPE
        SYNTAX      Integer32(1..15)
        MAX-ACCESS  read-write
        STATUS      current
        DESCRIPTION
            "The privilege level of configuration read-only.If the
            privilege level value is 15,it can access all groups.
            range: 1-15.  "
        ::= {     sm24tat4xbPrivilegeLevelConfigEntry 3 }

    sm24tat4xbPrivilegeLevelConfigReadWrite OBJECT-TYPE
        SYNTAX      Integer32(1..15)
        MAX-ACCESS  read-write
        STATUS      current
        DESCRIPTION
            "The privilege level of configuration/execute read/write.
            If the privilege level value is 15,it can access all groups.
            range: 1-15. "
        ::= {     sm24tat4xbPrivilegeLevelConfigEntry 4 }

    sm24tat4xbPrivilegeLevelStatusReadOnly OBJECT-TYPE
        SYNTAX      Integer32(1..15)
        MAX-ACCESS  read-write
        STATUS      current
        DESCRIPTION
            "The privilege level of status/statistics read-only.
            If the privilege level value is 15,it can access all groups.
            range: 1-15. "
        ::= {     sm24tat4xbPrivilegeLevelConfigEntry 5 }

    sm24tat4xbPrivilegeLevelStatusReadWrite OBJECT-TYPE
        SYNTAX      Integer32(1..15)
        MAX-ACCESS  read-write
        STATUS      current
        DESCRIPTION
            "The privilege level of status/statistics read-write.
            If the privilege level value is 15,it can access all groups.
            range: 1-15. "
        ::= {     sm24tat4xbPrivilegeLevelConfigEntry 6 }
-- =======================================================================================================================
sm24tat4xbIP  OBJECT IDENTIFIER ::= { sm24tat4xbSystem 4 }

sm24tat4xbIPConfigurationBasic OBJECT IDENTIFIER ::= { sm24tat4xbIP 1 }

sm24tat4xbIPConfigIPv4DHCPClientEnable OBJECT-TYPE
    SYNTAX      Integer32 (0|1)
    MAX-ACCESS  read-write
    STATUS      current
    DESCRIPTION
        "IPv4 DHCP Client Enabled
        0: Disable
        1: Enable"
    ::= {sm24tat4xbIPConfigurationBasic 1 }

sm24tat4xbIPConfigIPv4Address OBJECT-TYPE
    SYNTAX      DisplayString
    MAX-ACCESS  read-write
    STATUS      current
    DESCRIPTION
        "IPv4 Address."
    ::= {sm24tat4xbIPConfigurationBasic 2 }

sm24tat4xbIPConfigSubnetMask OBJECT-TYPE
    SYNTAX      DisplayString
    MAX-ACCESS  read-write
    STATUS      current
    DESCRIPTION
        "IPv4 SubnetMask."
    ::= {sm24tat4xbIPConfigurationBasic 3 }

sm24tat4xbIPConfigGateway OBJECT-TYPE
    SYNTAX      DisplayString
    MAX-ACCESS  read-write
    STATUS      current
    DESCRIPTION
        "IPv4 Gateway."
    ::= {sm24tat4xbIPConfigurationBasic 4 }

sm24tat4xbIPConfigDNSServer OBJECT-TYPE
    SYNTAX      Integer32 (0..5)
    MAX-ACCESS  read-write
    STATUS      current
    DESCRIPTION
        "DNS Server Source.
        0: No DNS configuration is applied
        1: DNS configuration is manually set
        2: DNS configuration is derived from DHCPv4
        3: DNS configuration is derived from DHCPv4 on specific VLAN.
	    4. DNS configuration is derived from DHCPv6.
	    5. DNS configuration is derived from DHCPv6 on specific VLAN.
    	"
    ::= {sm24tat4xbIPConfigurationBasic 5 }

sm24tat4xbIPConfigDNSServerValue OBJECT-TYPE
    SYNTAX      DisplayString
    MAX-ACCESS  read-write
    STATUS      current
    DESCRIPTION
        "DNS IPv4 Address or VLAN value."
    ::= {sm24tat4xbIPConfigurationBasic 6 }

sm24tat4xbIPConfiguration OBJECT IDENTIFIER ::= { sm24tat4xbIP 2 }

sm24tat4xbMode OBJECT-TYPE
    SYNTAX      Integer32 (0|1)
    MAX-ACCESS  read-write
    STATUS      current
    DESCRIPTION
        "IP Configuration Mode.
        default:0
        0: Host
        1: Router"
    ::= {sm24tat4xbIPConfiguration 2 }

sm24tat4xbDNSServerSource1 OBJECT-TYPE
    SYNTAX      Integer32 (0..5)
    MAX-ACCESS  read-write
    STATUS      current
    DESCRIPTION
        "DNS Server Source.
        0: No DNS configuration is applied
       1: DNS configuration is manually set
        2: DNS configuration is derived from DHCPv4
       3: DNS configuration is derived from DHCPv4 on specific VLAN.
    	4. DNS configuration is derived from DHCPv6.
    	5. DNS configuration is derived from DHCPv6 on specific VLAN.
    	"
    ::= {sm24tat4xbIPConfiguration 3 }

sm24tat4xbDNSServerSource2 OBJECT-TYPE
    SYNTAX      Integer32 (0..5)
    MAX-ACCESS  read-write
    STATUS      current
    DESCRIPTION
        "DNS Server Source.
        0: No DNS configuration is applied
        1: DNS configuration is manually set
        2: DNS configuration is derived from DHCPv4
        3: DNS configuration is derived from DHCPv4 on specific VLAN.
        4. DNS configuration is derived from DHCPv6.
        5. DNS configuration is derived from DHCPv6 on specific VLAN.
        "
    ::= {sm24tat4xbIPConfiguration 4 }

sm24tat4xbDNSServerSource3 OBJECT-TYPE
    SYNTAX      Integer32 (0..5)
    MAX-ACCESS  read-write
    STATUS      current
    DESCRIPTION
        "DNS Server Source.
        0: No DNS configuration is applied
        1: DNS configuration is manually set
        2: DNS configuration is derived from DHCPv4
        3: DNS configuration is derived from DHCPv4 on specific VLAN.
	    4. DNS configuration is derived from DHCPv6.
	    5. DNS configuration is derived from DHCPv6 on specific VLAN.
	    "
    ::= {sm24tat4xbIPConfiguration 5 }

sm24tat4xbDNSServerSource4 OBJECT-TYPE
    SYNTAX      Integer32 (0..5)
    MAX-ACCESS  read-write
    STATUS      current
    DESCRIPTION
        "DNS Server Source.
        0: No DNS configuration is applied
        1: DNS configuration is manually set
        2: DNS configuration is derived from DHCPv4
        3: DNS configuration is derived from DHCPv4 on specific VLAN.
	    4. DNS configuration is derived from DHCPv6.
	    5. DNS configuration is derived from DHCPv6 on specific VLAN.
	    "
    ::= {sm24tat4xbIPConfiguration 6 }

sm24tat4xbDNSServerValue1 OBJECT-TYPE
    SYNTAX      DisplayString
    MAX-ACCESS  read-write
    STATUS      current
    DESCRIPTION
        "DNS IPv4/IPv6 Address or VLAN value."
    ::= {sm24tat4xbIPConfiguration 7 }

sm24tat4xbDNSServerValue2 OBJECT-TYPE
    SYNTAX      DisplayString
    MAX-ACCESS  read-write
    STATUS      current
    DESCRIPTION
      "DNS IPv4/IPv6 Address or VLAN value."
    ::= {sm24tat4xbIPConfiguration 8 }

sm24tat4xbDNSServerValue3 OBJECT-TYPE
    SYNTAX      DisplayString
    MAX-ACCESS  read-write
    STATUS      current
    DESCRIPTION
        "DNS IPv4/IPv6 Address or VLAN value."
    ::= {sm24tat4xbIPConfiguration 9 }

sm24tat4xbDNSServerValue4 OBJECT-TYPE
    SYNTAX      DisplayString
    MAX-ACCESS  read-write
    STATUS      current
    DESCRIPTION
        "DNS IPv4/IPv6 Address or VLAN value."
    ::= {sm24tat4xbIPConfiguration 10 }

sm24tat4xbDNSProxy OBJECT-TYPE
    SYNTAX      Integer32 (0|1)
    MAX-ACCESS  read-write
    STATUS      current
    DESCRIPTION
        "DNS Proxy enable/disable.
        default:0
        0: disable
        1: enable"
    ::= {sm24tat4xbIPConfiguration 11 }


sm24tat4xbIPInterfaces OBJECT IDENTIFIER ::= { sm24tat4xbIP 3 }

sm24tat4xbIPInterfacesDHCPPerPortMode OBJECT-TYPE
    SYNTAX      INTEGER { disable(0), enable(1) }
    MAX-ACCESS  read-write
    STATUS      current
    DESCRIPTION
        "The dhcp per-port mode for the interface.
        0: Disable,
        1: Enable,
        default: Disable. "
    ::= { sm24tat4xbIPInterfaces 1 }

sm24tat4xbIPInterfacesDHCPPerPortIPRangeLow OBJECT-TYPE
    SYNTAX      IpAddress
    MAX-ACCESS  read-write
    STATUS      current
    DESCRIPTION
        "The dhcp per-port ip low for the interface."
    ::= { sm24tat4xbIPInterfaces 2 }

sm24tat4xbIPInterfacesDHCPPerPortIPRangeHigh OBJECT-TYPE
    SYNTAX      IpAddress
    MAX-ACCESS  read-write
    STATUS      current
    DESCRIPTION
        "The dhcp per-port ip high for the interface."
    ::= { sm24tat4xbIPInterfaces 3 }

sm24tat4xbIPInterfacesDHCPPerPortApply OBJECT-TYPE
    SYNTAX      Integer32 (1)
    MAX-ACCESS  read-write
    STATUS      current
    DESCRIPTION
        "1: Apply DHCP Per Port settings."
    ::= { sm24tat4xbIPInterfaces 4 }

sm24tat4xbIPInterfacesDHCPPerPortVLAN OBJECT-TYPE
    SYNTAX      Integer32 (1..4095)
    MAX-ACCESS  read-write
    STATUS      current
    DESCRIPTION
        "dhcp per-port VLAN."
    ::= { sm24tat4xbIPInterfaces 6 }

sm24tat4xbIPInterfacesTable OBJECT-TYPE
    SYNTAX      SEQUENCE OF SM24TAT4XBIPInterfacesEntry
    MAX-ACCESS  not-accessible
    STATUS      current
    DESCRIPTION
        "A table of IP interface for switch."
    ::= { sm24tat4xbIPInterfaces 5 }

sm24tat4xbIPInterfacesEntry OBJECT-TYPE
    SYNTAX    SM24TAT4XBIPInterfacesEntry
    MAX-ACCESS    not-accessible
    STATUS    current
    DESCRIPTION
        "An entry in the sm24tat4xbIPInterfacesTable."
    INDEX    { sm24tat4xbIPInterfacesIndex }
    ::= { sm24tat4xbIPInterfacesTable 1 }

SM24TAT4XBIPInterfacesEntry ::=
    SEQUENCE {
    sm24tat4xbIPInterfacesIndex            Integer32,
    sm24tat4xbIPInterfacesVLAN            Integer32,
    sm24tat4xbIPInterfacesIPv4DHCP            Integer32,
    sm24tat4xbIPInterfacesIPv4DHCPFallback        DisplayString,
    sm24tat4xbIPInterfacesIPv4DHCPCurrentLease    IpAddress,
    sm24tat4xbIPInterfacesIPv4Address         IpAddress,
    sm24tat4xbIPInterfacesIPv4Mask            Integer32,
	sm24tat4xbIPInterfacesIPv6DHCP            Integer32,
	sm24tat4xbIPInterfacesIPv6RapidCommit         Integer32,
	sm24tat4xbIPInterfacesIPv6CurrentLease        DisplayString,
    sm24tat4xbIPInterfacesIPv6Address         DisplayString,
    sm24tat4xbIPInterfacesIPv6Mask            Integer32,
	sm24tat4xbIPInterfacesRowStatus            RowStatus
    }

sm24tat4xbIPInterfacesIndex OBJECT-TYPE
    SYNTAX      Integer32 (1..128)
    MAX-ACCESS  not-accessible
    STATUS      current
    DESCRIPTION
        "interface table index"
    ::= {sm24tat4xbIPInterfacesEntry 1 }

sm24tat4xbIPInterfacesVLAN OBJECT-TYPE
    SYNTAX      Integer32 (1..4095)
    MAX-ACCESS  read-write
    STATUS      current
    DESCRIPTION
        "VLAN ID for interface, range: 1-4095."
    ::= {sm24tat4xbIPInterfacesEntry 2 }

sm24tat4xbIPInterfacesIPv4DHCP OBJECT-TYPE
    SYNTAX      Integer32 (0|1)
    MAX-ACCESS  read-write
    STATUS      current
    DESCRIPTION
        "IPv4 DHCP Setting for interface.
        default:0
        0: disable
        1: enable"
    ::= {sm24tat4xbIPInterfacesEntry 3 }

sm24tat4xbIPInterfacesIPv4DHCPFallback OBJECT-TYPE
    SYNTAX      DisplayString
    MAX-ACCESS  read-write
    STATUS      current
    DESCRIPTION
        "IPv4 DHCP fallbcak. range: 1-4294967295 seconds."
    ::= {sm24tat4xbIPInterfacesEntry 4 }


sm24tat4xbIPInterfacesIPv4DHCPCurrentLease OBJECT-TYPE
    SYNTAX      IpAddress
    MAX-ACCESS  read-only
    STATUS      current
    DESCRIPTION
        "IPv4 DHCP Current Lease Address for interface."
    ::= {sm24tat4xbIPInterfacesEntry 5 }


sm24tat4xbIPInterfacesIPv4Address OBJECT-TYPE
    SYNTAX      IpAddress
    MAX-ACCESS  read-write
    STATUS      current
    DESCRIPTION
        "IPv4 address for interface."
    ::= {sm24tat4xbIPInterfacesEntry 6 }

sm24tat4xbIPInterfacesIPv4Mask OBJECT-TYPE
    SYNTAX      Integer32 (1..32)
    MAX-ACCESS  read-write
    STATUS      current
    DESCRIPTION
        "IPv4 mask for interface."
    ::= { sm24tat4xbIPInterfacesEntry 7 }

sm24tat4xbIPInterfacesIPv6DHCP OBJECT-TYPE
    SYNTAX      Integer32 (0|1)
    MAX-ACCESS  read-write
    STATUS      current
    DESCRIPTION
        "IPv6 DHCP Setting for interface.
        default:0
        0: disable
        1: enable"
    ::= {sm24tat4xbIPInterfacesEntry 8 }

sm24tat4xbIPInterfacesIPv6RapidCommit OBJECT-TYPE
    SYNTAX      Integer32 (0|1)
    MAX-ACCESS  read-write
    STATUS      current
    DESCRIPTION
        "Enable the DHCPv6 Rapid-Commit option.
        default:0
        0: disable
        1: enable"
    ::= {sm24tat4xbIPInterfacesEntry 9 }

sm24tat4xbIPInterfacesIPv6CurrentLease OBJECT-TYPE
    SYNTAX      DisplayString
    MAX-ACCESS  read-only
    STATUS      current
    DESCRIPTION
        "IPv6 DHCP Current Lease Address for interface."
    ::= {sm24tat4xbIPInterfacesEntry 10 }


sm24tat4xbIPInterfacesIPv6Address OBJECT-TYPE
    SYNTAX      DisplayString (SIZE (0..30))
    MAX-ACCESS  read-write
    STATUS      current
    DESCRIPTION
        "IPv6 address for interface."
    ::= { sm24tat4xbIPInterfacesEntry 11 }

sm24tat4xbIPInterfacesIPv6Mask OBJECT-TYPE
    SYNTAX      Integer32 (1..128)
    MAX-ACCESS  read-write
    STATUS      current
    DESCRIPTION
        "IPv6 mask for interface."
    ::= { sm24tat4xbIPInterfacesEntry 12 }

sm24tat4xbIPInterfacesRowStatus OBJECT-TYPE
    SYNTAX      RowStatus
    MAX-ACCESS  read-create
    STATUS      current
    DESCRIPTION
	    "This object indicates the status of this entry, and is used
		to create/delete entries.  Any object in an entry of this
		table may be modified while the value of the corresponding
		instance of this object is active(1).
		createAndGo, notReady not supported."
    ::= { sm24tat4xbIPInterfacesEntry 13 }


sm24tat4xbIPRoutes OBJECT IDENTIFIER ::= { sm24tat4xbIP 4 }

sm24tat4xbIPRoutesTable OBJECT-TYPE
    SYNTAX      SEQUENCE OF SM24TAT4XBIPRoutesEntry
    MAX-ACCESS  not-accessible
    STATUS      current
    DESCRIPTION
        "IP routes table for switch."
    ::= { sm24tat4xbIPRoutes 1 }

sm24tat4xbIPRoutesEntry OBJECT-TYPE
    SYNTAX    SM24TAT4XBIPRoutesEntry
    MAX-ACCESS    not-accessible
    STATUS    current
    DESCRIPTION
        "Entry in the sm24tat4xbIPRoutesTable."
    INDEX    { sm24tat4xbIPRoutesIndex }
    ::= { sm24tat4xbIPRoutesTable 1 }

SM24TAT4XBIPRoutesEntry ::=
    SEQUENCE {
    sm24tat4xbIPRoutesIndex            Integer32,
    sm24tat4xbIPRoutesNetwork             DisplayString,
    sm24tat4xbIPRoutesMaskLength          Integer32,
    sm24tat4xbIPRoutesGateway             DisplayString,
    sm24tat4xbIPRoutesNextHopVLAN         Integer32,
	sm24tat4xbIPRoutesRowStatus            RowStatus
    }

sm24tat4xbIPRoutesIndex OBJECT-TYPE
    SYNTAX      Integer32 (1..32)
    MAX-ACCESS  not-accessible
    STATUS      current
    DESCRIPTION
        "routes table index"
    ::= {sm24tat4xbIPRoutesEntry 2 }

sm24tat4xbIPRoutesNetwork OBJECT-TYPE
    SYNTAX      DisplayString (SIZE (0..30))
    MAX-ACCESS  read-write
    STATUS      current
    DESCRIPTION
        "IPv4/IPv6 Network address.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry.
        If Set IPRoutesNetwork, please also set IPRoutesMaskLength, IPRoutesGateway, IPRoutesNextHopVLAN."
    ::= {sm24tat4xbIPRoutesEntry 3 }

sm24tat4xbIPRoutesMaskLength OBJECT-TYPE
    SYNTAX      Integer32 (1..32)
    MAX-ACCESS  read-write
    STATUS      current
    DESCRIPTION
        "IPv4/IPv6 mask length.
        Please set IPRoutesNetwork first.
        Note: All entries in routes table will be sort by 1.network address 2.mask length 3. gateway 4. next hop VLAN, if you add/modify an entry, all entries will be reordered. Please check all entries in table to find your modified entry after set/add an entry."
    ::= { sm24tat4xbIPRoutesEntry 4 }

sm24tat4xbIPRoutesGateway OBJECT-TYPE
    SYNTAX      DisplayString (SIZE (0..30))
    MAX-ACCESS  read-write
    STATUS      current
    DESCRIPTION
        "IPv4/IPv6 Gateway.
        Please set IPRoutesNetwork first.
        Please don't set IPRoutesNetwork to IPv6 and then Set IPRoutesGateway to IPv4, vice versa.
        Note: All entries in routes table will be sort by 1.network address 2.mask length 3. gateway 4. next hop VLAN, if you add/modify an entry, all entries will be reordered. Please check all entries in table to find your modified entry after set/add an entry."
    ::= {sm24tat4xbIPRoutesEntry 5 }

sm24tat4xbIPRoutesNextHopVLAN OBJECT-TYPE
    SYNTAX      Integer32 (1..4095)
    MAX-ACCESS  read-write
    STATUS      current
    DESCRIPTION
        "Next Hop VLAN ID, range: 1-4095.
        Please set IPRoutesNetwork first.
        This entry only work when 1.network address is IPv6, 2.Gateway is link-local, 3.Interface of specific VLAN ID is IPv6.
        Note: All entries in routes table will be sort by 1.network address 2.mask length 3. gateway 4. next hop VLAN, if you add/modify an entry, all entries will be reordered. Please check all entries in table to find your modified entry after set/add an entry."
    ::= {sm24tat4xbIPRoutesEntry 6 }

sm24tat4xbIPRoutesRowStatus OBJECT-TYPE
    SYNTAX      RowStatus
    MAX-ACCESS  read-create
    STATUS      current
    DESCRIPTION
	    "This object indicates the status of this entry, and is used
		to create/delete entries.  Any object in an entry of this
		table may be modified while the value of the corresponding
		instance of this object is active(1).
		createAndGo, notReady not supported."
    ::= { sm24tat4xbIPRoutesEntry 7 }

sm24tat4xbIPStatusInterface OBJECT IDENTIFIER ::= { sm24tat4xbIP 8 }

sm24tat4xbIPStatusInterfaceTable OBJECT-TYPE
        SYNTAX      SEQUENCE OF     SM24TAT4XBIPStatusInterfaceEntry
        MAX-ACCESS  not-accessible
        STATUS      current
        DESCRIPTION
            "The system IP Status table to show all IP interfaces."
        ::= {     sm24tat4xbIPStatusInterface 1 }

    sm24tat4xbIPStatusInterfaceEntry OBJECT-TYPE
        SYNTAX      SM24TAT4XBIPStatusInterfaceEntry
        MAX-ACCESS  not-accessible
        STATUS      current
        DESCRIPTION
            "An entry in the IP Status Table."
        INDEX    {    sm24tat4xbIPStatusInterfaceIndex  }
        ::= {     sm24tat4xbIPStatusInterfaceTable 1 }

    SM24TAT4XBIPStatusInterfaceEntry         ::= SEQUENCE {
        sm24tat4xbIPStatusInterfaceIndex     Integer32,
        sm24tat4xbIPStatusInterfaceName      DisplayString,
        sm24tat4xbIPStatusInterfaceType      DisplayString,
        sm24tat4xbIPStatusInterfaceAddress    DisplayString,
        sm24tat4xbIPStatusInterfaceStatus    DisplayString
        }

    sm24tat4xbIPStatusInterfaceIndex OBJECT-TYPE
        SYNTAX      Integer32(1..1024)
        MAX-ACCESS  not-accessible
        STATUS      current
        DESCRIPTION
            "The entry of table to show all IP interfaces."
        ::= {     sm24tat4xbIPStatusInterfaceEntry 1 }

    sm24tat4xbIPStatusInterfaceName OBJECT-TYPE
        SYNTAX      DisplayString
        MAX-ACCESS  read-only
        STATUS      current
        DESCRIPTION
            "The name of the interface."
        ::= {     sm24tat4xbIPStatusInterfaceEntry 2 }

    sm24tat4xbIPStatusInterfaceType OBJECT-TYPE
        SYNTAX      DisplayString
        MAX-ACCESS  read-only
        STATUS      current
        DESCRIPTION
            "The address type of the entry. This may be LINK or IPv4."
        ::= {     sm24tat4xbIPStatusInterfaceEntry 3 }

    sm24tat4xbIPStatusInterfaceAddress OBJECT-TYPE
        SYNTAX      DisplayString
        MAX-ACCESS  read-only
        STATUS      current
        DESCRIPTION
            "The current address of the interface (of the given type)."
        ::= {     sm24tat4xbIPStatusInterfaceEntry 4 }

    sm24tat4xbIPStatusInterfaceStatus OBJECT-TYPE
        SYNTAX      DisplayString
        MAX-ACCESS  read-only
        STATUS      current
        DESCRIPTION
            "The status flags of the interface (and/or address)."
        ::= {     sm24tat4xbIPStatusInterfaceEntry 5 }

sm24tat4xbIPStatusRoute OBJECT IDENTIFIER ::= { sm24tat4xbIP 9 }

    sm24tat4xbIPStatusRouteTable OBJECT-TYPE
        SYNTAX      SEQUENCE OF     SM24TAT4XBIPStatusRouteEntry
        MAX-ACCESS  not-accessible
        STATUS      current
        DESCRIPTION
            "The IP Status Route table show all routing entries."
        ::= {     sm24tat4xbIPStatusRoute 1 }

    sm24tat4xbIPStatusRouteEntry OBJECT-TYPE
        SYNTAX      SM24TAT4XBIPStatusRouteEntry
        MAX-ACCESS  not-accessible
        STATUS      current
        DESCRIPTION
            "an entry in the IP Status route table."
        INDEX    {     sm24tat4xbIPStatusRouteIndex  }
        ::= {     sm24tat4xbIPStatusRouteTable 1 }

    SM24TAT4XBIPStatusRouteEntry         ::= SEQUENCE {
        sm24tat4xbIPStatusRouteIndex      Integer32,
        sm24tat4xbIPStatusRouteNetwork    DisplayString,
        sm24tat4xbIPStatusRouteGateway    DisplayString,
        sm24tat4xbIPStatusRouteAddress    DisplayString
     }

    sm24tat4xbIPStatusRouteIndex OBJECT-TYPE
        SYNTAX      Integer32(1..2048)
        MAX-ACCESS  not-accessible
        STATUS      current
        DESCRIPTION
            "The entry of table to show all routing entries."
        ::= {     sm24tat4xbIPStatusRouteEntry 1 }

    sm24tat4xbIPStatusRouteNetwork OBJECT-TYPE
        SYNTAX      DisplayString
        MAX-ACCESS  read-only
        STATUS      current
        DESCRIPTION
            "The destination IP network or host address of this route."
        ::= {     sm24tat4xbIPStatusRouteEntry 2 }

    sm24tat4xbIPStatusRouteGateway OBJECT-TYPE
        SYNTAX      DisplayString
        MAX-ACCESS  read-only
        STATUS      current
        DESCRIPTION
            "The gateway address of this route."
        ::= {     sm24tat4xbIPStatusRouteEntry 3 }

    sm24tat4xbIPStatusRouteAddress OBJECT-TYPE
        SYNTAX      DisplayString
        MAX-ACCESS  read-only
        STATUS      current
        DESCRIPTION
            "The route address."
        ::= {     sm24tat4xbIPStatusRouteEntry 4 }

sm24tat4xbIPStatusNeighborCache OBJECT IDENTIFIER ::= { sm24tat4xbIP 10 }

    sm24tat4xbIPStatusNeighborCacheTable OBJECT-TYPE
    SYNTAX      SEQUENCE OF     SM24TAT4XBIPStatusNeighborCacheEntry
    MAX-ACCESS  not-accessible
    STATUS      current
    DESCRIPTION
        "The Ip Status Neighbor Cache Table."
    ::= {     sm24tat4xbIPStatusNeighborCache 1 }

    sm24tat4xbIPStatusNeighborCacheEntry OBJECT-TYPE
    SYNTAX      SM24TAT4XBIPStatusNeighborCacheEntry
    MAX-ACCESS  not-accessible
    STATUS      current
    DESCRIPTION
        "An entry in the Ip Status Neighbor Cache Table."
    INDEX    {     sm24tat4xbIPStatusNeighborCacheIndex  }
    ::= {     sm24tat4xbIPStatusNeighborCacheTable 1 }

    SM24TAT4XBIPStatusNeighborCacheEntry ::= SEQUENCE {
        sm24tat4xbIPStatusNeighborCacheIndex        Integer32,
        sm24tat4xbIPStatusNeighborCacheIPAddress    DisplayString,
        sm24tat4xbIPStatusNeighborCacheLinkAddress      DisplayString
        }

    sm24tat4xbIPStatusNeighborCacheIndex OBJECT-TYPE
    SYNTAX      Integer32(1..1024)
    MAX-ACCESS  not-accessible
    STATUS      current
    DESCRIPTION
        "The index for the Ip Status Neighbor Cache Table."
    ::= {     sm24tat4xbIPStatusNeighborCacheEntry 1 }

    sm24tat4xbIPStatusNeighborCacheIPAddress OBJECT-TYPE
    SYNTAX      DisplayString
    MAX-ACCESS  read-only
    STATUS      current
    DESCRIPTION
        "The IP address of the entry."
    ::= {     sm24tat4xbIPStatusNeighborCacheEntry 2 }

    sm24tat4xbIPStatusNeighborCacheLinkAddress OBJECT-TYPE
    SYNTAX      DisplayString
    MAX-ACCESS  read-only
    STATUS      current
    DESCRIPTION
        "The Link (MAC) address for which a binding to the
        IP address given exist."
    ::= {     sm24tat4xbIPStatusNeighborCacheEntry 3 }

sm24tat4xbIPStatusDNSServer OBJECT IDENTIFIER ::= { sm24tat4xbIP 11 }

    sm24tat4xbIPStatusDNSServerType OBJECT-TYPE
    SYNTAX      DisplayString
    MAX-ACCESS  read-only
    STATUS      current
    DESCRIPTION
        "The configuration type of DNS server."
    ::= {     sm24tat4xbIPStatusDNSServer 1 }

    sm24tat4xbIPStatusDNSServerIPAddress OBJECT-TYPE
    SYNTAX      DisplayString
    MAX-ACCESS  read-only
    STATUS      current
    DESCRIPTION
        "The IP address of the DNS server."
    ::= {     sm24tat4xbIPStatusDNSServer 2 }

    sm24tat4xbIPStatusDNSServerInterface OBJECT-TYPE
    SYNTAX      DisplayString
    MAX-ACCESS  read-only
    STATUS      current
    DESCRIPTION
        "The name of the interface."
    ::= {     sm24tat4xbIPStatusDNSServer 3 }

-- =======================================================================================================================
sm24tat4xbSyslog                        OBJECT IDENTIFIER ::= { sm24tat4xbSystem 5 }

sm24tat4xbSyslogConf                        OBJECT IDENTIFIER ::= { sm24tat4xbSyslog 1 }

sm24tat4xbSysLogInfo                        OBJECT IDENTIFIER    ::= {  sm24tat4xbSyslog 2 }
--
-- =======================================================================================================================
-- Objects in the sm24tat4xbSystemLog Group
-- =======================================================================================================================
--sm24tat4xbSystemLogConf

    sm24tat4xbSystemLogServerMode OBJECT-TYPE
    SYNTAX      AdminMode
    MAX-ACCESS  read-write
    STATUS      current
    DESCRIPTION
        "The System log server mode admin state."
    DEFVAL  { disable }
    ::= {     sm24tat4xbSyslogConf 1 }

    sm24tat4xbSystemLogServerAddress OBJECT-TYPE
    SYNTAX      DisplayString
    MAX-ACCESS  read-write
    STATUS      current
    DESCRIPTION
        "The Host address of syslog server."
    ::= {     sm24tat4xbSyslogConf 2 }

--    sm24tat4xbSystemLogSyslogLevel OBJECT-TYPE
--        SYNTAX      INTEGER {
--            info(0),
--            warning(1),
--            error(2)
--        }
--        MAX-ACCESS  read-write
--        STATUS      current
--        DESCRIPTION
--            "The syslog level.
--            info(0)    : Info.
--            warning(1): Warning.
--            error(2)  : Error."
--        DEFVAL  { info }
--        ::= {     sm24tat4xbSyslogConf 3 }

    sm24tat4xbSystemLogServerPort OBJECT-TYPE
    SYNTAX      Integer32(1..65535)
    MAX-ACCESS  read-write
    STATUS      current
    DESCRIPTION
        "syslog service port number.
        range : 1-65535, default : 514."
    ::= {     sm24tat4xbSyslogConf 4 }

--sm24tat4xbSystemLogInfo
    sm24tat4xbSystemLogInfoLevel OBJECT-TYPE
    SYNTAX      INTEGER { emergency(0), alert(1), critical(2), error(3), warning(4), notice(5), information(6), debug(7), all(8) }
    MAX-ACCESS  read-write
    STATUS      current
    DESCRIPTION
        "The Level input field is used to filter the display system log entries.
        0: Emergency.
        1: Alert.
        2: Critical.
        3: Error.
        4: Warning.
        5: Notice.
        6: Information.
        7: Debug.
        8: All."
    DEFVAL  { all }
    ::= {     sm24tat4xbSysLogInfo 1 }

    sm24tat4xbSystemLogInfoClearLevel OBJECT-TYPE
    SYNTAX      INTEGER { emergency(0), alert(1), critical(2), error(3), warning(4), notice(5), information(6), debug(7), all(8) }
    MAX-ACCESS  read-write
    STATUS      current
    DESCRIPTION
        "The Clear Level input field is used to specify which
        system log entries will be cleared.
        default: 8 (All).
        0: Emergency.
        1: Alert.
        2: Critical.
        3: Error.
        4: Warning.
        5: Notice.
        6: Information.
        7: Debug.
        8: All."
    DEFVAL  { all }
    ::= {     sm24tat4xbSysLogInfo 2 }

    sm24tat4xbSystemLogInfoClearCmd OBJECT-TYPE
    SYNTAX      ActivateCmd
    MAX-ACCESS  read-write
    STATUS      current
    DESCRIPTION
        "Command to clear the syslog.
        noAction(0) : do nothing  (read only).
        activate(1) : Clear Syslog."
    DEFVAL  { noAction }
    ::= {     sm24tat4xbSysLogInfo 3 }

    sm24tat4xbSystemLogDetailedInfoTable OBJECT-TYPE
    SYNTAX      SEQUENCE OF     SM24TAT4XBSystemLogDetailedInfoEntry
    MAX-ACCESS  not-accessible
    STATUS      current
    DESCRIPTION
        "The system detailed Log Info table."
    ::= {     sm24tat4xbSysLogInfo 4 }

    sm24tat4xbSystemLogDetailedInfoEntry OBJECT-TYPE
    SYNTAX      SM24TAT4XBSystemLogDetailedInfoEntry
    MAX-ACCESS  not-accessible
    STATUS      current
    DESCRIPTION
        "An entry in the system detailed Log Info table."
    INDEX    {     sm24tat4xbSystemLogDetailedInfoID  }
    ::= {     sm24tat4xbSystemLogDetailedInfoTable 1 }

    SM24TAT4XBSystemLogDetailedInfoEntry         ::= SEQUENCE {
    sm24tat4xbSystemLogDetailedSwitchIndex    Integer32,
    sm24tat4xbSystemLogDetailedInfoID        Integer32,
    sm24tat4xbSystemLogDetailedInfoLevel     DisplayString,
    sm24tat4xbSystemLogDetailedInfoTime      DisplayString,
    sm24tat4xbSystemLogDetailedInfoMessage    DisplayString
    }

    sm24tat4xbSystemLogDetailedSwitchIndex OBJECT-TYPE
    SYNTAX      Integer32(1..16)
    MAX-ACCESS  not-accessible
    STATUS      current
    DESCRIPTION
        "The switch index for the system detailed Log Info table."
    ::= {     sm24tat4xbSystemLogDetailedInfoEntry 1 }

    sm24tat4xbSystemLogDetailedInfoID OBJECT-TYPE
    SYNTAX      Integer32(1..999)
    MAX-ACCESS  not-accessible
    STATUS      current
    DESCRIPTION
        "The index for the system detailed Log Info table."
    ::= {     sm24tat4xbSystemLogDetailedInfoEntry 2 }

    sm24tat4xbSystemLogDetailedInfoLevel OBJECT-TYPE
    SYNTAX      DisplayString
    MAX-ACCESS  read-only
    STATUS      current
    DESCRIPTION
        "The Info Level."
    ::= {     sm24tat4xbSystemLogDetailedInfoEntry 3 }

    sm24tat4xbSystemLogDetailedInfoTime OBJECT-TYPE
    SYNTAX      DisplayString(SIZE (0..20))
    MAX-ACCESS  read-only
    STATUS      current
    DESCRIPTION
        "The time"
    ::= {     sm24tat4xbSystemLogDetailedInfoEntry 4 }

    sm24tat4xbSystemLogDetailedInfoMessage OBJECT-TYPE
    SYNTAX      DisplayString
    MAX-ACCESS  read-only
    STATUS      current
    DESCRIPTION
        "The message of this entry."
    ::= {     sm24tat4xbSystemLogDetailedInfoEntry 5 }
-- =======================================================================================================================
sm24tat4xbSnmp                        OBJECT IDENTIFIER ::= { sm24tat4xbSystem 6 }

sm24tat4xbSnmpSystem                        OBJECT IDENTIFIER ::= { sm24tat4xbSnmp 1 }

sm24tat4xbSnmpSystemMode OBJECT-TYPE
    SYNTAX    Integer32
    MAX-ACCESS    read-write
    STATUS    current
    DESCRIPTION
        "SNMP mode operation.
        default : 1, 0: disable, 1: enable. "
    ::= { sm24tat4xbSnmpSystem 1 }

sm24tat4xbSnmpSystemVersion OBJECT-TYPE
    SYNTAX    Integer32
    MAX-ACCESS    read-write
    STATUS    current
    DESCRIPTION
        "SNMP supported version.
        default : snmpv2c.
        1: snmpv1
        2: snmpv2c
        3: snmpv3."
    ::= { sm24tat4xbSnmpSystem 2 }

sm24tat4xbSnmpSystemReadCommunity OBJECT-TYPE
    SYNTAX    DisplayString
    MAX-ACCESS    read-write
    STATUS    current
    DESCRIPTION
        "Indicates the community read access string to permit access to SNMP agent.
        The allowed string length is 0 to 255.
        The field is applicable only when SNMP version is SNMPv1 or SNMPv2c."
    ::= { sm24tat4xbSnmpSystem 3 }

sm24tat4xbSnmpSystemWriteCommunity OBJECT-TYPE
    SYNTAX    DisplayString
    MAX-ACCESS    read-write
    STATUS    current
    DESCRIPTION
        "Indicates the community write access string to permit access to SNMP agent.
        The allowed string length is 0 to 255.
        The field is applicable only when SNMP version is SNMPv1 or SNMPv2c."
    ::= { sm24tat4xbSnmpSystem 4 }

--sm24tat4xbSnmpSystemEngineID OBJECT-TYPE
--    SYNTAX    DisplayString
--    MAX-ACCESS    read-write
--    STATUS    current
--    DESCRIPTION
--    "Indicates the SNMPv3 engine ID.
--    The string must contain an even number(in hexadecimal format) with number of digits between 10 and 64,
--	but all-zeros and all-'F's are not allowed.
--	Allow string length is 10 to 32.
--	Change of the Engine ID will clear all original local users."
--    ::= { sm24tat4xbSnmpSystem 5 }

sm24tat4xbSnmpSystemWriteCommunityMode OBJECT-TYPE
    SYNTAX    Integer32
    MAX-ACCESS    read-write
    STATUS    current
    DESCRIPTION
        "SNMP write community mode operation.
        default : 1, 0: disable, 1: enable. "
    ::= { sm24tat4xbSnmpSystem 6 }

sm24tat4xbSnmpSystemReadCommunityMode OBJECT-TYPE
    SYNTAX    Integer32
    MAX-ACCESS    read-write
    STATUS    current
    DESCRIPTION
        "SNMP read community mode operation.
        default : 1, 0: disable, 1: enable. "
    ::= { sm24tat4xbSnmpSystem 7 }


--sm24tat4xbSnmpTrapGlobalMode OBJECT-TYPE
--    SYNTAX    Integer32
--    MAX-ACCESS    read-write
--    STATUS    current
--    DESCRIPTION
--    "Indicates the trap mode operation.
--    0:Disable.
--	1:Enable."
--    ::= { sm24tat4xbSnmp 2 }

sm24tat4xbTrapDestinationConfTable OBJECT-TYPE
    SYNTAX      SEQUENCE OF SM24TAT4XBTrapDestinationConfEntry
    MAX-ACCESS  not-accessible
    STATUS      current
    DESCRIPTION
        "A list of trap host entry. The numbers of entries are given by the value of TrapHostConfNumber."
    ::= { sm24tat4xbSnmp 3 }

sm24tat4xbTrapDestinationConfEntry OBJECT-TYPE
    SYNTAX      SM24TAT4XBTrapDestinationConfEntry
    MAX-ACCESS  not-accessible
    STATUS      current
    DESCRIPTION
        "This is the entry information for trap host."
    INDEX    { sm24tat4xbTrapDestinationConfIndex  }
    ::= { sm24tat4xbTrapDestinationConfTable 1 }

SM24TAT4XBTrapDestinationConfEntry ::= SEQUENCE {
    sm24tat4xbTrapDestinationConfIndex              Integer32,
    sm24tat4xbTrapDestinationConfTrapConfigName         DisplayString,
    sm24tat4xbTrapDestinationConfTrapMode            Integer32,
    sm24tat4xbTrapDestinationConfTrapVersion        Integer32,
    sm24tat4xbTrapDestinationConfTrapCommunity          DisplayString,
    sm24tat4xbTrapDestinationConfTrapDestinationAddres      DisplayString,
    sm24tat4xbTrapDestinationConfTrapDestinationPort    Integer32,
--  sm24tat4xbTrapDestinationConfTrapInformMode         Integer32,
--  sm24tat4xbTrapDestinationConfTrapInformTimeout      Integer32,
--  sm24tat4xbTrapDestinationConfTrapInformRetryTimes    Integer32,
--  sm24tat4xbTrapDestinationConfTrapProbeSecurityEngineID  Integer32,
    sm24tat4xbTrapDestinationConfTrapSecurityEngineID    DisplayString,
    sm24tat4xbTrapDestinationConfTrapSecurityName        DisplayString,
    sm24tat4xbTrapDestinationConfTrapRowStatus          Integer32
}

sm24tat4xbTrapDestinationConfIndex OBJECT-TYPE
    SYNTAX    Integer32(1..65535)
    MAX-ACCESS    not-accessible
    STATUS    current
    DESCRIPTION
        "Index of tarp destination configurations."
    ::= { sm24tat4xbTrapDestinationConfEntry 1 }

sm24tat4xbTrapDestinationConfTrapConfigName OBJECT-TYPE
    SYNTAX    DisplayString
    MAX-ACCESS    read-write
    STATUS    current
    DESCRIPTION
        "Indicates which trap Configuration's name for configuring.
        The allowed string length is 0 to 255, and the allowed content is
        ASCII characters from 33 to 126."
    ::= { sm24tat4xbTrapDestinationConfEntry 2 }

sm24tat4xbTrapDestinationConfTrapMode OBJECT-TYPE
    SYNTAX    Integer32
    MAX-ACCESS    read-write
    STATUS    current
    DESCRIPTION
        "Indicates the SNMP mode operation. Possible modes are:
        2: Enable TCP SNMP mode operation.
        1: Enable UDP SNMP mode operation.
        0: Disable SNMP mode operation. "
    ::= { sm24tat4xbTrapDestinationConfEntry 3 }

sm24tat4xbTrapDestinationConfTrapVersion OBJECT-TYPE
    SYNTAX    Integer32
    MAX-ACCESS    read-write
    STATUS    current
    DESCRIPTION
        "0: snmpv1
        1: snmpv2c
        3: snmpv3.
        "
    ::= { sm24tat4xbTrapDestinationConfEntry 4 }

sm24tat4xbTrapDestinationConfTrapCommunity OBJECT-TYPE
    SYNTAX    DisplayString
    MAX-ACCESS    read-write
    STATUS    current
    DESCRIPTION
        "Indicates the community access string when sending SNMP trap packet.
        The allowed string length is 0 to 255, and the allowed content is
        ASCII characters from 33 to 126."
    ::= { sm24tat4xbTrapDestinationConfEntry 5 }

sm24tat4xbTrapDestinationConfTrapDestinationAddres OBJECT-TYPE
    SYNTAX    DisplayString
    MAX-ACCESS    read-write
    STATUS    current
    DESCRIPTION
        "Indicates the SNMP trap destination address.
        It allow a valid IP address in dotted decimal notation ('x.y.z.w').
        And it also allow a valid hostname.
        A valid hostname is a string drawn from the alphabet (A-Za-z), digits (0-9),
        dot (.), dash (-). Spaces are not allowed, the first character must be an alpha character,
        and the first and last characters must not be a dot or a dash.
        Indicates the SNMP trap destination IPv6 address.
        IPv6 address is in 128-bit records represented as eight fields of up to four hexadecimal digits
        with a colon separating each field (:).
        For example, 'fe80::215:c5ff:fe03:4dc7'. The symbol '::' is a special syntax
        that can be used as a shorthand way of representing multiple 16-bit groups of contiguous zeros;
        but it can appear only once.
        It can also represent a legally valid IPv4 address.
        For example, '::192.1.2.34'."
    ::= { sm24tat4xbTrapDestinationConfEntry 6 }

sm24tat4xbTrapDestinationConfTrapDestinationPort OBJECT-TYPE
    SYNTAX    Integer32
    MAX-ACCESS    read-write
    STATUS    current
    DESCRIPTION
        "Indicates the SNMP trap destination port.
        SNMP Agent will send SNMP message via this port,
        the port range is 1~65535."
    ::= { sm24tat4xbTrapDestinationConfEntry 7 }

--sm24tat4xbTrapDestinationConfTrapInformMode OBJECT-TYPE
--    SYNTAX    Integer32
--    MAX-ACCESS    read-write
--    STATUS    current
--    DESCRIPTION
--    "Indicates the SNMP trap inform mode operation. Possible modes are:
--    1: Enable SNMP trap inform mode operation.
--    0: Disable SNMP trap inform mode operation. "
--    ::= { sm24tat4xbTrapDestinationConfEntry 8 }
--
--sm24tat4xbTrapDestinationConfTrapInformTimeout OBJECT-TYPE
--    SYNTAX    Integer32
--    MAX-ACCESS    read-write
--    STATUS    current
--    DESCRIPTION
--    "Indicates the SNMP trap inform timeout. The allowed range is 0 to 2147."
--    ::= { sm24tat4xbTrapDestinationConfEntry 9 }
--
--sm24tat4xbTrapDestinationConfTrapInformRetryTimes OBJECT-TYPE
--    SYNTAX    Integer32
--    MAX-ACCESS    read-write
--    STATUS    current
--    DESCRIPTION
--    "Indicates the SNMP trap inform retry times. The allowed range is 0 to 255."
--    ::= { sm24tat4xbTrapDestinationConfEntry 10 }
--
--sm24tat4xbTrapDestinationConfTrapProbeSecurityEngineID OBJECT-TYPE
--    SYNTAX    Integer32
--    MAX-ACCESS    read-write
--    STATUS    current
--    DESCRIPTION
--    "Indicates the SNMP trap probe security engine ID mode of operation.
--    Possible values are:
--    1: Enable SNMP trap probe security engine ID mode of operation.
--    0: Disable SNMP trap probe security engine ID mode of operation."
--    ::= { sm24tat4xbTrapDestinationConfEntry 11 }

sm24tat4xbTrapDestinationConfTrapSecurityEngineID OBJECT-TYPE
    SYNTAX    DisplayString
    MAX-ACCESS    read-write
    STATUS    current
    DESCRIPTION
        "Indicates the SNMP trap security engine ID.
        SNMPv3 sends traps and informs using USM for authentication and privacy.
        A unique engine ID for these traps and informs is needed.
        When Trap Probe Security Engine ID is enabled, the ID will be probed automatically.
        Otherwise, the ID specified in this field is used.
        The string must contain an even number(in hexadecimal format) with
        number of digits between 10 and 64, but all-zeros and all-'F's are not allowed."
    ::= { sm24tat4xbTrapDestinationConfEntry 12 }

sm24tat4xbTrapDestinationConfTrapSecurityName OBJECT-TYPE
    SYNTAX    DisplayString
    MAX-ACCESS    read-write
    STATUS    current
    DESCRIPTION
        "Indicates the SNMP trap security name.
        SNMPv3 traps and informs using USM for authentication and privacy.
        A unique security name is needed when traps and informs are enabled.
        This name from user name of user configuration."
    ::= { sm24tat4xbTrapDestinationConfEntry 13 }

sm24tat4xbTrapDestinationConfTrapRowStatus OBJECT-TYPE
    SYNTAX    Integer32
    MAX-ACCESS    read-write
    STATUS    current
    DESCRIPTION
        "This object indicates the status of this entry, and is
        used to create(5)/delete(6) entries.  Any object in an entry of
        this table may be modified while the value of the
        corresponding instance of this object is active(1).
        createAndGo, notReady not supported."
    ::= { sm24tat4xbTrapDestinationConfEntry 14 }


sm24tat4xbSNMPCommunityConfTable OBJECT-TYPE
    SYNTAX      SEQUENCE OF SM24TAT4XBSNMPCommunityConfEntry
    MAX-ACCESS  not-accessible
    STATUS      current
    DESCRIPTION
        "A list of snmp community configuration entry."
    ::= { sm24tat4xbSnmp 5 }

sm24tat4xbSNMPCommunityConfEntry OBJECT-TYPE
    SYNTAX      SM24TAT4XBSNMPCommunityConfEntry
    MAX-ACCESS  not-accessible
    STATUS      current
    DESCRIPTION
        "This is the entry information for snmp community configuration."
    INDEX    { sm24tat4xbSNMPCommunityConfIndex  }
    ::= { sm24tat4xbSNMPCommunityConfTable 1 }

SM24TAT4XBSNMPCommunityConfEntry ::= SEQUENCE {
    sm24tat4xbSNMPCommunityConfIndex            Integer32,
    sm24tat4xbSNMPCommunityConfSNMPv3Community         DisplayString,
    sm24tat4xbSNMPCommunityConfSNMPv3SourceIP          IpAddress,
    sm24tat4xbSNMPCommunityConfSNMPv3SourceMask        IpAddress,
    sm24tat4xbSNMPCommunityConfSNMPv3RowStatus         Integer32
}

sm24tat4xbSNMPCommunityConfIndex OBJECT-TYPE
    SYNTAX    Integer32(1..65535)
    MAX-ACCESS    read-write
    STATUS    current
    DESCRIPTION
        "Community configuration index."
    ::= { sm24tat4xbSNMPCommunityConfEntry 1 }

sm24tat4xbSNMPCommunityConfSNMPv3Community OBJECT-TYPE
    SYNTAX    DisplayString
    MAX-ACCESS    read-write
    STATUS    current
    DESCRIPTION
        "Indicates the community access string to permit access to SNMPv3 agent.
        The allowed string length is 1 to 32, and the allowed content is
        ASCII characters from 33 to 126.
        The community string will be treated as security name and map a SNMPv1
        or SNMPv2c community string."
    ::= { sm24tat4xbSNMPCommunityConfEntry 2 }


sm24tat4xbSNMPCommunityConfSNMPv3SourceIP OBJECT-TYPE
    SYNTAX      IpAddress
    MAX-ACCESS  read-write
    STATUS      current
    DESCRIPTION
        "Indicates the SNMP access source address.
        A particular range of source addresses can be used to restrict source subnet
        when combined with source mask."
    ::= {sm24tat4xbSNMPCommunityConfEntry 3 }

sm24tat4xbSNMPCommunityConfSNMPv3SourceMask OBJECT-TYPE
    SYNTAX      IpAddress
    MAX-ACCESS  read-write
    STATUS      current
    DESCRIPTION
        "Indicates the SNMP access source address mask."
    ::= {sm24tat4xbSNMPCommunityConfEntry 4 }

sm24tat4xbSNMPCommunityConfSNMPv3RowStatus OBJECT-TYPE
    SYNTAX    Integer32
    MAX-ACCESS    read-write
    STATUS    current
    DESCRIPTION
        "This object indicates the status of this entry, and is
        used to create(5)/delete(6) entries.  Any object in an entry of
        this table may be modified while the value of the
        corresponding instance of this object is active(1).
        createAndGo, notReady not supported."
    ::= { sm24tat4xbSNMPCommunityConfEntry 5 }

sm24tat4xbSNMPv3UserConfTable OBJECT-TYPE
    SYNTAX      SEQUENCE OF SM24TAT4XBSNMPv3UserConfEntry
    MAX-ACCESS  not-accessible
    STATUS      current
    DESCRIPTION
        "A list of snmpv3 user configuration entry."
    ::= { sm24tat4xbSnmp 6 }

sm24tat4xbSNMPv3UserConfEntry OBJECT-TYPE
    SYNTAX      SM24TAT4XBSNMPv3UserConfEntry
    MAX-ACCESS  not-accessible
    STATUS      current
    DESCRIPTION
        "This is the entry information for snmpv3 user configuration."
    INDEX    { sm24tat4xbSNMPv3UserConfIndex  }
    ::= { sm24tat4xbSNMPv3UserConfTable 1 }

SM24TAT4XBSNMPv3UserConfEntry ::= SEQUENCE {
    sm24tat4xbSNMPv3UserConfIndex             Integer32,
    sm24tat4xbSNMPv3UserConfEngineID          DisplayString,
    sm24tat4xbSNMPv3UserConfUserName          DisplayString,
    sm24tat4xbSNMPv3UserConfSecurityLevel         Integer32,
    sm24tat4xbSNMPv3UserConfAuthenticationProtocol    Integer32,
    sm24tat4xbSNMPv3UserConfAuthenticationPassword    DisplayString,
    sm24tat4xbSNMPv3UserConfPrivacyProtocol        Integer32,
    sm24tat4xbSNMPv3UserConfPrivacyPassword        DisplayString,
    sm24tat4xbSNMPv3UserConfRowStatus         RowStatus
}

sm24tat4xbSNMPv3UserConfIndex OBJECT-TYPE
    SYNTAX    Integer32(1..65535)
    MAX-ACCESS    read-write
    STATUS    current
    DESCRIPTION
        "User configuration index."
    ::= { sm24tat4xbSNMPv3UserConfEntry 1 }

sm24tat4xbSNMPv3UserConfEngineID OBJECT-TYPE
    SYNTAX    DisplayString
    MAX-ACCESS    read-write
    STATUS    current
    DESCRIPTION
        "An octet string identifying the engine ID that this entry should belong to.
        The string must contain an even number(in hexadecimal format) with
        number of digits between 10 and 64, but all-zeros and all-'F's are not allowed.
        The SNMPv3 architecture uses the User-based Security Model (USM)
        for message security and the View-based Access Control Model (VACM) for access control.
        For the USM entry, the usmUserEngineID and usmUserName are the entry's keys.
        In a simple agent, usmUserEngineID is always that agent's own snmpEngineID value.
        The value can also take the value of the snmpEngineID of a remote SNMP engine with
        which this user can communicate. In other words, if user engine ID equal system engine ID
        then it is local user; otherwise it's remote user. "
    ::= { sm24tat4xbSNMPv3UserConfEntry 2 }

sm24tat4xbSNMPv3UserConfUserName OBJECT-TYPE
    SYNTAX    DisplayString
    MAX-ACCESS    read-write
    STATUS    current
    DESCRIPTION
        "A string identifying the user name that this entry should belong to.
        The allowed string length is 1 to 32, and the allowed content is
        ASCII characters from 33 to 126."
    ::= { sm24tat4xbSNMPv3UserConfEntry 3 }

sm24tat4xbSNMPv3UserConfSecurityLevel OBJECT-TYPE
    SYNTAX    Integer32
    MAX-ACCESS    read-write
    STATUS    current
    DESCRIPTION
        "1:NoAuth, NoPriv
        2:Auth, NoPriv
	    3:Auth, Priv"
    ::= { sm24tat4xbSNMPv3UserConfEntry 4 }

sm24tat4xbSNMPv3UserConfAuthenticationProtocol OBJECT-TYPE
    SYNTAX    Integer32
    MAX-ACCESS    read-write
    STATUS    current
    DESCRIPTION
        "0:None
        1:MD5
	    2:SHA"
    ::= { sm24tat4xbSNMPv3UserConfEntry 5 }

sm24tat4xbSNMPv3UserConfAuthenticationPassword OBJECT-TYPE
    SYNTAX    DisplayString
    MAX-ACCESS    read-write
    STATUS    current
    DESCRIPTION
        "A string identifying the authentication password phrase.
        For MD5 authentication protocol, the allowed string length is 8 to 32.
        For SHA authentication protocol, the allowed string length is 8 to 40.
        The allowed content is ASCII characters from 33 to 126."
    ::= { sm24tat4xbSNMPv3UserConfEntry 6 }

sm24tat4xbSNMPv3UserConfPrivacyProtocol OBJECT-TYPE
    SYNTAX    Integer32
    MAX-ACCESS    read-write
    STATUS    current
    DESCRIPTION
        "0:None
        1:DES
        2:AES"
    ::= { sm24tat4xbSNMPv3UserConfEntry 7 }

sm24tat4xbSNMPv3UserConfPrivacyPassword OBJECT-TYPE
    SYNTAX    DisplayString
    MAX-ACCESS    read-write
    STATUS    current
    DESCRIPTION
        "A string identifying the privacy password phrase.
        The allowed string length is 8 to 32, and the allowed content is
        ASCII characters from 33 to 126."
    ::= { sm24tat4xbSNMPv3UserConfEntry 8 }

sm24tat4xbSNMPv3UserConfRowStatus OBJECT-TYPE
    SYNTAX    RowStatus
    MAX-ACCESS    read-create
    STATUS    current
    DESCRIPTION
        "This object indicates the status of this entry, and is
        used to create(5)/delete(6) entries.  Any object in an entry of
        this table may be modified while the value of the
        corresponding instance of this object is active(1).
        createAndGo, notReady not supported."
    ::= { sm24tat4xbSNMPv3UserConfEntry 9 }

sm24tat4xbSNMPv3GroupConfTable OBJECT-TYPE
    SYNTAX      SEQUENCE OF SM24TAT4XBSNMPv3GroupConfEntry
    MAX-ACCESS  not-accessible
    STATUS      current
    DESCRIPTION
        "A list of snmpv3 group configuration entry."
    ::= { sm24tat4xbSnmp 7 }

sm24tat4xbSNMPv3GroupConfEntry OBJECT-TYPE
    SYNTAX      SM24TAT4XBSNMPv3GroupConfEntry
    MAX-ACCESS  not-accessible
    STATUS      current
    DESCRIPTION
        "This is the entry information for snmpv3 group configuration."
    INDEX    { sm24tat4xbSNMPv3GroupConfIndex  }
    ::= { sm24tat4xbSNMPv3GroupConfTable 1 }

SM24TAT4XBSNMPv3GroupConfEntry ::= SEQUENCE {
    sm24tat4xbSNMPv3GroupConfIndex             Integer32,
    sm24tat4xbSNMPv3GroupConfSecurityModel         Integer32,
    sm24tat4xbSNMPv3GroupConfSecurityName      DisplayString,
    sm24tat4xbSNMPv3GroupConfGroupName         DisplayString,
    sm24tat4xbSNMPv3GroupConfRowStatus         RowStatus
}

sm24tat4xbSNMPv3GroupConfIndex OBJECT-TYPE
    SYNTAX    Integer32(1..65535)
    MAX-ACCESS    read-write
    STATUS    current
    DESCRIPTION
        "Group configuration index."
    ::= { sm24tat4xbSNMPv3GroupConfEntry 1 }

sm24tat4xbSNMPv3GroupConfSecurityModel OBJECT-TYPE
    SYNTAX    Integer32
    MAX-ACCESS    read-write
    STATUS    current
    DESCRIPTION
        "1:v1
        2:v2c
	    3:usm"
    ::= { sm24tat4xbSNMPv3GroupConfEntry 2 }

sm24tat4xbSNMPv3GroupConfSecurityName OBJECT-TYPE
    SYNTAX    DisplayString
    MAX-ACCESS    read-write
    STATUS    current
    DESCRIPTION
        "A string identifying the security name that this entry should belong to.
        The allowed string length is 1 to 32, and the allowed content is
        ASCII characters from 33 to 126.
        This name is from the Community of Community configuration."
    ::= { sm24tat4xbSNMPv3GroupConfEntry 3 }

sm24tat4xbSNMPv3GroupConfGroupName OBJECT-TYPE
    SYNTAX    DisplayString
    MAX-ACCESS    read-write
    STATUS    current
    DESCRIPTION
        "A string identifying the group name that this entry should belong to.
        The allowed string length is 1 to 32, and the allowed content is
        ASCII characters from 33 to 126. "
    ::= { sm24tat4xbSNMPv3GroupConfEntry 4 }


sm24tat4xbSNMPv3GroupConfRowStatus OBJECT-TYPE
    SYNTAX    RowStatus
    MAX-ACCESS    read-create
    STATUS    current
    DESCRIPTION
        "This object indicates the status of this entry, and is
        used to create(5)/delete(6) entries.  Any object in an entry of
        this table may be modified while the value of the
        corresponding instance of this object is active(1).
        createAndGo, notReady not supported."
    ::= { sm24tat4xbSNMPv3GroupConfEntry 5 }

sm24tat4xbSNMPv3ViewsConfTable OBJECT-TYPE
    SYNTAX      SEQUENCE OF SM24TAT4XBSNMPv3ViewsConfEntry
    MAX-ACCESS  not-accessible
    STATUS      current
    DESCRIPTION
        "A list of snmpv3 view configuration entry."
    ::= { sm24tat4xbSnmp 8 }

sm24tat4xbSNMPv3ViewsConfEntry OBJECT-TYPE
    SYNTAX      SM24TAT4XBSNMPv3ViewsConfEntry
    MAX-ACCESS  not-accessible
    STATUS      current
    DESCRIPTION
        "This is the entry information for snmpv3 view configuration."
    INDEX    { sm24tat4xbSNMPv3ViewsConfIndex  }
    ::= { sm24tat4xbSNMPv3ViewsConfTable 1 }

SM24TAT4XBSNMPv3ViewsConfEntry ::= SEQUENCE {
    sm24tat4xbSNMPv3ViewsConfIndex            Integer32,
    sm24tat4xbSNMPv3ViewsConfViewName        DisplayString,
    sm24tat4xbSNMPv3ViewsConfViewType        Integer32,
    sm24tat4xbSNMPv3ViewsConfOIDSubtree      DisplayString,
    sm24tat4xbSNMPv3ViewsConfRowStatus        RowStatus
}

sm24tat4xbSNMPv3ViewsConfIndex OBJECT-TYPE
    SYNTAX    Integer32(1..65535)
    MAX-ACCESS    read-write
    STATUS    current
    DESCRIPTION
        "view configuration index."
    ::= { sm24tat4xbSNMPv3ViewsConfEntry 1 }

sm24tat4xbSNMPv3ViewsConfViewName OBJECT-TYPE
    SYNTAX    DisplayString
    MAX-ACCESS    read-write
    STATUS    current
    DESCRIPTION
        "A string identifying the view name that this entry should belong to.
        The allowed string length is 1 to 32, and the allowed content is
        ASCII characters from 33 to 126. "
    ::= { sm24tat4xbSNMPv3ViewsConfEntry 2 }

sm24tat4xbSNMPv3ViewsConfViewType OBJECT-TYPE
    SYNTAX    Integer32
    MAX-ACCESS    read-write
    STATUS    current
    DESCRIPTION
        "0:included
        1:excluded"
    ::= { sm24tat4xbSNMPv3ViewsConfEntry 3 }

sm24tat4xbSNMPv3ViewsConfOIDSubtree OBJECT-TYPE
    SYNTAX    DisplayString
    MAX-ACCESS    read-write
    STATUS    current
    DESCRIPTION
        "The OID defining the root of the subtree to add to the named view.
        The allowed OID length is 1 to 128. The allowed string content is
        digital number or asterisk(*)"
    ::= { sm24tat4xbSNMPv3ViewsConfEntry 4 }

sm24tat4xbSNMPv3ViewsConfRowStatus OBJECT-TYPE
    SYNTAX    RowStatus
    MAX-ACCESS    read-create
    STATUS    current
    DESCRIPTION
        "This object indicates the status of this entry, and is
        used to create(5)/delete(6) entries.  Any object in an entry of
        this table may be modified while the value of the
        corresponding instance of this object is active(1).
        createAndGo, notReady not supported."
    ::= { sm24tat4xbSNMPv3ViewsConfEntry 5 }


sm24tat4xbSNMPv3AccessConfTable OBJECT-TYPE
    SYNTAX      SEQUENCE OF SM24TAT4XBSNMPv3AccessConfEntry
    MAX-ACCESS  not-accessible
    STATUS      current
    DESCRIPTION
        "A list of snmpv3 access configuration entry."
    ::= { sm24tat4xbSnmp 9 }

sm24tat4xbSNMPv3AccessConfEntry OBJECT-TYPE
    SYNTAX      SM24TAT4XBSNMPv3AccessConfEntry
    MAX-ACCESS  not-accessible
    STATUS      current
    DESCRIPTION
        "This is the entry information for snmpv3 access configuration."
    INDEX    { sm24tat4xbSNMPv3AccessConfIndex  }
    ::= { sm24tat4xbSNMPv3AccessConfTable 1 }

SM24TAT4XBSNMPv3AccessConfEntry ::= SEQUENCE {
    sm24tat4xbSNMPv3AccessConfIndex            Integer32,
    sm24tat4xbSNMPv3AccessConfGroupName        DisplayString,
    sm24tat4xbSNMPv3AccessConfSecurityModel        Integer32,
    sm24tat4xbSNMPv3AccessConfSecurityLevel        Integer32,
    sm24tat4xbSNMPv3AccessConfReadViewName     DisplayString,
    sm24tat4xbSNMPv3AccessConfWriteViewName    DisplayString,
    sm24tat4xbSNMPv3AccessConfRowStatus        RowStatus
}

sm24tat4xbSNMPv3AccessConfIndex OBJECT-TYPE
    SYNTAX    Integer32(1..65535)
    MAX-ACCESS    read-write
    STATUS    current
    DESCRIPTION
        "Access configuration index"
    ::= { sm24tat4xbSNMPv3AccessConfEntry 1 }

sm24tat4xbSNMPv3AccessConfGroupName OBJECT-TYPE
    SYNTAX    DisplayString
    MAX-ACCESS    read-write
    STATUS    current
    DESCRIPTION
        "Group name from Group configuration."
    ::= { sm24tat4xbSNMPv3AccessConfEntry 2 }

sm24tat4xbSNMPv3AccessConfSecurityModel OBJECT-TYPE
    SYNTAX    Integer32
    MAX-ACCESS    read-write
    STATUS    current
    DESCRIPTION
        "0:any
        1:v1
	    2:v2c
	    3:usm"
    ::= { sm24tat4xbSNMPv3AccessConfEntry 3 }

sm24tat4xbSNMPv3AccessConfSecurityLevel OBJECT-TYPE
    SYNTAX    Integer32
    MAX-ACCESS    read-write
    STATUS    current
    DESCRIPTION
        "1:NoAuth, NoPriv
        2:Auth, NoPriv
        3:Auth, Priv"
    ::= { sm24tat4xbSNMPv3AccessConfEntry 4 }

sm24tat4xbSNMPv3AccessConfReadViewName OBJECT-TYPE
    SYNTAX    DisplayString
    MAX-ACCESS    read-write
    STATUS    current
    DESCRIPTION
        "Read View Name from View configuration."
    ::= { sm24tat4xbSNMPv3AccessConfEntry 5 }

sm24tat4xbSNMPv3AccessConfWriteViewName OBJECT-TYPE
    SYNTAX    DisplayString
    MAX-ACCESS    read-write
    STATUS    current
    DESCRIPTION
        "Write View Name from View configuration."
    ::= { sm24tat4xbSNMPv3AccessConfEntry 6 }

sm24tat4xbSNMPv3AccessConfRowStatus OBJECT-TYPE
    SYNTAX    RowStatus
    MAX-ACCESS    read-create
    STATUS    current
    DESCRIPTION
        "This object indicates the status of this entry, and is
        used to create(5)/delete(6) entries.  Any object in an entry of
        this table may be modified while the value of the
        corresponding instance of this object is active(1).
        createAndGo, notReady not supported."
    ::= { sm24tat4xbSNMPv3AccessConfEntry 7 }

-- =======================================================================================================================
sm24tat4xbDHCPServer                     OBJECT IDENTIFIER ::= { sm24tat4xbSystem 9 }

sm24tat4xbDHCPServerConfig                  OBJECT IDENTIFIER ::= { sm24tat4xbDHCPServer 7 }

sm24tat4xbDHCPServerConfigTable OBJECT-TYPE
    SYNTAX      SEQUENCE OF SM24TAT4XBDHCPServerConfigEntry
    MAX-ACCESS  not-accessible
    STATUS      current
    DESCRIPTION
        " "
    ::= { sm24tat4xbDHCPServerConfig 1 }

sm24tat4xbDHCPServerConfigEntry OBJECT-TYPE
    SYNTAX    SM24TAT4XBDHCPServerConfigEntry
    MAX-ACCESS    not-accessible
    STATUS    current
    DESCRIPTION
        " "
    INDEX    { sm24tat4xbDHCPServerConfigIndex }
    ::= { sm24tat4xbDHCPServerConfigTable 1 }


SM24TAT4XBDHCPServerConfigEntry ::=
    SEQUENCE {
    sm24tat4xbDHCPServerConfigIndex            Integer32,
    sm24tat4xbDHCPServerConfigInterfaceVLAN        Integer32,
    sm24tat4xbDHCPServerConfigInterfaceMode        Integer32,
    sm24tat4xbDHCPServerConfigInterfaceStartIPEndIP    DisplayString,
--      sm24tat4xbDHCPServerConfigInterfaceEndIP        IpAddress,
    sm24tat4xbDHCPServerConfigInterfaceLeaseTime    Integer32,
    sm24tat4xbDHCPServerConfigInterfaceSubnetMask      IpAddress,
    sm24tat4xbDHCPServerConfigInterfaceDefaultRouter    IpAddress,
    sm24tat4xbDHCPServerConfigInterfaceDNSServer    IpAddress
    }

sm24tat4xbDHCPServerConfigIndex OBJECT-TYPE
    SYNTAX      Integer32 (1..4094)
    MAX-ACCESS  not-accessible
    STATUS      current
    DESCRIPTION
        "table index."
    ::= {sm24tat4xbDHCPServerConfigEntry 1 }

sm24tat4xbDHCPServerConfigInterfaceVLAN OBJECT-TYPE
    SYNTAX      Integer32 (1..4094)
    MAX-ACCESS  read-only
    STATUS      current
    DESCRIPTION
        "The VLAN in which DHCP server is enabled or disabled. "
    ::= {sm24tat4xbDHCPServerConfigEntry 2 }

sm24tat4xbDHCPServerConfigInterfaceMode OBJECT-TYPE
    SYNTAX      Integer32 (0|1)
    MAX-ACCESS  read-write
    STATUS      current
    DESCRIPTION
        "Indicate the operation mode per VLAN.
        0:disable
        1:enable"
    ::= {sm24tat4xbDHCPServerConfigEntry 3 }

sm24tat4xbDHCPServerConfigInterfaceStartIPEndIP OBJECT-TYPE
    SYNTAX      DisplayString
    MAX-ACCESS  read-write
    STATUS      current
    DESCRIPTION
        "Please set SubnetMask first.
        Start IP and End IP. Format: x.x.x.x-x.x.x.x"
    ::= {sm24tat4xbDHCPServerConfigEntry 4 }

--sm24tat4xbDHCPServerConfigInterfaceEndIP OBJECT-TYPE
--    SYNTAX      IpAddress
--    MAX-ACCESS  read-write
--    STATUS      current
--    DESCRIPTION
--    "End IP"
--    ::= {sm24tat4xbDHCPServerConfigEntry 5 }

sm24tat4xbDHCPServerConfigInterfaceLeaseTime OBJECT-TYPE
    SYNTAX      Integer32
    MAX-ACCESS  read-write
    STATUS      current
    DESCRIPTION
        "The lease time in second."
    ::= {sm24tat4xbDHCPServerConfigEntry 6 }

sm24tat4xbDHCPServerConfigInterfaceSubnetMask OBJECT-TYPE
    SYNTAX      IpAddress
    MAX-ACCESS  read-write
    STATUS      current
    DESCRIPTION
        "Configure subnet mask of the DHCP address. "
    ::= {sm24tat4xbDHCPServerConfigEntry 7 }

sm24tat4xbDHCPServerConfigInterfaceDefaultRouter OBJECT-TYPE
    SYNTAX      IpAddress
    MAX-ACCESS  read-write
    STATUS      current
    DESCRIPTION
        "Configure the destination IP network or host address of the default route."
    ::= {sm24tat4xbDHCPServerConfigEntry 8 }

sm24tat4xbDHCPServerConfigInterfaceDNSServer OBJECT-TYPE
    SYNTAX      IpAddress
    MAX-ACCESS  read-write
    STATUS      current
    DESCRIPTION
        "Configure the default DNS server. "
    ::= {sm24tat4xbDHCPServerConfigEntry 9 }

sm24tat4xbDHCPServerStatus                  OBJECT IDENTIFIER ::= { sm24tat4xbDHCPServer 8 }

sm24tat4xbDHCPServerStatusTable OBJECT-TYPE
    SYNTAX      SEQUENCE OF SM24TAT4XBDHCPServerStatusEntry
    MAX-ACCESS  not-accessible
    STATUS      current
    DESCRIPTION
        " "
    ::= { sm24tat4xbDHCPServerStatus 1 }

sm24tat4xbDHCPServerStatusEntry OBJECT-TYPE
    SYNTAX    SM24TAT4XBDHCPServerStatusEntry
    MAX-ACCESS    not-accessible
    STATUS    current
    DESCRIPTION
        " "
    INDEX    { sm24tat4xbDHCPServerStatusIndex }
    ::= { sm24tat4xbDHCPServerStatusTable 1 }


SM24TAT4XBDHCPServerStatusEntry ::=
    SEQUENCE {
    sm24tat4xbDHCPServerStatusIndex            Integer32,
    sm24tat4xbDHCPServerStatusInterfaceVLAN        Integer32,
    sm24tat4xbDHCPServerStatusInterfaceType        DisplayString,
    sm24tat4xbDHCPServerStatusInterfaceStartIP     IpAddress,
    sm24tat4xbDHCPServerStatusInterfaceEndIP        IpAddress,
    sm24tat4xbDHCPServerStatusInterfaceLeaseTime    Integer32,
    sm24tat4xbDHCPServerStatusInterfaceSubnetMask      IpAddress,
    sm24tat4xbDHCPServerStatusInterfaceDefaultRouter    IpAddress,
    sm24tat4xbDHCPServerStatusInterfaceDNSServer    IpAddress
    }

sm24tat4xbDHCPServerStatusIndex OBJECT-TYPE
    SYNTAX      Integer32 (1..4094)
    MAX-ACCESS  not-accessible
    STATUS      current
    DESCRIPTION
        "table index."
    ::= {sm24tat4xbDHCPServerStatusEntry 1 }

sm24tat4xbDHCPServerStatusInterfaceVLAN OBJECT-TYPE
    SYNTAX      Integer32 (1..4094)
    MAX-ACCESS  read-only
    STATUS      current
    DESCRIPTION
        "The VLAN in which DHCP server is enabled or disabled. "
    ::= {sm24tat4xbDHCPServerStatusEntry 2 }

sm24tat4xbDHCPServerStatusInterfaceType OBJECT-TYPE
    SYNTAX      DisplayString
    MAX-ACCESS  read-only
    STATUS      current
    DESCRIPTION
        " "
    ::= {sm24tat4xbDHCPServerStatusEntry 3 }

sm24tat4xbDHCPServerStatusInterfaceStartIP OBJECT-TYPE
    SYNTAX      IpAddress
    MAX-ACCESS  read-only
    STATUS      current
    DESCRIPTION
        "Start IP"
    ::= {sm24tat4xbDHCPServerStatusEntry 4 }

sm24tat4xbDHCPServerStatusInterfaceEndIP OBJECT-TYPE
    SYNTAX      IpAddress
    MAX-ACCESS  read-only
    STATUS      current
    DESCRIPTION
        "End IP"
    ::= {sm24tat4xbDHCPServerStatusEntry 5 }

sm24tat4xbDHCPServerStatusInterfaceLeaseTime OBJECT-TYPE
    SYNTAX      Integer32
    MAX-ACCESS  read-only
    STATUS      current
    DESCRIPTION
        "The lease time in second."
    ::= {sm24tat4xbDHCPServerStatusEntry 6 }

sm24tat4xbDHCPServerStatusInterfaceSubnetMask OBJECT-TYPE
    SYNTAX      IpAddress
    MAX-ACCESS  read-only
    STATUS      current
    DESCRIPTION
        "Configure subnet mask of the DHCP address. "
    ::= {sm24tat4xbDHCPServerStatusEntry 7 }

sm24tat4xbDHCPServerStatusInterfaceDefaultRouter OBJECT-TYPE
    SYNTAX      IpAddress
    MAX-ACCESS  read-only
    STATUS      current
    DESCRIPTION
        "Configure the destination IP network or host address of the default route."
    ::= {sm24tat4xbDHCPServerStatusEntry 8 }

sm24tat4xbDHCPServerStatusInterfaceDNSServer OBJECT-TYPE
    SYNTAX      IpAddress
    MAX-ACCESS  read-only
    STATUS      current
    DESCRIPTION
        "Configure the default DNS server. "
    ::= {sm24tat4xbDHCPServerStatusEntry 9 }

--sm24tat4xbDHCPServerConf                 OBJECT IDENTIFIER ::= { sm24tat4xbDHCPServer 1 }
--
--sm24tat4xbDHCPServerGlobalMode OBJECT-TYPE
--    SYNTAX      Integer32 (0|1)
--    MAX-ACCESS  read-write
--    STATUS      current
--    DESCRIPTION
--    "default: 0,
--    Global Mode :
--    0: Disable,
--    1: Enable.
--    "
--    ::= { sm24tat4xbDHCPServerConf 1 }
--
--sm24tat4xbDHCPServerVLANMode OBJECT-TYPE
--    SYNTAX      Integer32 (0|1)
--    MAX-ACCESS  read-write
--    STATUS      current
--    DESCRIPTION
--    "default: 0,
--    0: Disable,
--    1: Enable.
--    "
--    ::= { sm24tat4xbDHCPServerConf 2 }
--
--sm24tat4xbVLANModeTable OBJECT-TYPE
--    SYNTAX      SEQUENCE OF SM24TAT4XBVLANModeEntry
--    MAX-ACCESS  not-accessible
--    STATUS      current
--    DESCRIPTION
--    "A table of VLAN Mode for DHCP Server."
--    ::= { sm24tat4xbDHCPServerConf 2 }

--sm24tat4xbVLANModeEntry OBJECT-TYPE
--    SYNTAX    SM24TAT4XBVLANModeEntry
--    MAX-ACCESS    not-accessible
--    STATUS    current
--    DESCRIPTION
--    "An entry in the sm24tat4xbVLANModeTable."
--    INDEX    { sm24tat4xbVLANModeIndex }
--    ::= { sm24tat4xbVLANModeTable 1 }
--
--SM24TAT4XBVLANModeEntry ::=
--    SEQUENCE {
--    sm24tat4xbVLANModeIndex                Integer32,
--    sm24tat4xbVLANModeRangeLow             Integer32,
--    sm24tat4xbVLANModeRangeHigh            Integer32,
--    sm24tat4xbVLANModeEnable                Integer32,
--		sm24tat4xbVLANModeRowStatus            RowStatus
--    }
--
--sm24tat4xbVLANModeIndex OBJECT-TYPE
--    SYNTAX      Integer32 (1..2048)
--    MAX-ACCESS  not-accessible
--    STATUS      current
--    DESCRIPTION
--    "VLAN Mode table index, range: 1-2048."
--    ::= {sm24tat4xbVLANModeEntry 1 }
--
--sm24tat4xbVLANModeRangeLow OBJECT-TYPE
--    SYNTAX      Integer32 (1..4095)
--    MAX-ACCESS  read-create
--    STATUS      current
--    DESCRIPTION
--    "VLAN Mode low range: 1-4095."
--    ::= {sm24tat4xbVLANModeEntry 2 }
--
--sm24tat4xbVLANModeRangeHigh OBJECT-TYPE
--    SYNTAX      Integer32 (1..4095)
--    MAX-ACCESS  read-create
--    STATUS      current
--    DESCRIPTION
--    "VLAN Mode high range: 1-4095."
--    ::= {sm24tat4xbVLANModeEntry 3 }
--
--sm24tat4xbVLANModeEnable OBJECT-TYPE
--    SYNTAX      Integer32 (0..1)
--    MAX-ACCESS  read-create
--    STATUS      current
--    DESCRIPTION
--    "VLAN Mode Enable, Enable:1, Disable:0."
--    ::= {sm24tat4xbVLANModeEntry 4 }
--
--sm24tat4xbVLANModeRowStatus OBJECT-TYPE
--    SYNTAX      RowStatus
--    MAX-ACCESS  read-create
--    STATUS      current
--    DESCRIPTION
--      "This object indicates the status of this entry, and is
--    used to create/delete entries.  Any object in an entry of
--    this table may be modified while the value of the
--    corresponding instance of this object is active(1).
--    createAndGo, notReady not supported."
--    ::= {     sm24tat4xbVLANModeEntry 5 }
--


-- sm24tat4xbDHCPServerBindingType OBJECT-TYPE
--    SYNTAX      Integer32 (0|1|2|3)
--    MAX-ACCESS  read-only
--    STATUS      current
--    DESCRIPTION
--    "default: None,
--    Global Mode :
--    0: None,
--    1: Automatic,
--    2: Manual,
--    3: Expired.
--    "
--    ::= { sm24tat4xbDHCPServerConf 2 }

-- sm24tat4xbDHCPServerBindingState OBJECT-TYPE
--    SYNTAX      Integer32 (0|1|2|3)
--    MAX-ACCESS  read-only
--    STATUS      current
--    DESCRIPTION
--    "default: None,
--    Global Mode :
--    0: None,
--    1: Allocated,
--    2: Committed,
--    3: Expired.
--    "
--    ::= { sm24tat4xbDHCPServerConf 3 }

-- sm24tat4xbDHCPServerBindingIP OBJECT-TYPE
--    SYNTAX      DisplayString
--    MAX-ACCESS  read-only
--    STATUS      current
--    DESCRIPTION
--    "The DHCP Server Binding IP"
--    ::= { sm24tat4xbDHCPServerConf 4 }
--
--
--sm24tat4xbDHCPServerExcludedIP                 OBJECT IDENTIFIER ::= { sm24tat4xbDHCPServer 2 }
--
--sm24tat4xbExcludedIPTable OBJECT-TYPE
--    SYNTAX      SEQUENCE OF SM24TAT4XBExcludedIPEntry
--    MAX-ACCESS  not-accessible
--    STATUS      current
--    DESCRIPTION
--    "A table of Excluded IP for DHCP Server."
--    ::= { sm24tat4xbDHCPServerExcludedIP 1 }
--
--sm24tat4xbExcludedIPEntry OBJECT-TYPE
--    SYNTAX    SM24TAT4XBExcludedIPEntry
--    MAX-ACCESS    not-accessible
--    STATUS    current
--    DESCRIPTION
--    "An entry in the sm24tat4xbExcludedIPTable."
--    INDEX    { sm24tat4xbExcludedIPIndex }
--    ::= { sm24tat4xbExcludedIPTable 1 }
--
--SM24TAT4XBExcludedIPEntry ::=
--    SEQUENCE {
--    sm24tat4xbExcludedIPIndex                Integer32,
--    sm24tat4xbExcludedIPRangeLow             IpAddress,
--    sm24tat4xbExcludedIPRangeHigh            IpAddress,
--		sm24tat4xbExcludedIPRowStatus            RowStatus
--    }
--
--sm24tat4xbExcludedIPIndex OBJECT-TYPE
--    SYNTAX      Integer32 (1..16)
--    MAX-ACCESS  not-accessible
--    STATUS      current
--    DESCRIPTION
--    "Excluded IP table index, range: 1-16."
--    ::= {sm24tat4xbExcludedIPEntry 1 }
--
--sm24tat4xbExcludedIPRangeLow OBJECT-TYPE
--    SYNTAX      IpAddress
--    MAX-ACCESS  read-create
--    STATUS      current
--    DESCRIPTION
--    "ExcludedIP low range."
--    ::= {sm24tat4xbExcludedIPEntry 2 }
--
--sm24tat4xbExcludedIPRangeHigh OBJECT-TYPE
--    SYNTAX      IpAddress
--    MAX-ACCESS  read-create
--    STATUS      current
--    DESCRIPTION
--    "ExcludedIP high range."
--    ::= {sm24tat4xbExcludedIPEntry 3 }
--
--sm24tat4xbExcludedIPRowStatus OBJECT-TYPE
--    SYNTAX      RowStatus
--    MAX-ACCESS  read-create
--    STATUS      current
--    DESCRIPTION
--      "This object indicates the status of this entry, and is
--    used to create/delete entries.  Any object in an entry of
--    this table may be modified while the value of the
--    corresponding instance of this object is active(1).
--    createAndGo, notReady not supported."
--    ::= {sm24tat4xbExcludedIPEntry 4 }
--
--
--
--sm24tat4xbDHCPServerPoolConf                 OBJECT IDENTIFIER ::= { sm24tat4xbDHCPServer 3 }
--
--sm24tat4xbDHCPServerPoolTable OBJECT-TYPE
--    SYNTAX      SEQUENCE OF SM24TAT4XBDHCPServerPoolEntry
--    MAX-ACCESS  not-accessible
--    STATUS      current
--    DESCRIPTION
--    "This is the entry information for DHCP Pool."
--    ::= { sm24tat4xbDHCPServerPoolConf 1 }
--
--sm24tat4xbDHCPServerPoolEntry OBJECT-TYPE
--    SYNTAX      SM24TAT4XBDHCPServerPoolEntry
--    MAX-ACCESS  not-accessible
--    STATUS      current
--    DESCRIPTION
--        " "
--    INDEX    { sm24tat4xbDHCPServerConfIndex  }
--    ::= { sm24tat4xbDHCPServerPoolTable 1 }
--
--SM24TAT4XBDHCPServerPoolEntry ::= SEQUENCE {
--    sm24tat4xbDHCPServerConfIndex        Integer32,
--    sm24tat4xbDHCPServerPoolName        DisplayString,
--    sm24tat4xbDHCPServerPoolType        Integer32,
--    sm24tat4xbDHCPServerIP              IpAddress,
--    sm24tat4xbDHCPServerSubnetMask          IpAddress,
--    sm24tat4xbDHCPServerLeaseTimeDays        Integer32,
--    sm24tat4xbDHCPServerLeaseTimeHours      Integer32,
--    sm24tat4xbDHCPServerLeaseTimeMinutes    Integer32,
--    sm24tat4xbDHCPServerDomainName          DisplayString,
--    sm24tat4xbDHCPServerBroadcastAddress    IpAddress,
--    sm24tat4xbDHCPServerDefRouter1          IpAddress,
--    sm24tat4xbDHCPServerDefRouter2          IpAddress,
--    sm24tat4xbDHCPServerDefRouter3          IpAddress,
--    sm24tat4xbDHCPServerDefRouter4          IpAddress,
--    sm24tat4xbDHCPServerDNSServer1          IpAddress,
--    sm24tat4xbDHCPServerDNSServer2          IpAddress,
--    sm24tat4xbDHCPServerDNSServer3          IpAddress,
--    sm24tat4xbDHCPServerDNSServer4          IpAddress,
--    sm24tat4xbDHCPServerNTPServer1          IpAddress,
--    sm24tat4xbDHCPServerNTPServer2          IpAddress,
--    sm24tat4xbDHCPServerNTPServer3          IpAddress,
--    sm24tat4xbDHCPServerNTPServer4          IpAddress,
--    sm24tat4xbDHCPServerNetbiosType         Integer32,
--    sm24tat4xbDHCPServerNetbiosScope        DisplayString,
--    sm24tat4xbDHCPServerNetbiosNameServer1      IpAddress,
--    sm24tat4xbDHCPServerNetbiosNameServer2      IpAddress,
--    sm24tat4xbDHCPServerNetbiosNameServer3      IpAddress,
--    sm24tat4xbDHCPServerNetbiosNameServer4      IpAddress,
--    sm24tat4xbDHCPServerNisDomainName        DisplayString,
--    sm24tat4xbDHCPServerNisServer1          IpAddress,
--    sm24tat4xbDHCPServerNisServer2          IpAddress,
--    sm24tat4xbDHCPServerNisServer3          IpAddress,
--    sm24tat4xbDHCPServerNisServer4          IpAddress,
--    sm24tat4xbDHCPServerClientIDType        Integer32,
--    sm24tat4xbDHCPServerClientID        DisplayString,
--    sm24tat4xbDHCPServerHWAddr          DisplayString,
--    sm24tat4xbDHCPServerClientName          DisplayString,
--    sm24tat4xbDHCPServerVendorClassID1      DisplayString,
--    sm24tat4xbDHCPServerVendorSpecificInfo1     DisplayString,
--    sm24tat4xbDHCPServerVendorClassID2      DisplayString,
--    sm24tat4xbDHCPServerVendorSpecificInfo2     DisplayString,
--    sm24tat4xbDHCPServerVendorClassID3      DisplayString,
--    sm24tat4xbDHCPServerVendorSpecificInfo3     DisplayString,
--    sm24tat4xbDHCPServerVendorClassID4      DisplayString,
--    sm24tat4xbDHCPServerVendorSpecificInfo4     DisplayString,
--    sm24tat4xbDHCPServerVendorClassID5      DisplayString,
--    sm24tat4xbDHCPServerVendorSpecificInfo5     DisplayString,
--    sm24tat4xbDHCPServerVendorClassID6      DisplayString,
--    sm24tat4xbDHCPServerVendorSpecificInfo6     DisplayString,
--    sm24tat4xbDHCPServerVendorClassID7      DisplayString,
--    sm24tat4xbDHCPServerVendorSpecificInfo7     DisplayString,
--    sm24tat4xbDHCPServerVendorClassID8      DisplayString,
--    sm24tat4xbDHCPServerVendorSpecificInfo8     DisplayString,
--    sm24tat4xbDHCPServerRowStatus        RowStatus
--}
--
--sm24tat4xbDHCPServerConfIndex OBJECT-TYPE
--    SYNTAX      Integer32 (1..64)
--    MAX-ACCESS  not-accessible
--    STATUS      current
--    DESCRIPTION
--    " pool, range : 1 - 64. "
--    ::= { sm24tat4xbDHCPServerPoolEntry 1 }
--
--sm24tat4xbDHCPServerPoolName OBJECT-TYPE
--    SYNTAX      DisplayString(SIZE (1..32))
--    MAX-ACCESS  read-create
--    STATUS      current
--    DESCRIPTION
--    " DHCP pool name. "
--    ::= { sm24tat4xbDHCPServerPoolEntry 2 }
--
--sm24tat4xbDHCPServerPoolType OBJECT-TYPE
--    SYNTAX      Integer32(0|1|2)
--    MAX-ACCESS  read-create
--    STATUS      current
--    DESCRIPTION
--    " DHCP Server Pool Type.
--	    0:None
--	    1:Network
--	    2:Host, please set DHCP Server IP first."
--    ::= { sm24tat4xbDHCPServerPoolEntry 3 }
--
--sm24tat4xbDHCPServerIP OBJECT-TYPE
--    SYNTAX      IpAddress
--    MAX-ACCESS  read-create
--    STATUS      current
--    DESCRIPTION
--    " DHCP Server IP. "
--    ::= { sm24tat4xbDHCPServerPoolEntry 4 }
--
--sm24tat4xbDHCPServerSubnetMask OBJECT-TYPE
--    SYNTAX      IpAddress
--    MAX-ACCESS  read-create
--    STATUS      current
--    DESCRIPTION
--    " DHCP Server IPv4 Subnet Mask. "
--    ::= { sm24tat4xbDHCPServerPoolEntry 5}
--
--sm24tat4xbDHCPServerLeaseTimeDays OBJECT-TYPE
--    SYNTAX      Integer32(0..365)
--    MAX-ACCESS  read-create
--    STATUS      current
--    DESCRIPTION
--    " DHCP Server IPv4 Lease Time:Days. "
--    ::= { sm24tat4xbDHCPServerPoolEntry 6 }
--
--sm24tat4xbDHCPServerLeaseTimeHours OBJECT-TYPE
--    SYNTAX      Integer32(0..23)
--    MAX-ACCESS  read-create
--    STATUS      current
--    DESCRIPTION
--    " DHCP Server IPv4 Lease Time:Hours. "
--    ::= { sm24tat4xbDHCPServerPoolEntry 7 }
--
--sm24tat4xbDHCPServerLeaseTimeMinutes OBJECT-TYPE
--    SYNTAX      Integer32(0..59)
--    MAX-ACCESS  read-create
--    STATUS      current
--    DESCRIPTION
--    " DHCP Server IPv4 Lease Time:Minutes. "
--    ::= { sm24tat4xbDHCPServerPoolEntry 8 }
--
--sm24tat4xbDHCPServerDomainName OBJECT-TYPE
--    SYNTAX      DisplayString(SIZE (0..128))
--    MAX-ACCESS  read-create
--    STATUS      current
--    DESCRIPTION
--    " DHCP Server Domain Name. "
--    ::= { sm24tat4xbDHCPServerPoolEntry 9 }
--
--sm24tat4xbDHCPServerBroadcastAddress OBJECT-TYPE
--    SYNTAX      IpAddress
--    MAX-ACCESS  read-create
--    STATUS      current
--    DESCRIPTION
--    " DHCP Server IPv4 Broadcast Address. "
--    ::= { sm24tat4xbDHCPServerPoolEntry 10 }
--
--sm24tat4xbDHCPServerDefRouter1 OBJECT-TYPE
--    SYNTAX      IpAddress
--    MAX-ACCESS  read-create
--    STATUS      current
--    DESCRIPTION
--    " DHCP Server IPv4 Default Router 1. "
--    ::= { sm24tat4xbDHCPServerPoolEntry 11 }
--
--sm24tat4xbDHCPServerDefRouter2 OBJECT-TYPE
--    SYNTAX      IpAddress
--    MAX-ACCESS  read-create
--    STATUS      current
--    DESCRIPTION
--    " DHCP Server IPv4 Default Router 2. "
--    ::= { sm24tat4xbDHCPServerPoolEntry 12 }
--
--sm24tat4xbDHCPServerDefRouter3 OBJECT-TYPE
--    SYNTAX      IpAddress
--    MAX-ACCESS  read-create
--    STATUS      current
--    DESCRIPTION
--    " DHCP Server IPv4 Default Router 3. "
--    ::= { sm24tat4xbDHCPServerPoolEntry 13 }
--
--sm24tat4xbDHCPServerDefRouter4 OBJECT-TYPE
--    SYNTAX      IpAddress
--    MAX-ACCESS  read-create
--    STATUS      current
--    DESCRIPTION
--    " DHCP Server IPv4 Default Router 4. "
--    ::= { sm24tat4xbDHCPServerPoolEntry 14 }
--
--sm24tat4xbDHCPServerDNSServer1 OBJECT-TYPE
--    SYNTAX      IpAddress
--    MAX-ACCESS  read-create
--    STATUS      current
--    DESCRIPTION
--    " DHCP Server DNS Server 1. "
--    ::= { sm24tat4xbDHCPServerPoolEntry 15 }
--
--sm24tat4xbDHCPServerDNSServer2 OBJECT-TYPE
--    SYNTAX      IpAddress
--    MAX-ACCESS  read-create
--    STATUS      current
--    DESCRIPTION
--    " DHCP Server DNS Server 2. "
--    ::= { sm24tat4xbDHCPServerPoolEntry 16 }
--
--sm24tat4xbDHCPServerDNSServer3 OBJECT-TYPE
--    SYNTAX      IpAddress
--    MAX-ACCESS  read-create
--    STATUS      current
--    DESCRIPTION
--    " DHCP Server DNS Server 3. "
--    ::= { sm24tat4xbDHCPServerPoolEntry 17 }
--
--sm24tat4xbDHCPServerDNSServer4 OBJECT-TYPE
--    SYNTAX      IpAddress
--    MAX-ACCESS  read-create
--    STATUS      current
--    DESCRIPTION
--    " DHCP Server DNS Server 4. "
--    ::= { sm24tat4xbDHCPServerPoolEntry 18 }
--
--sm24tat4xbDHCPServerNTPServer1 OBJECT-TYPE
--    SYNTAX      IpAddress
--    MAX-ACCESS  read-create
--    STATUS      current
--    DESCRIPTION
--    " DHCP Server NTP Server 1. "
--    ::= { sm24tat4xbDHCPServerPoolEntry 19 }
--
--sm24tat4xbDHCPServerNTPServer2 OBJECT-TYPE
--    SYNTAX      IpAddress
--    MAX-ACCESS  read-create
--    STATUS      current
--    DESCRIPTION
--    " DHCP Server NTP Server 2. "
--    ::= { sm24tat4xbDHCPServerPoolEntry 20 }
--
--sm24tat4xbDHCPServerNTPServer3 OBJECT-TYPE
--    SYNTAX      IpAddress
--    MAX-ACCESS  read-create
--    STATUS      current
--    DESCRIPTION
--    " DHCP Server NTP Server 3. "
--    ::= { sm24tat4xbDHCPServerPoolEntry 21 }
--
--sm24tat4xbDHCPServerNTPServer4 OBJECT-TYPE
--    SYNTAX      IpAddress
--    MAX-ACCESS  read-create
--    STATUS      current
--    DESCRIPTION
--    " DHCP Server NTP Server 4. "
--    ::= { sm24tat4xbDHCPServerPoolEntry 22 }
--
--sm24tat4xbDHCPServerNetbiosType OBJECT-TYPE
--    SYNTAX      Integer32(1..4)
--    MAX-ACCESS  read-create
--    STATUS      current
--    DESCRIPTION
--    " DHCP Server Netbios Node Type.
--	    0:None
--	    1:B-node
--	    2:P-node
--	    3:M-node
--	    4:H-node"
--    ::= { sm24tat4xbDHCPServerPoolEntry 23 }
--
--sm24tat4xbDHCPServerNetbiosScope OBJECT-TYPE
--    SYNTAX      DisplayString(SIZE (0..128))
--    MAX-ACCESS  read-create
--    STATUS      current
--    DESCRIPTION
--    " DHCP Server Netbios Scope. "
--    ::= { sm24tat4xbDHCPServerPoolEntry 24 }
--
--sm24tat4xbDHCPServerNetbiosNameServer1 OBJECT-TYPE
--    SYNTAX      IpAddress
--    MAX-ACCESS  read-create
--    STATUS      current
--    DESCRIPTION
--    " DHCP Server Netbios Name Server 1. "
--    ::= { sm24tat4xbDHCPServerPoolEntry 25 }
--
--sm24tat4xbDHCPServerNetbiosNameServer2 OBJECT-TYPE
--    SYNTAX      IpAddress
--    MAX-ACCESS  read-create
--    STATUS      current
--    DESCRIPTION
--    " DHCP Server Netbios Name Server 2. "
--    ::= { sm24tat4xbDHCPServerPoolEntry 26 }
--
--sm24tat4xbDHCPServerNetbiosNameServer3 OBJECT-TYPE
--    SYNTAX      IpAddress
--    MAX-ACCESS  read-create
--    STATUS      current
--    DESCRIPTION
--    " DHCP Server Netbios Name Server 3. "
--    ::= { sm24tat4xbDHCPServerPoolEntry 27 }
--
--sm24tat4xbDHCPServerNetbiosNameServer4 OBJECT-TYPE
--    SYNTAX      IpAddress
--    MAX-ACCESS  read-create
--    STATUS      current
--    DESCRIPTION
--    " DHCP Server Netbios Name Server 4. "
--    ::= { sm24tat4xbDHCPServerPoolEntry 28 }
--
--sm24tat4xbDHCPServerNisDomainName OBJECT-TYPE
--    SYNTAX      DisplayString(SIZE (0..128))
--    MAX-ACCESS  read-create
--    STATUS      current
--    DESCRIPTION
--    " DHCP Server Nis Domain Name. "
--    ::= { sm24tat4xbDHCPServerPoolEntry 29 }
--
--sm24tat4xbDHCPServerNisServer1 OBJECT-TYPE
--    SYNTAX      IpAddress
--    MAX-ACCESS  read-create
--    STATUS      current
--    DESCRIPTION
--    " DHCP Server Nis Server 1. "
--    ::= { sm24tat4xbDHCPServerPoolEntry 30 }
--
--sm24tat4xbDHCPServerNisServer2 OBJECT-TYPE
--    SYNTAX      IpAddress
--    MAX-ACCESS  read-create
--    STATUS      current
--    DESCRIPTION
--    " DHCP Server Nis Server 2. "
--    ::= { sm24tat4xbDHCPServerPoolEntry 31 }
--
--sm24tat4xbDHCPServerNisServer3 OBJECT-TYPE
--    SYNTAX      IpAddress
--    MAX-ACCESS  read-create
--    STATUS      current
--    DESCRIPTION
--    " DHCP Server Nis Server 3. "
--    ::= { sm24tat4xbDHCPServerPoolEntry 32 }
--
--sm24tat4xbDHCPServerNisServer4 OBJECT-TYPE
--    SYNTAX      IpAddress
--    MAX-ACCESS  read-create
--    STATUS      current
--    DESCRIPTION
--    " DHCP Server Nis Server 4. "
--    ::= { sm24tat4xbDHCPServerPoolEntry 33 }
--
--sm24tat4xbDHCPServerClientIDType OBJECT-TYPE
--    SYNTAX      Integer32(0..2)
--    MAX-ACCESS  read-create
--    STATUS      current
--    DESCRIPTION
--    " DHCP Server Client ID Type.
--	    0:None
--	    1:FQDN
--	    2:MAC"
--    ::= { sm24tat4xbDHCPServerPoolEntry 34 }
--
--sm24tat4xbDHCPServerClientID OBJECT-TYPE
--    SYNTAX      DisplayString(SIZE (0..128))
--    MAX-ACCESS  read-create
--    STATUS      current
--    DESCRIPTION
--    " DHCP Server Pool Client ID. "
--    ::= { sm24tat4xbDHCPServerPoolEntry 35 }
--
--sm24tat4xbDHCPServerHWAddr OBJECT-TYPE
--    SYNTAX      DisplayString(SIZE (0..17))
--    MAX-ACCESS  read-create
--    STATUS      current
--    DESCRIPTION
--    " DHCP Server Pool Hardware Address. "
--    ::= { sm24tat4xbDHCPServerPoolEntry 36 }
--
--sm24tat4xbDHCPServerClientName OBJECT-TYPE
--    SYNTAX      DisplayString(SIZE (0..32))
--    MAX-ACCESS  read-create
--    STATUS      current
--    DESCRIPTION
--    " DHCP Server Pool Client Name. "
--    ::= { sm24tat4xbDHCPServerPoolEntry 37 }
--
--sm24tat4xbDHCPServerVendorClassID1 OBJECT-TYPE
--    SYNTAX      DisplayString(SIZE (0..64))
--    MAX-ACCESS  read-create
--    STATUS      current
--    DESCRIPTION
--    " DHCP Server Vendor Class ID 1. Please also set VendorSpecificInfo1."
--    ::= { sm24tat4xbDHCPServerPoolEntry 38 }
--
--sm24tat4xbDHCPServerVendorSpecificInfo1 OBJECT-TYPE
--    SYNTAX      DisplayString(SIZE (0..32))
--    MAX-ACCESS  read-create
--    STATUS      current
--    DESCRIPTION
--    " DHCP Server Vendor Specific Info 1. Please also set VendorClassID1."
--    ::= { sm24tat4xbDHCPServerPoolEntry 39 }
--
--sm24tat4xbDHCPServerVendorClassID2 OBJECT-TYPE
--    SYNTAX      DisplayString(SIZE (0..64))
--    MAX-ACCESS  read-create
--    STATUS      current
--    DESCRIPTION
--    " DHCP Server Vendor Class ID 2. Please also set VendorSpecificInfo2."
--    ::= { sm24tat4xbDHCPServerPoolEntry 40 }
--
--sm24tat4xbDHCPServerVendorSpecificInfo2 OBJECT-TYPE
--    SYNTAX      DisplayString(SIZE (0..32))
--    MAX-ACCESS  read-create
--    STATUS      current
--    DESCRIPTION
--    " DHCP Server Vendor Specific Info 2. Please also set VendorClassID2."
--    ::= { sm24tat4xbDHCPServerPoolEntry 41 }
--
--sm24tat4xbDHCPServerVendorClassID3 OBJECT-TYPE
--    SYNTAX      DisplayString(SIZE (0..64))
--    MAX-ACCESS  read-create
--    STATUS      current
--    DESCRIPTION
--    " DHCP Server Vendor Class ID 3. Please also set VendorSpecificInfo3."
--    ::= { sm24tat4xbDHCPServerPoolEntry 42 }
--
--sm24tat4xbDHCPServerVendorSpecificInfo3 OBJECT-TYPE
--    SYNTAX      DisplayString(SIZE (0..32))
--    MAX-ACCESS  read-create
--    STATUS      current
--    DESCRIPTION
--    " DHCP Server Vendor Specific Info 3. Please also set VendorClassID3."
--    ::= { sm24tat4xbDHCPServerPoolEntry 43 }
--
--sm24tat4xbDHCPServerVendorClassID4 OBJECT-TYPE
--    SYNTAX      DisplayString(SIZE (0..64))
--    MAX-ACCESS  read-create
--    STATUS      current
--    DESCRIPTION
--    " DHCP Server Vendor Class ID 4. Please also set VendorSpecificInfo4."
--    ::= { sm24tat4xbDHCPServerPoolEntry 44 }
--
--sm24tat4xbDHCPServerVendorSpecificInfo4 OBJECT-TYPE
--    SYNTAX      DisplayString(SIZE (0..32))
--    MAX-ACCESS  read-create
--    STATUS      current
--    DESCRIPTION
--    " DHCP Server Vendor Specific Info 4. Please also set VendorClassID4."
--    ::= { sm24tat4xbDHCPServerPoolEntry 45 }
--
--sm24tat4xbDHCPServerVendorClassID5 OBJECT-TYPE
--    SYNTAX      DisplayString(SIZE (0..64))
--    MAX-ACCESS  read-create
--    STATUS      current
--    DESCRIPTION
--    " DHCP Server Vendor Class ID 5. Please also set VendorSpecificInfo5."
--    ::= { sm24tat4xbDHCPServerPoolEntry 46 }
--
--sm24tat4xbDHCPServerVendorSpecificInfo5 OBJECT-TYPE
--    SYNTAX      DisplayString(SIZE (0..32))
--    MAX-ACCESS  read-create
--    STATUS      current
--    DESCRIPTION
--    " DHCP Server Vendor Specific Info 5. Please also set VendorClassID5."
--    ::= { sm24tat4xbDHCPServerPoolEntry 47 }
--
--sm24tat4xbDHCPServerVendorClassID6 OBJECT-TYPE
--    SYNTAX      DisplayString(SIZE (0..64))
--    MAX-ACCESS  read-create
--    STATUS      current
--    DESCRIPTION
--    " DHCP Server Vendor Class ID 6. Please also set VendorSpecificInfo6."
--    ::= { sm24tat4xbDHCPServerPoolEntry 48 }
--
--sm24tat4xbDHCPServerVendorSpecificInfo6 OBJECT-TYPE
--    SYNTAX      DisplayString(SIZE (0..32))
--    MAX-ACCESS  read-create
--    STATUS      current
--    DESCRIPTION
--    " DHCP Server Vendor Specific Info 6. Please also set VendorClassID6."
--    ::= { sm24tat4xbDHCPServerPoolEntry 49 }
--
--sm24tat4xbDHCPServerVendorClassID7 OBJECT-TYPE
--    SYNTAX      DisplayString(SIZE (0..64))
--    MAX-ACCESS  read-create
--    STATUS      current
--    DESCRIPTION
--    " DHCP Server Vendor Class ID 7. Please also set VendorSpecificInfo7."
--    ::= { sm24tat4xbDHCPServerPoolEntry 50 }
--
--sm24tat4xbDHCPServerVendorSpecificInfo7 OBJECT-TYPE
--    SYNTAX      DisplayString(SIZE (0..32))
--    MAX-ACCESS  read-create
--    STATUS      current
--    DESCRIPTION
--    " DHCP Server Vendor Specific Info 7. Please also set VendorClassID7."
--    ::= { sm24tat4xbDHCPServerPoolEntry 51 }
--
--sm24tat4xbDHCPServerVendorClassID8 OBJECT-TYPE
--    SYNTAX      DisplayString(SIZE (0..64))
--    MAX-ACCESS  read-create
--    STATUS      current
--    DESCRIPTION
--    " DHCP Server Vendor Class ID 8. Please also set VendorSpecificInfo8."
--    ::= { sm24tat4xbDHCPServerPoolEntry 52 }
--
--sm24tat4xbDHCPServerVendorSpecificInfo8 OBJECT-TYPE
--    SYNTAX      DisplayString(SIZE (0..32))
--    MAX-ACCESS  read-create
--    STATUS      current
--    DESCRIPTION
--    " DHCP Server Vendor Specific Info 8. Please also set VendorClassID8."
--    ::= { sm24tat4xbDHCPServerPoolEntry 53 }
--
--sm24tat4xbDHCPServerRowStatus OBJECT-TYPE
--    SYNTAX      RowStatus
--    MAX-ACCESS  read-create
--    STATUS      current
--    DESCRIPTION
--      "This object indicates the status of this entry, and is
--    used to create/delete entries.  Any object in an entry of
--    this table may be modified while the value of the
--    corresponding instance of this object is active(1).
--    createAndGo, notReady not supported."
--    ::= {sm24tat4xbDHCPServerPoolEntry 54 }
--
--sm24tat4xbDHCPServerStatistics             OBJECT IDENTIFIER ::= { sm24tat4xbDHCPServer 4 }
--
--sm24tat4xbDHCPServerStatisticsDatabaseCountersPool OBJECT-TYPE
--    SYNTAX      Integer32
--    MAX-ACCESS  read-only
--    STATUS      current
--    DESCRIPTION
--    "
--    "
--    ::= { sm24tat4xbDHCPServerStatistics 1 }
--
--sm24tat4xbDHCPServerStatisticsDatabaseCountersExcludedIPAddress OBJECT-TYPE
--    SYNTAX      Integer32
--    MAX-ACCESS  read-only
--    STATUS      current
--    DESCRIPTION
--    "
--    "
--    ::= { sm24tat4xbDHCPServerStatistics 2 }
--
--sm24tat4xbDHCPServerStatisticsDatabaseCountersDeclinedIPAddress OBJECT-TYPE
--    SYNTAX      Integer32
--    MAX-ACCESS  read-only
--    STATUS      current
--    DESCRIPTION
--    "
--    "
--    ::= { sm24tat4xbDHCPServerStatistics 3 }
--
--sm24tat4xbDHCPServerStatisticsBindingCountersAutomaticBinding OBJECT-TYPE
--    SYNTAX      Integer32
--    MAX-ACCESS  read-only
--    STATUS      current
--    DESCRIPTION
--    "
--    "
--    ::= { sm24tat4xbDHCPServerStatistics 4 }
--
--sm24tat4xbDHCPServerStatisticsBindingCountersManualBinding OBJECT-TYPE
--    SYNTAX      Integer32
--    MAX-ACCESS  read-only
--    STATUS      current
--    DESCRIPTION
--    "
--    "
--    ::= { sm24tat4xbDHCPServerStatistics 5 }
--
--sm24tat4xbDHCPServerStatisticsBindingCountersExpiredBinding OBJECT-TYPE
--    SYNTAX      Integer32
--    MAX-ACCESS  read-only
--    STATUS      current
--    DESCRIPTION
--    "
--    "
--    ::= { sm24tat4xbDHCPServerStatistics 6 }
--
--sm24tat4xbDHCPServerStatisticsDHCPMessageReceivedCountersDISCOVER OBJECT-TYPE
--    SYNTAX      Integer32
--    MAX-ACCESS  read-only
--    STATUS      current
--    DESCRIPTION
--    "
--    "
--    ::= { sm24tat4xbDHCPServerStatistics 7 }
--
--sm24tat4xbDHCPServerStatisticsDHCPMessageReceivedCountersREQUEST OBJECT-TYPE
--    SYNTAX      Integer32
--    MAX-ACCESS  read-only
--    STATUS      current
--    DESCRIPTION
--    "
--    "
--    ::= { sm24tat4xbDHCPServerStatistics 8 }
--
--sm24tat4xbDHCPServerStatisticsDHCPMessageReceivedCountersDECLINE OBJECT-TYPE
--    SYNTAX      Integer32
--    MAX-ACCESS  read-only
--    STATUS      current
--    DESCRIPTION
--    "
--    "
--    ::= { sm24tat4xbDHCPServerStatistics 9 }
--
--sm24tat4xbDHCPServerStatisticsDHCPMessageReceivedCountersRELEASE OBJECT-TYPE
--    SYNTAX      Integer32
--    MAX-ACCESS  read-only
--    STATUS      current
--    DESCRIPTION
--    "
--    "
--    ::= { sm24tat4xbDHCPServerStatistics 10 }
--
--sm24tat4xbDHCPServerStatisticsDHCPMessageReceivedCountersINFORM OBJECT-TYPE
--    SYNTAX      Integer32
--    MAX-ACCESS  read-only
--    STATUS      current
--    DESCRIPTION
--    "
--    "
--    ::= { sm24tat4xbDHCPServerStatistics 11 }
--
--sm24tat4xbDHCPServerStatisticsDHCPMessageSentCountersOFFER OBJECT-TYPE
--    SYNTAX      Integer32
--    MAX-ACCESS  read-only
--    STATUS      current
--    DESCRIPTION
--    "
--    "
--    ::= { sm24tat4xbDHCPServerStatistics 12 }
--
--sm24tat4xbDHCPServerStatisticsDHCPMessageSentCountersACK OBJECT-TYPE
--    SYNTAX      Integer32
--    MAX-ACCESS  read-only
--    STATUS      current
--    DESCRIPTION
--    "
--    "
--    ::= { sm24tat4xbDHCPServerStatistics 13 }
--
--sm24tat4xbDHCPServerStatisticsDHCPMessageSentCountersNAK OBJECT-TYPE
--    SYNTAX      Integer32
--    MAX-ACCESS  read-only
--    STATUS      current
--    DESCRIPTION
--    "
--    "
--    ::= { sm24tat4xbDHCPServerStatistics 14 }
--
--sm24tat4xbDHCPServerClear OBJECT-TYPE
--    SYNTAX      Integer32
--    MAX-ACCESS  read-write
--    STATUS      current
--    DESCRIPTION
--    "
--    "
--    ::= { sm24tat4xbDHCPServerStatistics 15 }
--
--sm24tat4xbDHCPServerBinding             OBJECT IDENTIFIER ::= { sm24tat4xbDHCPServer 5 }
--
--sm24tat4xbDHCPServerBindingTable OBJECT-TYPE
--    SYNTAX      SEQUENCE OF SM24TAT4XBDHCPServerBindingEntry
--    MAX-ACCESS  not-accessible
--    STATUS      current
--    DESCRIPTION
--        " "
--    ::= { sm24tat4xbDHCPServerBinding 1 }
--
--sm24tat4xbDHCPServerBindingEntry OBJECT-TYPE
--    SYNTAX      SM24TAT4XBDHCPServerBindingEntry
--    MAX-ACCESS  not-accessible
--    STATUS      current
--    DESCRIPTION
--        " "
--    INDEX    { sm24tat4xbDHCPServerBindingIndex  }
--    ::= { sm24tat4xbDHCPServerBindingTable 1 }
--
--SM24TAT4XBDHCPServerBindingEntry ::= SEQUENCE {
--    sm24tat4xbDHCPServerBindingIndex         Integer32,
--    sm24tat4xbDHCPServerBindingIP            DisplayString,
--    sm24tat4xbDHCPServerBindingType          DisplayString,
--    sm24tat4xbDHCPServerBindingState         DisplayString,
--    sm24tat4xbDHCPServerBindingPoolName          DisplayString,
--    sm24tat4xbDHCPServerBindingServerID          DisplayString,
--    sm24tat4xbDHCPServerBindingVLAN          Integer32,
--    sm24tat4xbDHCPServerBindingSubnetMask        DisplayString,
--    sm24tat4xbDHCPServerBindingClientIDType      DisplayString,
--    sm24tat4xbDHCPServerBindingClientIDValue     DisplayString,
--    sm24tat4xbDHCPServerBindingMACAddress        DisplayString,
--    sm24tat4xbDHCPServerBindingLeaseTime         DisplayString,
--    sm24tat4xbDHCPServerBindingWillExpiredIn     DisplayString,
--    sm24tat4xbDHCPServerBindingDelete        Integer32
--}
--
--sm24tat4xbDHCPServerBindingIndex OBJECT-TYPE
--    SYNTAX      Integer32
--    MAX-ACCESS  not-accessible
--    STATUS      current
--    DESCRIPTION
--    "Index"
--    ::= { sm24tat4xbDHCPServerBindingEntry 1 }
--
--sm24tat4xbDHCPServerBindingIP OBJECT-TYPE
--    SYNTAX      DisplayString
--    MAX-ACCESS  read-only
--    STATUS      current
--    DESCRIPTION
--        " "
--    ::= { sm24tat4xbDHCPServerBindingEntry 2 }
--
--sm24tat4xbDHCPServerBindingType OBJECT-TYPE
--    SYNTAX      DisplayString
--    MAX-ACCESS  read-only
--    STATUS      current
--    DESCRIPTION
--        " "
--    ::= { sm24tat4xbDHCPServerBindingEntry 3 }
--
--sm24tat4xbDHCPServerBindingState OBJECT-TYPE
--    SYNTAX      DisplayString
--    MAX-ACCESS  read-only
--    STATUS      current
--    DESCRIPTION
--        " "
--    ::= { sm24tat4xbDHCPServerBindingEntry 4 }
--
--sm24tat4xbDHCPServerBindingPoolName OBJECT-TYPE
--    SYNTAX      DisplayString
--    MAX-ACCESS  read-only
--    STATUS      current
--    DESCRIPTION
--        " "
--    ::= { sm24tat4xbDHCPServerBindingEntry 5 }
--
--sm24tat4xbDHCPServerBindingServerID OBJECT-TYPE
--    SYNTAX      DisplayString
--    MAX-ACCESS  read-only
--    STATUS      current
--    DESCRIPTION
--        " "
--    ::= { sm24tat4xbDHCPServerBindingEntry 6 }
--
--sm24tat4xbDHCPServerBindingVLAN OBJECT-TYPE
--    SYNTAX      Integer32
--    MAX-ACCESS  read-only
--    STATUS      current
--    DESCRIPTION
--        " "
--    ::= { sm24tat4xbDHCPServerBindingEntry 7 }
--
--sm24tat4xbDHCPServerBindingSubnetMask OBJECT-TYPE
--    SYNTAX      DisplayString
--    MAX-ACCESS  read-only
--    STATUS      current
--    DESCRIPTION
--        " "
--    ::= { sm24tat4xbDHCPServerBindingEntry 8 }
--
--sm24tat4xbDHCPServerBindingClientIDType OBJECT-TYPE
--    SYNTAX      DisplayString
--    MAX-ACCESS  read-only
--    STATUS      current
--    DESCRIPTION
--        " "
--    ::= { sm24tat4xbDHCPServerBindingEntry 9 }
--
--sm24tat4xbDHCPServerBindingClientIDValue OBJECT-TYPE
--    SYNTAX      DisplayString
--    MAX-ACCESS  read-only
--    STATUS      current
--    DESCRIPTION
--        " "
--    ::= { sm24tat4xbDHCPServerBindingEntry 10 }
--
--sm24tat4xbDHCPServerBindingMACAddress OBJECT-TYPE
--    SYNTAX      DisplayString
--    MAX-ACCESS  read-only
--    STATUS      current
--    DESCRIPTION
--        " "
--    ::= { sm24tat4xbDHCPServerBindingEntry 11 }
--
--sm24tat4xbDHCPServerBindingLeaseTime OBJECT-TYPE
--    SYNTAX      DisplayString
--    MAX-ACCESS  read-only
--    STATUS      current
--    DESCRIPTION
--        " "
--    ::= { sm24tat4xbDHCPServerBindingEntry 12 }
--
--sm24tat4xbDHCPServerBindingWillExpiredIn OBJECT-TYPE
--    SYNTAX      DisplayString
--    MAX-ACCESS  read-only
--    STATUS      current
--    DESCRIPTION
--        " "
--    ::= { sm24tat4xbDHCPServerBindingEntry 13 }
--
--sm24tat4xbDHCPServerBindingDelete OBJECT-TYPE
--    SYNTAX      Integer32
--    MAX-ACCESS  read-write
--    STATUS      current
--    DESCRIPTION
--        " "
--    ::= { sm24tat4xbDHCPServerBindingEntry 14 }
--
--sm24tat4xbDHCPServerBindingClearAutomatic    OBJECT-TYPE
--    SYNTAX      Integer32
--    MAX-ACCESS  read-write
--    STATUS      current
--    DESCRIPTION
--	    "1:clear"
--    ::= { sm24tat4xbDHCPServerBinding 2 }
--
--sm24tat4xbDHCPServerBindingClearManual    OBJECT-TYPE
--    SYNTAX      Integer32
--    MAX-ACCESS  read-write
--    STATUS      current
--    DESCRIPTION
--	    "1:clear"
--    ::= { sm24tat4xbDHCPServerBinding 3 }
--
--sm24tat4xbDHCPServerBindingClearExpired    OBJECT-TYPE
--    SYNTAX      Integer32
--    MAX-ACCESS  read-write
--    STATUS      current
--    DESCRIPTION
--	    "1:clear"
--    ::= { sm24tat4xbDHCPServerBinding 4 }
--
--sm24tat4xbDHCPServerDeclined             OBJECT IDENTIFIER ::= { sm24tat4xbDHCPServer 6 }
--
--sm24tat4xbDHCPServerDeclinedTable OBJECT-TYPE
--    SYNTAX      SEQUENCE OF SM24TAT4XBDHCPServerDeclinedEntry
--    MAX-ACCESS  not-accessible
--    STATUS      current
--    DESCRIPTION
--        " "
--    ::= { sm24tat4xbDHCPServerDeclined 1 }
--
--sm24tat4xbDHCPServerDeclinedEntry OBJECT-TYPE
--    SYNTAX      SM24TAT4XBDHCPServerDeclinedEntry
--    MAX-ACCESS  not-accessible
--    STATUS      current
--    DESCRIPTION
--        " "
--    INDEX    { sm24tat4xbDHCPServerDeclinedIndex  }
--    ::= { sm24tat4xbDHCPServerDeclinedTable 1 }
--
--SM24TAT4XBDHCPServerDeclinedEntry ::= SEQUENCE {
--    sm24tat4xbDHCPServerDeclinedIndex         Integer32,
--    sm24tat4xbDHCPServerDeclinedIP            DisplayString
--}
--
--sm24tat4xbDHCPServerDeclinedIndex OBJECT-TYPE
--    SYNTAX      Integer32
--    MAX-ACCESS  not-accessible
--    STATUS      current
--    DESCRIPTION
--    "Index"
--    ::= { sm24tat4xbDHCPServerDeclinedEntry 1 }
--
--sm24tat4xbDHCPServerDeclinedIP OBJECT-TYPE
--    SYNTAX      DisplayString
--    MAX-ACCESS  read-only
--    STATUS      current
--    DESCRIPTION
--        " "
--    ::= { sm24tat4xbDHCPServerDeclinedEntry 2 }

-- =======================================================================================================================
sm24tat4xbVLANConf                     OBJECT IDENTIFIER ::= { sm24tat4xbSystem 10 }

sm24tat4xbVLAN                     OBJECT IDENTIFIER ::= { sm24tat4xbVLANConf 2}

sm24tat4xbVlanStatus          OBJECT IDENTIFIER    ::= { sm24tat4xbVLAN 6 }

--
-- =======================================================================================================================
-- Start sm24tat4xbVlan group
-- =======================================================================================================================
    sm24tat4xbVlanExistingVLANs  OBJECT-TYPE
        SYNTAX      DisplayString
        MAX-ACCESS  read-write
        STATUS      current
        DESCRIPTION
            "This field shows the VLANs that are created on the switch.
            More VLANs may be created by using a
            list syntax where the individual elements are separated by commas.
            Ranges are specified with a
            dash separating the lower and upper bound.
            The following example will create VLANs 1, 10, 11, 12
            , 13, 200, and 300: 1,10-13,200,300.
            default: 1."
        ::= {     sm24tat4xbVLAN 1 }

    sm24tat4xbVlanEthertypeforCustomSPorts  OBJECT-TYPE
        SYNTAX      DisplayString
        MAX-ACCESS  read-write
        STATUS      current
        DESCRIPTION
            "This field specifies the ethertype/TPID (specified in hexadecimal)
            used for Custom S-ports. The
            setting is in force for all ports whose Port Type
            is set to S-Custom-Port.
            range: 0600-ffff,
            default: 88a8."
        ::= {     sm24tat4xbVLAN 2 }

    sm24tat4xbVlanTable OBJECT-TYPE
        SYNTAX      SEQUENCE OF     SM24TAT4XBVlanEntry
        MAX-ACCESS  not-accessible
        STATUS      current
        DESCRIPTION
            "Configure Vlan ports Configuration mode.
            INDEX for this table is ifIndex which is
            equivalent to the panel port number."
        ::= {     sm24tat4xbVLAN 3 }

    sm24tat4xbVlanEntry OBJECT-TYPE
        SYNTAX      SM24TAT4XBVlanEntry
        MAX-ACCESS  not-accessible
        STATUS      current
        DESCRIPTION
            "The Vlan entry."
        INDEX    {     ifIndex  }
        ::= {     sm24tat4xbVlanTable 1 }

    SM24TAT4XBVlanEntry         ::= SEQUENCE {
        sm24tat4xbVlanMode          INTEGER,
        sm24tat4xbVlanPortVLAN      Integer32,
        sm24tat4xbVlanPortType      INTEGER,
        sm24tat4xbVlanIngressFiltering  AdminMode,
--          sm24tat4xbVlanVLANTrunking      AdminMode,
        sm24tat4xbVlanIngressAcceptance INTEGER,
        sm24tat4xbVlanEgressTagging     INTEGER,
        sm24tat4xbVlanAllowedVLANs      DisplayString,
        sm24tat4xbVlanForbiddenVLANs    DisplayString
        }

    sm24tat4xbVlanMode OBJECT-TYPE
        SYNTAX      INTEGER{access(0), trunk(1), hybrid(2)}
        MAX-ACCESS  read-write
        STATUS      current
        DESCRIPTION
            "The port mode determines the fundamental
            behavior of the port in question.
            A port can be in one of three modes as described below.
            0: access,
            1: trunk,
            2: hybrid."
        DEFVAL  { access }
        ::= {     sm24tat4xbVlanEntry 2 }

    sm24tat4xbVlanPortVLAN OBJECT-TYPE
        SYNTAX      Integer32(1..4094)
        MAX-ACCESS  read-write
        STATUS      current
        DESCRIPTION
            "Determines the port's VLAN ID (a.k.a. PVID).
            range: 1-4095,
            default: 1."
        ::= {     sm24tat4xbVlanEntry 3 }

    sm24tat4xbVlanPortType OBJECT-TYPE
        SYNTAX      INTEGER { unaware(0), cPort(1), sPort(2), sCustomPort(3) }
        MAX-ACCESS  read-write
        STATUS      current
        DESCRIPTION
            "Ports in hybrid mode allow for changing the port type,
            that is, whether a frame's VLAN tag is
            used to classify the frame on ingress to a particular VLAN,
            and if so, which TPID it reacts on.
            Likewise, on egress, the Port Type determines the
            TPID of the tag, if a tag is required.
            0: unaware,
            1: c-Port,
            2: s-Port,
            3: s-Custom-Port."
        DEFVAL  { cPort }
        ::= {     sm24tat4xbVlanEntry 4 }

    sm24tat4xbVlanIngressFiltering OBJECT-TYPE
        SYNTAX      AdminMode
        MAX-ACCESS  read-write
        STATUS      current
        DESCRIPTION
            "Hybrid ports allow for changing ingress filtering.
            Access and Trunk ports always have ingress
            filtering enabled.If ingress filtering is enabled,
            frames classified to
            a VLAN that the port is not a member of get discarded."
        ::= {     sm24tat4xbVlanEntry 5 }

--    sm24tat4xbVlanVLANTrunking OBJECT-TYPE
--        SYNTAX      AdminMode
--        MAX-ACCESS  read-write
--        STATUS      current
--        DESCRIPTION
--            "Trunk and Hybrid ports allow for enabling VLAN trunking.
--            When VLAN trunking is enabled, frames
--            classified to unknown VLANs are accepted on the port
--            whether ingress filtering is enabled or not."
--        DEFVAL  { disable }
--        ::= {     sm24tat4xbVlanEntry 6 }

    sm24tat4xbVlanIngressAcceptance OBJECT-TYPE
        SYNTAX      INTEGER  { taggedAndUntagged  ( 0 ),
                      taggedOnly ( 1 ),
                      untaggedOnly ( 2 )
                    }
        MAX-ACCESS  read-write
        STATUS      current
        DESCRIPTION
            "Hybrid ports allow for changing the type of frames that are
            accepted on ingress.
            0: Tagged and Untagged,
            1: Tagged Only,
            2: Untagged Only."
        ::= {     sm24tat4xbVlanEntry 7 }

    sm24tat4xbVlanEgressTagging OBJECT-TYPE
        SYNTAX      INTEGER  { untagPortVlan  ( 0 ),
                      tagAll ( 1 ),
                      untagAll ( 2 )
                    }
        MAX-ACCESS  read-write
        STATUS      current
        DESCRIPTION
            "Ports in Trunk and Hybrid mode may control the
            tagging of frames on egress.
            0: Untag Port VLAN,
            1: Tag All,
            2: Untag All."
        ::= {     sm24tat4xbVlanEntry 8 }

    sm24tat4xbVlanAllowedVLANs OBJECT-TYPE
        SYNTAX      DisplayString
        MAX-ACCESS  read-write
        STATUS      current
        DESCRIPTION
            "Ports in Trunk and Hybrid mode may control which
            VLANs they are allowed to become members of.
            Access ports can only be member of one VLAN, the Access VLAN.
            range: 1~4095.
            '-': Allowed VLANs is empty."
        ::= {     sm24tat4xbVlanEntry 9 }

    sm24tat4xbVlanForbiddenVLANs OBJECT-TYPE
        SYNTAX      DisplayString
        MAX-ACCESS  read-write
        STATUS      current
        DESCRIPTION
            "A port may be configured to never be member of one or
            more VLANs. This is particularly useful
            when dynamic VLAN protocols like MVRP and GVRP
            must be prevented from dynamically adding ports
            to VLANs.
            range: 1~4095.
            '-': Forbidden VLANs is empty."
        ::= {     sm24tat4xbVlanEntry 10 }

--sm24tat4xbVLANMembershipStatusTable

    sm24tat4xbVLANMembershipStatusTable OBJECT-TYPE
        SYNTAX      SEQUENCE OF     SM24TAT4XBVLANMembershipStatusEntry
        MAX-ACCESS  not-accessible
        STATUS      current
        DESCRIPTION
            "Vlan membership Status table.
            INDEX for this table is ifIndex which is
            equivalent to the panel port number."
        ::= {     sm24tat4xbVlanStatus 1 }

    sm24tat4xbVLANMembershipStatusEntry OBJECT-TYPE
        SYNTAX      SM24TAT4XBVLANMembershipStatusEntry
        MAX-ACCESS  not-accessible
        STATUS      current
        DESCRIPTION
            "Vlan membership Status entry."
        INDEX    {     ifIndex, sm24tat4xbVLANMembershipVlanID    }
        ::= {     sm24tat4xbVLANMembershipStatusTable 1 }

    SM24TAT4XBVLANMembershipStatusEntry         ::= SEQUENCE {
        sm24tat4xbVLANMembershipVlanID      Integer32,
        sm24tat4xbVLANMembershipStatus      INTEGER
        }

    sm24tat4xbVLANMembershipVlanID OBJECT-TYPE
        SYNTAX      Integer32(1..4095)
        MAX-ACCESS  not-accessible
        STATUS      current
        DESCRIPTION
            "VLAN ID for which the Port members are displayed."
        ::= {     sm24tat4xbVLANMembershipStatusEntry 2 }

    sm24tat4xbVLANMembershipStatus OBJECT-TYPE
        SYNTAX      INTEGER  { portIsNotInVlan  ( 0 ),
                      portIncludedInVlan ( 1 ),
                      portInForbiddenPortList( 2 ),
                      portInForbiddenPortListAndVlan( 3 )
                    }
        MAX-ACCESS  read-only
        STATUS      current
        DESCRIPTION
            "portIsNotInVlan(0): A port is nothing in a VLAN.
            portIncludedInVlan(1): A port is included in a VLAN.
            portInForbiddenPortList(2): A port is in the forbidden port list.
            portInForbiddenPortListAndVlan(3):
            A port is in the forbidden port list and at the same
            time attempted included in the VLAN."
        ::= {     sm24tat4xbVLANMembershipStatusEntry 3 }

--sm24tat4xbVLANPortStatusTable
    sm24tat4xbVLANPortStatusTable OBJECT-TYPE
        SYNTAX      SEQUENCE OF     SM24TAT4XBVLANPortStatusEntry
        MAX-ACCESS  not-accessible
        STATUS      current
        DESCRIPTION
            "The vlan port status table.
            INDEX for this table is ifIndex which is
            equivalent to the panel port number."
        ::= {     sm24tat4xbVlanStatus 2 }

    sm24tat4xbVLANPortStatusEntry OBJECT-TYPE
        SYNTAX      SM24TAT4XBVLANPortStatusEntry
        MAX-ACCESS  not-accessible
        STATUS      current
        DESCRIPTION
            "The vlan port status entry."
        INDEX    {     ifIndex }
        ::= {     sm24tat4xbVLANPortStatusTable 1 }

    SM24TAT4XBVLANPortStatusEntry         ::= SEQUENCE {
        sm24tat4xbVLANPortStatusPortType      DisplayString,
        sm24tat4xbVLANPortStatusIngressFiltering  AdminMode,
        sm24tat4xbVLANPortStatusFrameType     DisplayString,
        sm24tat4xbVLANPortStatusPortVLANID    Integer32,
        sm24tat4xbVLANPortStatusTxTag         DisplayString,
        sm24tat4xbVLANPortStatusUntaggedVLANID    Integer32,
        sm24tat4xbVLANPortStatusConflicts     DisplayString
        }

    sm24tat4xbVLANPortStatusPortType OBJECT-TYPE
        SYNTAX      DisplayString
        MAX-ACCESS  read-only
        STATUS      current
        DESCRIPTION
            "Shows the port type (Unaware, C-Port, S-Port,
            S-Custom-Port.) that a given user wants to configure on
            the port.The field is empty if not overridden by the selected user."
        ::= {     sm24tat4xbVLANPortStatusEntry 2 }

    sm24tat4xbVLANPortStatusIngressFiltering OBJECT-TYPE
        SYNTAX      AdminMode
        MAX-ACCESS  read-only
        STATUS      current
        DESCRIPTION
            "Shows whether a given user wants ingress filtering enabled or not."
        ::= {     sm24tat4xbVLANPortStatusEntry 3 }

    sm24tat4xbVLANPortStatusFrameType OBJECT-TYPE
        SYNTAX      DisplayString
        MAX-ACCESS  read-only
        STATUS      current
        DESCRIPTION
            "Shows the acceptable frame types (All, Taged,
            Untagged) that a given user wants to configure on the port.
            The field is empty if not overridden by the selected user."
        ::= {     sm24tat4xbVLANPortStatusEntry 4 }

    sm24tat4xbVLANPortStatusPortVLANID OBJECT-TYPE
        SYNTAX      Integer32 (1..4095)
        MAX-ACCESS  read-only
        STATUS      current
        DESCRIPTION
            "Shows the Port VLAN ID (PVID) that a given user
            wants the port to have.
            The field is 0 if not overridden by the selected user."
        ::= {     sm24tat4xbVLANPortStatusEntry 5 }

    sm24tat4xbVLANPortStatusTxTag OBJECT-TYPE
        SYNTAX      DisplayString
        MAX-ACCESS  read-only
        STATUS      current
        DESCRIPTION
            "Shows the Tx Tag requirements (Tag All, Tag PVID,
            Tag UVID, Untag All, Untag PVID, Untag UVID)
            that a given user has on a port.The field is empty
            if not overridden by the selected user."
        ::= {     sm24tat4xbVLANPortStatusEntry 6 }

    sm24tat4xbVLANPortStatusUntaggedVLANID OBJECT-TYPE
        SYNTAX      Integer32(1..4095)
        MAX-ACCESS  read-only
        STATUS      current
        DESCRIPTION
            "If Tx Tag is overridden by the selected user and is
            set to Tag or Untag UVID, then this field will show
            the VLAN ID the user wants to tag or untag on egress.
            The field is 0 if not overridden by the selected
            user."
        ::= {     sm24tat4xbVLANPortStatusEntry 7 }

    sm24tat4xbVLANPortStatusConflicts OBJECT-TYPE
        SYNTAX      DisplayString
        MAX-ACCESS  read-only
        STATUS      current
        DESCRIPTION
            "Two users may have conflicting requirements to a port's
            configuration. For instance, one user may require
            all frames to be tagged on egress while another requires
            all frames to be untagged on egress.Since both
            users cannot win, this gives rise to a conflict,
            which is solved in a prioritized way. The Administrator
            has the least priority. Other software modules are
            prioritized according to their position in the drop-down
            list: The higher in the list, the higher priority.
            If conflicts exist, it will be displayed as 'Yes'."
        ::= {     sm24tat4xbVLANPortStatusEntry 8 }

sm24tat4xbMacBaesdVlanMembershipConfig     OBJECT IDENTIFIER    ::= { sm24tat4xbVLAN 7 }

sm24tat4xbMacBaesdVlanMembershipConfigTable  OBJECT-TYPE
    SYNTAX      SEQUENCE OF SM24TAT4XBMacBaesdVlanMembershipConfigEntry
    MAX-ACCESS  not-accessible
    STATUS      current
    DESCRIPTION
        "Mac-Based VLAN Membership table"
 ::= { sm24tat4xbMacBaesdVlanMembershipConfig 1 }

sm24tat4xbMacBaesdVlanMembershipConfigEntry OBJECT-TYPE
    SYNTAX    SM24TAT4XBMacBaesdVlanMembershipConfigEntry
    MAX-ACCESS    not-accessible
    STATUS    current
    DESCRIPTION
        "Mac-Based VLAN Membership table."
    INDEX    { sm24tat4xbMacBaesdVlanMembershipConfigIndex }
    ::= { sm24tat4xbMacBaesdVlanMembershipConfigTable 1 }

SM24TAT4XBMacBaesdVlanMembershipConfigEntry ::=
    SEQUENCE {
    sm24tat4xbMacBaesdVlanMembershipConfigIndex    Integer32,
    sm24tat4xbMacBaesdVlanMembershipConfigMACAddress    DisplayString,
    sm24tat4xbMacBaesdVlanMembershipConfigVLANID    Integer32,
    sm24tat4xbMacBaesdVlanMembershipConfigPortMembers  DisplayString,
    sm24tat4xbMacBaesdVlanMembershipConfigRowStatus    RowStatus
    }

sm24tat4xbMacBaesdVlanMembershipConfigIndex OBJECT-TYPE
    SYNTAX      Integer32(1..65535)
    MAX-ACCESS  not-accessible
    STATUS      current
    DESCRIPTION
        "Mac-Based VLAN membership index."
    ::= {sm24tat4xbMacBaesdVlanMembershipConfigEntry 1 }

sm24tat4xbMacBaesdVlanMembershipConfigMACAddress OBJECT-TYPE
    SYNTAX      DisplayString
    MAX-ACCESS  read-create
    STATUS      current
    DESCRIPTION
        "MAC address: xx-xx-xx-xx-xx-xx."
    ::= {sm24tat4xbMacBaesdVlanMembershipConfigEntry 2 }

sm24tat4xbMacBaesdVlanMembershipConfigVLANID OBJECT-TYPE
    SYNTAX      Integer32
    MAX-ACCESS  read-create
    STATUS      current
    DESCRIPTION
        "VLAN ID"
    ::= {sm24tat4xbMacBaesdVlanMembershipConfigEntry 3 }

sm24tat4xbMacBaesdVlanMembershipConfigPortMembers OBJECT-TYPE
    SYNTAX      DisplayString
    MAX-ACCESS  read-create
    STATUS      current
    DESCRIPTION
        "0:remove or exclude the port from the mapping
        1:include a port in the mapping"
    ::= {sm24tat4xbMacBaesdVlanMembershipConfigEntry 4 }

sm24tat4xbMacBaesdVlanMembershipConfigRowStatus OBJECT-TYPE
    SYNTAX      RowStatus
    MAX-ACCESS  read-create
    STATUS      current
    DESCRIPTION
        "Row Status."
    ::= {sm24tat4xbMacBaesdVlanMembershipConfigEntry 5 }

sm24tat4xbMacBaesdVlanMembershipStatusUser    OBJECT-TYPE
    SYNTAX      Integer32
    MAX-ACCESS  read-write
    STATUS      current
    DESCRIPTION
        "MAC-based VLAN Membership Status User"
    ::= { sm24tat4xbVLAN 8 }

sm24tat4xbMacBaesdVlanMembershipStatus     OBJECT IDENTIFIER    ::= { sm24tat4xbVLAN 9 }

sm24tat4xbMacBaesdVlanMembershipStatusTable  OBJECT-TYPE
    SYNTAX      SEQUENCE OF SM24TAT4XBMacBaesdVlanMembershipStatusEntry
    MAX-ACCESS  not-accessible
    STATUS      current
    DESCRIPTION
        "Mac-Based VLAN Membership table"
    ::= { sm24tat4xbMacBaesdVlanMembershipStatus 1 }

sm24tat4xbMacBaesdVlanMembershipStatusEntry OBJECT-TYPE
    SYNTAX    SM24TAT4XBMacBaesdVlanMembershipStatusEntry
    MAX-ACCESS    not-accessible
    STATUS    current
    DESCRIPTION
        "Mac-Based VLAN Membership table."
    INDEX    { sm24tat4xbMacBaesdVlanMembershipStatusIndex }
    ::= { sm24tat4xbMacBaesdVlanMembershipStatusTable 1 }

SM24TAT4XBMacBaesdVlanMembershipStatusEntry ::=
    SEQUENCE {
    sm24tat4xbMacBaesdVlanMembershipStatusIndex    Integer32,
    sm24tat4xbMacBaesdVlanMembershipStatusMACAddress    DisplayString,
    sm24tat4xbMacBaesdVlanMembershipStatusVLANID    Integer32,
    sm24tat4xbMacBaesdVlanMembershipStatusPortMembers  DisplayString
    }

sm24tat4xbMacBaesdVlanMembershipStatusIndex OBJECT-TYPE
    SYNTAX      Integer32(1..65535)
    MAX-ACCESS  not-accessible
    STATUS      current
    DESCRIPTION
        "Mac-Based VLAN membership index."
    ::= {sm24tat4xbMacBaesdVlanMembershipStatusEntry 1 }

sm24tat4xbMacBaesdVlanMembershipStatusMACAddress OBJECT-TYPE
    SYNTAX      DisplayString
    MAX-ACCESS  read-only
    STATUS      current
    DESCRIPTION
        "MAC address: xx-xx-xx-xx-xx-xx."
    ::= {sm24tat4xbMacBaesdVlanMembershipStatusEntry 2 }

sm24tat4xbMacBaesdVlanMembershipStatusVLANID OBJECT-TYPE
    SYNTAX      Integer32
    MAX-ACCESS  read-only
    STATUS      current
    DESCRIPTION
        "VLAN ID"
    ::= {sm24tat4xbMacBaesdVlanMembershipStatusEntry 3 }

sm24tat4xbMacBaesdVlanMembershipStatusPortMembers OBJECT-TYPE
    SYNTAX      DisplayString
    MAX-ACCESS  read-only
    STATUS      current
    DESCRIPTION
        "0:remove or exclude the port from the mapping
        1:include a port in the mapping"
    ::= {sm24tat4xbMacBaesdVlanMembershipStatusEntry 4 }

sm24tat4xbProtocolbasedVLANConfig     OBJECT IDENTIFIER    ::= { sm24tat4xbVLAN 10 }

sm24tat4xbProtocolbasedVLANConfigTable  OBJECT-TYPE
    SYNTAX      SEQUENCE OF SM24TAT4XBProtocolbasedVLANConfigEntry
    MAX-ACCESS  not-accessible
    STATUS      current
    DESCRIPTION
        "Protocol-based VLAN Config table"
    ::= { sm24tat4xbProtocolbasedVLANConfig 1 }

sm24tat4xbProtocolbasedVLANConfigEntry OBJECT-TYPE
    SYNTAX    SM24TAT4XBProtocolbasedVLANConfigEntry
    MAX-ACCESS    not-accessible
    STATUS    current
    DESCRIPTION
        "Protocol-based VLAN Config table"
    INDEX    { sm24tat4xbProtocolbasedVLANConfigIndex }
    ::= { sm24tat4xbProtocolbasedVLANConfigTable 1 }

SM24TAT4XBProtocolbasedVLANConfigEntry ::=
    SEQUENCE {
    sm24tat4xbProtocolbasedVLANConfigIndex        Integer32,
    sm24tat4xbProtocolbasedVLANConfigFrameType        Integer32,
    sm24tat4xbProtocolbasedVLANConfigValueEthernetEtype  DisplayString,
    sm24tat4xbProtocolbasedVLANConfigValueSNAPOUI    DisplayString,
    sm24tat4xbProtocolbasedVLANConfigValueSNAPPID    DisplayString,
    sm24tat4xbProtocolbasedVLANConfigValueLLCDSAP    DisplayString,
    sm24tat4xbProtocolbasedVLANConfigValueLLCSSAP    DisplayString,
    sm24tat4xbProtocolbasedVLANConfigGroupName        DisplayString,
    sm24tat4xbProtocolbasedVLANConfigRowStatus        RowStatus
    }

sm24tat4xbProtocolbasedVLANConfigIndex OBJECT-TYPE
    SYNTAX      Integer32(1..65535)
    MAX-ACCESS  not-accessible
    STATUS      current
    DESCRIPTION
        "Protocol-based VLAN Config index."
    ::= {sm24tat4xbProtocolbasedVLANConfigEntry 1 }

sm24tat4xbProtocolbasedVLANConfigFrameType OBJECT-TYPE
    SYNTAX      Integer32
    MAX-ACCESS  read-create
    STATUS      current
    DESCRIPTION
        "Frame Type.
        1:Ethernet
        2:LLC
        3:SNAP"
    ::= {sm24tat4xbProtocolbasedVLANConfigEntry 2 }


sm24tat4xbProtocolbasedVLANConfigValueEthernetEtype OBJECT-TYPE
    SYNTAX      DisplayString
    MAX-ACCESS  read-create
    STATUS      current
    DESCRIPTION
        "Ethernet Etype.
        Valid values for etype range between 0x0600 and 0xffff "
    ::= {sm24tat4xbProtocolbasedVLANConfigEntry 3 }

sm24tat4xbProtocolbasedVLANConfigValueSNAPOUI OBJECT-TYPE
    SYNTAX      DisplayString
    MAX-ACCESS  read-create
    STATUS      current
    DESCRIPTION
        "SNAP OUI.
        Format:xx-xx-xx"
    ::= {sm24tat4xbProtocolbasedVLANConfigEntry 4 }

sm24tat4xbProtocolbasedVLANConfigValueSNAPPID OBJECT-TYPE
    SYNTAX      DisplayString
    MAX-ACCESS  read-create
    STATUS      current
    DESCRIPTION
        "SNAP PID
        Ranging between 0x00 and 0xff."
    ::= {sm24tat4xbProtocolbasedVLANConfigEntry 5 }

sm24tat4xbProtocolbasedVLANConfigValueLLCDSAP OBJECT-TYPE
    SYNTAX      DisplayString
    MAX-ACCESS  read-create
    STATUS      current
    DESCRIPTION
        "LLC DSAP.
        Range: 0x00-0xff"
    ::= {sm24tat4xbProtocolbasedVLANConfigEntry 6 }

sm24tat4xbProtocolbasedVLANConfigValueLLCSSAP OBJECT-TYPE
    SYNTAX      DisplayString
    MAX-ACCESS  read-create
    STATUS      current
    DESCRIPTION
        "LLC SSAP.
        Range: 0x00-0xff"
    ::= {sm24tat4xbProtocolbasedVLANConfigEntry 7 }

sm24tat4xbProtocolbasedVLANConfigGroupName OBJECT-TYPE
    SYNTAX      DisplayString
    MAX-ACCESS  read-create
    STATUS      current
    DESCRIPTION
        "Group Name
        16-character long string, unique for every entry, which consists of a combination of alphabets (a-z or A-Z) and integers(0-9)."
    ::= {sm24tat4xbProtocolbasedVLANConfigEntry 8 }

sm24tat4xbProtocolbasedVLANConfigRowStatus OBJECT-TYPE
    SYNTAX      RowStatus
    MAX-ACCESS  read-create
    STATUS      current
    DESCRIPTION
        "Row Status."
    ::= {sm24tat4xbProtocolbasedVLANConfigEntry 9 }



sm24tat4xbGroupNameToVLANMappingConfigTable  OBJECT-TYPE
    SYNTAX      SEQUENCE OF SM24TAT4XBGroupNameToVLANMappingConfigEntry
    MAX-ACCESS  not-accessible
    STATUS      current
    DESCRIPTION
        "Group Name To VLAN Mapping Config table"
    ::= { sm24tat4xbProtocolbasedVLANConfig 2 }

sm24tat4xbGroupNameToVLANMappingConfigEntry OBJECT-TYPE
    SYNTAX    SM24TAT4XBGroupNameToVLANMappingConfigEntry
    MAX-ACCESS    not-accessible
    STATUS    current
    DESCRIPTION
        "Group Name To VLAN Mapping Config table."
    INDEX    { sm24tat4xbGroupNameToVLANMappingConfigIndex }
    ::= { sm24tat4xbGroupNameToVLANMappingConfigTable 1 }

SM24TAT4XBGroupNameToVLANMappingConfigEntry ::=
    SEQUENCE {
    sm24tat4xbGroupNameToVLANMappingConfigIndex    Integer32,
    sm24tat4xbGroupNameToVLANMappingConfigGroupName    DisplayString,
    sm24tat4xbGroupNameToVLANMappingConfigVLANID    Integer32,
    sm24tat4xbGroupNameToVLANMappingConfigPortMembers  DisplayString,
    sm24tat4xbGroupNameToVLANMappingConfigRowStatus    RowStatus
    }

sm24tat4xbGroupNameToVLANMappingConfigIndex OBJECT-TYPE
    SYNTAX      Integer32(1..65535)
    MAX-ACCESS  not-accessible
    STATUS      current
    DESCRIPTION
        "Group Name To VLAN Mapping Config index."
    ::= {sm24tat4xbGroupNameToVLANMappingConfigEntry 1 }

sm24tat4xbGroupNameToVLANMappingConfigGroupName OBJECT-TYPE
    SYNTAX      DisplayString
    MAX-ACCESS  read-create
    STATUS      current
    DESCRIPTION
        "Group Name
        16-character long string, unique for every entry, which consists of a combination of alphabets (a-z or A-Z) and integers(0-9)."
    ::= {sm24tat4xbGroupNameToVLANMappingConfigEntry 2 }

sm24tat4xbGroupNameToVLANMappingConfigVLANID OBJECT-TYPE
    SYNTAX      Integer32
    MAX-ACCESS  read-create
    STATUS      current
    DESCRIPTION
        "VLAN ID"
    ::= {sm24tat4xbGroupNameToVLANMappingConfigEntry 3 }

sm24tat4xbGroupNameToVLANMappingConfigPortMembers OBJECT-TYPE
    SYNTAX      DisplayString
    MAX-ACCESS  read-create
    STATUS      current
    DESCRIPTION
        "0:remove or exclude the port from the mapping
        1:include a port in the mapping"
    ::= {sm24tat4xbGroupNameToVLANMappingConfigEntry 4 }

sm24tat4xbGroupNameToVLANMappingConfigRowStatus OBJECT-TYPE
    SYNTAX      RowStatus
    MAX-ACCESS  read-create
    STATUS      current
    DESCRIPTION
        "Row Status."
    ::= {sm24tat4xbGroupNameToVLANMappingConfigEntry 5 }

sm24tat4xbIPSubnetBasedVLANConfig     OBJECT IDENTIFIER    ::= { sm24tat4xbVLAN 11 }

sm24tat4xbIPSubnetBasedVLANConfigTable  OBJECT-TYPE
    SYNTAX      SEQUENCE OF SM24TAT4XBIPSubnetBasedVLANConfigEntry
    MAX-ACCESS  not-accessible
    STATUS      current
    DESCRIPTION
        "IP Subnet Based VLAN Config table"
    ::= { sm24tat4xbIPSubnetBasedVLANConfig 1 }

sm24tat4xbIPSubnetBasedVLANConfigEntry OBJECT-TYPE
    SYNTAX    SM24TAT4XBIPSubnetBasedVLANConfigEntry
    MAX-ACCESS    not-accessible
    STATUS    current
    DESCRIPTION
        "IP Subnet Based VLAN Config table."
    INDEX    { sm24tat4xbIPSubnetBasedVLANConfigIndex }
    ::= { sm24tat4xbIPSubnetBasedVLANConfigTable 1 }

SM24TAT4XBIPSubnetBasedVLANConfigEntry ::=
    SEQUENCE {
    sm24tat4xbIPSubnetBasedVLANConfigIndex    Integer32,
    sm24tat4xbIPSubnetBasedVLANConfigIPAddress    IpAddress,
    sm24tat4xbIPSubnetBasedVLANConfigMaskLength    Integer32,
    sm24tat4xbIPSubnetBasedVLANConfigVLANID    Integer32,
    sm24tat4xbIPSubnetBasedVLANConfigPortMembers  DisplayString,
    sm24tat4xbIPSubnetBasedVLANConfigRowStatus    RowStatus
    }

sm24tat4xbIPSubnetBasedVLANConfigIndex OBJECT-TYPE
    SYNTAX      Integer32(1..65535)
    MAX-ACCESS  not-accessible
    STATUS      current
    DESCRIPTION
        "IP Subnet Based VLAN Config index."
    ::= {sm24tat4xbIPSubnetBasedVLANConfigEntry 1 }

sm24tat4xbIPSubnetBasedVLANConfigIPAddress OBJECT-TYPE
    SYNTAX      IpAddress
    MAX-ACCESS  read-create
    STATUS      current
    DESCRIPTION
        "The subnet's IP address"
    ::= {sm24tat4xbIPSubnetBasedVLANConfigEntry 2 }

sm24tat4xbIPSubnetBasedVLANConfigMaskLength OBJECT-TYPE
    SYNTAX      Integer32
    MAX-ACCESS  read-create
    STATUS      current
    DESCRIPTION
        "The subnet's mask length. "
    ::= {sm24tat4xbIPSubnetBasedVLANConfigEntry 3 }

sm24tat4xbIPSubnetBasedVLANConfigVLANID OBJECT-TYPE
    SYNTAX      Integer32
    MAX-ACCESS  read-create
    STATUS      current
    DESCRIPTION
        "VLAN ID"
    ::= {sm24tat4xbIPSubnetBasedVLANConfigEntry 4 }

sm24tat4xbIPSubnetBasedVLANConfigPortMembers OBJECT-TYPE
    SYNTAX      DisplayString
    MAX-ACCESS  read-create
    STATUS      current
    DESCRIPTION
        "0:remove or exclude the port from the mapping
        1:include a port in the mapping"
    ::= {sm24tat4xbIPSubnetBasedVLANConfigEntry 5 }

sm24tat4xbIPSubnetBasedVLANConfigRowStatus OBJECT-TYPE
    SYNTAX      RowStatus
    MAX-ACCESS  read-create
    STATUS      current
    DESCRIPTION
        "Row Status."
    ::= {sm24tat4xbIPSubnetBasedVLANConfigEntry 6 }

sm24tat4xbVLANNameConfig     OBJECT IDENTIFIER    ::= { sm24tat4xbVLAN 12 }

sm24tat4xbVLANNameConfigTable  OBJECT-TYPE
    SYNTAX      SEQUENCE OF SM24TAT4XBVLANNameConfigEntry
    MAX-ACCESS  not-accessible
    STATUS      current
    DESCRIPTION
        "VLAN Name Config table"
    ::= { sm24tat4xbVLANNameConfig 1 }

sm24tat4xbVLANNameConfigEntry OBJECT-TYPE
    SYNTAX    SM24TAT4XBVLANNameConfigEntry
    MAX-ACCESS    not-accessible
    STATUS    current
    DESCRIPTION
        "VLAN Name Config table."
    INDEX    { sm24tat4xbVLANNameConfigIndex }
    ::= { sm24tat4xbVLANNameConfigTable 1 }

SM24TAT4XBVLANNameConfigEntry ::=
    SEQUENCE {
    sm24tat4xbVLANNameConfigIndex    Integer32,
    sm24tat4xbVLANNameConfigVLANName     DisplayString
    }

sm24tat4xbVLANNameConfigIndex OBJECT-TYPE
    SYNTAX      Integer32(1..65535)
    MAX-ACCESS  not-accessible
    STATUS      current
    DESCRIPTION
        "VLAN Name Config index."
    ::= {sm24tat4xbVLANNameConfigEntry 1 }

sm24tat4xbVLANNameConfigVLANName OBJECT-TYPE
    SYNTAX      DisplayString
    MAX-ACCESS  read-write
    STATUS      current
    DESCRIPTION
        "VLAN Name."
    ::= {sm24tat4xbVLANNameConfigEntry 2 }


sm24tat4xbNTPConf    OBJECT IDENTIFIER ::= { sm24tat4xbSystem 12 }

sm24tat4xbNTPConfigMode OBJECT-TYPE
        SYNTAX    INTEGER {useLocal(0),useNTP(1)}
        MAX-ACCESS    read-write
        STATUS    current
        DESCRIPTION
            "The system NTP Mode.
            useLocal(0) : Use Local Settings,
            useNTP(1)    : Use NTP Server."
        DEFVAL  { useLocal }
        ::= {     sm24tat4xbNTPConf 1 }

--sm24tat4xbNTPConfigAutomatic    OBJECT-TYPE
--        SYNTAX      Integer32 (0|1)
--        MAX-ACCESS  read-write
--        STATUS      current
--        DESCRIPTION
--            "Indicates the Automatic mode operation. Possible modes are:
--            0:Disable, NTP servers available from the config.
--            1:Enable, NTP servers available from the DHCP."
--        ::= { sm24tat4xbNTPConf 2 }

sm24tat4xbNTPConfigTimeSyncInterval    OBJECT-TYPE
        SYNTAX      Integer32 (5|10|15|30|60|120)
        MAX-ACCESS  read-write
        STATUS      current
        DESCRIPTION
            "Time-Sync Interval.
            Valid values are restricted to 5,10,15,30,60,120 minutes. "
        ::= { sm24tat4xbNTPConf 3 }

sm24tat4xbNTPConfigServerAddress1    OBJECT-TYPE
        SYNTAX      DisplayString
        MAX-ACCESS  read-write
        STATUS      current
        DESCRIPTION
            "Provide the IPv4 or IPv6 address of a NTP server."
        ::= { sm24tat4xbNTPConf 4 }

sm24tat4xbNTPConfigServerAddress2    OBJECT-TYPE
        SYNTAX      DisplayString
        MAX-ACCESS  read-write
        STATUS      current
        DESCRIPTION
            "Provide the IPv4 or IPv6 address of a NTP server."
        ::= { sm24tat4xbNTPConf 5 }

sm24tat4xbNTPConfigServerAddress3    OBJECT-TYPE
        SYNTAX      DisplayString
        MAX-ACCESS  read-write
        STATUS      current
        DESCRIPTION
            "Provide the IPv4 or IPv6 address of a NTP server."
        ::= { sm24tat4xbNTPConf 6 }

sm24tat4xbNTPConfigServerAddress4    OBJECT-TYPE
        SYNTAX      DisplayString
        MAX-ACCESS  read-write
        STATUS      current
        DESCRIPTION
            "Provide the IPv4 or IPv6 address of a NTP server."
        ::= { sm24tat4xbNTPConf 7 }

sm24tat4xbNTPConfigServerAddress5    OBJECT-TYPE
        SYNTAX      DisplayString
        MAX-ACCESS  read-write
        STATUS      current
        DESCRIPTION
            "Provide the IPv4 or IPv6 address of a NTP server."
        ::= { sm24tat4xbNTPConf 8 }

sm24tat4xbTemperature    OBJECT IDENTIFIER ::= { sm24tat4xbSystem 13 }

sm24tat4xbTemperature1    OBJECT IDENTIFIER ::= { sm24tat4xbTemperature 1 }

sm24tat4xbTemperature1Celsius    OBJECT-TYPE
        SYNTAX      DisplayString
        MAX-ACCESS  read-only
        STATUS      current
        DESCRIPTION
            "Value of Celsius"
        ::= { sm24tat4xbTemperature1 1 }

sm24tat4xbTemperature1Fahrenheit    OBJECT-TYPE
        SYNTAX      DisplayString
        MAX-ACCESS  read-only
        STATUS      current
        DESCRIPTION
            "Value of Fahrenheit"
        ::= { sm24tat4xbTemperature1 2 }

sm24tat4xbTemperature2    OBJECT IDENTIFIER ::= { sm24tat4xbTemperature 2 }

sm24tat4xbTemperature2Celsius    OBJECT-TYPE
        SYNTAX      DisplayString
        MAX-ACCESS  read-only
        STATUS      current
        DESCRIPTION
            "Value of Celsius"
        ::= { sm24tat4xbTemperature2 1 }

sm24tat4xbTemperature2Fahrenheit    OBJECT-TYPE
        SYNTAX      DisplayString
        MAX-ACCESS  read-only
        STATUS      current
        DESCRIPTION
            "Value of Fahrenheit"
        ::= { sm24tat4xbTemperature2 2 }

-- =======================================================================================================================
sm24tat4xbConfiguration                     OBJECT IDENTIFIER ::= { sm24tat4xbProductId 2 }

sm24tat4xbPort                          OBJECT IDENTIFIER ::= { sm24tat4xbConfiguration 1 }

sm24tat4xbPortConfigurationTable OBJECT-TYPE
    SYNTAX      SEQUENCE OF SM24TAT4XBPortConfigurationEntry
    MAX-ACCESS  not-accessible
    STATUS      current
    DESCRIPTION
        " Show port configurations. "
    ::= { sm24tat4xbPort 1 }

sm24tat4xbPortConfigurationEntry OBJECT-TYPE
    SYNTAX      SM24TAT4XBPortConfigurationEntry
    MAX-ACCESS  not-accessible
    STATUS      current
    DESCRIPTION
        " "
    INDEX    { sm24tat4xbPortConfPort  }
    ::= { sm24tat4xbPortConfigurationTable 1 }

SM24TAT4XBPortConfigurationEntry ::= SEQUENCE {
    sm24tat4xbPortConfPort             Integer32,
    sm24tat4xbPortConfDescription          DisplayString,
    sm24tat4xbPortConfLink             DisplayString,
    sm24tat4xbPortConfSpeedStatus          DisplayString,
    sm24tat4xbPortConfSpeedMode        Integer32,
    sm24tat4xbPortConfFlowControlRxStatus      Integer32,
    sm24tat4xbPortConfFlowControlTxStatus      Integer32,
    sm24tat4xbPortConfFlowControlMode      Integer32,
    sm24tat4xbPortConfMaximumFrameSize     Integer32
-- sm24tat4xbPortConfExcessiveCollisionMode    Integer32,
-- sm24tat4xbPortConfPowerControl         Integer32,
-- sm24tat4xbPortConfPortMedia        DisplayString
}

sm24tat4xbPortConfPort OBJECT-TYPE
    SYNTAX      Integer32 (1..4095)
    MAX-ACCESS  not-accessible
    STATUS      current
    DESCRIPTION
        " port, range : 1 - port number. "
    ::= { sm24tat4xbPortConfigurationEntry 1 }

sm24tat4xbPortConfDescription OBJECT-TYPE
    SYNTAX      DisplayString
    MAX-ACCESS  read-write
    STATUS      current
    DESCRIPTION
        " Interface specific description.
        Up to 16 characters describing this interface. "
    ::= { sm24tat4xbPortConfigurationEntry 2 }

sm24tat4xbPortConfLink OBJECT-TYPE
    SYNTAX      DisplayString(SIZE (2..4))
    MAX-ACCESS  read-only
    STATUS      current
    DESCRIPTION
        " The current link state. "
    ::= { sm24tat4xbPortConfigurationEntry 3 }

sm24tat4xbPortConfSpeedStatus OBJECT-TYPE
    SYNTAX      DisplayString(SIZE (6..12))
    MAX-ACCESS  read-only
    STATUS      current
    DESCRIPTION
        " The current link speed of the port. "
    ::= { sm24tat4xbPortConfigurationEntry 4 }

sm24tat4xbPortConfSpeedMode OBJECT-TYPE
    SYNTAX      Integer32 (0..9)
    MAX-ACCESS  read-write
    STATUS      current
    DESCRIPTION
        "default: 1,
        0: disable state,
        1: auto,
        2: 10 Half,
        3: 10 Full,
        4: 100 Half,
        5: 100 Full,
        6: 1G full,
        7: 10G Full,
        8: 100-FX,
        9: 1000-X. "
    ::= { sm24tat4xbPortConfigurationEntry 5 }

sm24tat4xbPortConfFlowControlRxStatus OBJECT-TYPE
    SYNTAX      Integer32 (0|1)
    MAX-ACCESS  read-only
    STATUS      current
    DESCRIPTION
        "0: disable
        1: enable
        2: not support.  "
    ::= { sm24tat4xbPortConfigurationEntry 6 }

sm24tat4xbPortConfFlowControlTxStatus OBJECT-TYPE
    SYNTAX      Integer32 (0|1)
    MAX-ACCESS  read-only
    STATUS      current
    DESCRIPTION
        "0: disable
        1: enable
        2: not support.  "
    ::= { sm24tat4xbPortConfigurationEntry 7 }

sm24tat4xbPortConfFlowControlMode OBJECT-TYPE
    SYNTAX      Integer32 (0|1)
    MAX-ACCESS  read-write
    STATUS      current
    DESCRIPTION
        "default: 0,
        0: disable
        1: enable
        2: not support. "
    ::= { sm24tat4xbPortConfigurationEntry 8 }

sm24tat4xbPortConfMaximumFrameSize OBJECT-TYPE
    SYNTAX      Integer32 (1518..10240)
    MAX-ACCESS  read-write
    STATUS      current
    DESCRIPTION
        "default: 10240 , range : 1518 - 10240 "
    ::= { sm24tat4xbPortConfigurationEntry 9 }

--sm24tat4xbPortConfExcessiveCollisionMode OBJECT-TYPE
--    SYNTAX      Integer32 (0|1)
--    MAX-ACCESS  read-write
--    STATUS      current
--    DESCRIPTION
--    "default: 0,
--    Excessive Collision Mode :
--    0: Discard,
--    1: Restart,
--    2: not support.
--    "
--    ::= { sm24tat4xbPortConfigurationEntry 10 }

--sm24tat4xbPortConfPowerControl OBJECT-TYPE
--    SYNTAX      Integer32 (0..3)
--    MAX-ACCESS  read-write
--    STATUS      current
--    DESCRIPTION
--    "default: 0,
--    PowerControl :
--    0: disable,
--    1: Actiphy,
--    2: Dynamic (perfectReach),
--    3: Enable,
--    4: not support.
--    "
--    ::= { sm24tat4xbPortConfigurationEntry 11 }

--sm24tat4xbPortConfPortMedia OBJECT-TYPE
--    SYNTAX      DisplayString(SIZE (1..4))
--    MAX-ACCESS  read-only
--    STATUS      current
--    DESCRIPTION
--    " Show port media. "
--    ::= { sm24tat4xbPortConfigurationEntry 12 }


sm24tat4xbPortTrafficStatisticsTable OBJECT-TYPE
    SYNTAX      SEQUENCE OF SM24TAT4XBPortTrafficStatisticsEntry
    MAX-ACCESS  not-accessible
    STATUS      current
    DESCRIPTION
        " "
    ::= { sm24tat4xbPort 2 }

sm24tat4xbPortTrafficStatisticsEntry OBJECT-TYPE
    SYNTAX      SM24TAT4XBPortTrafficStatisticsEntry
    MAX-ACCESS  not-accessible
    STATUS      current
    DESCRIPTION
        " "
    INDEX    { sm24tat4xbPortTrafficStatisticsPort  }
    ::= { sm24tat4xbPortTrafficStatisticsTable 1 }

SM24TAT4XBPortTrafficStatisticsEntry ::= SEQUENCE {
    sm24tat4xbPortTrafficStatisticsPort      Integer32,
    sm24tat4xbPortTrafficStatisticsClear     Integer32,
    sm24tat4xbPortTrafficRxPackets        Counter64,
    sm24tat4xbPortTrafficRxOctets        Counter64,
    sm24tat4xbPortTrafficRxUnicast        Counter64,
    sm24tat4xbPortTrafficRxMulticast         Counter64,
    sm24tat4xbPortTrafficRxBroadcast         Counter64,
    sm24tat4xbPortTrafficRxPause         Counter64,
    sm24tat4xbPortTrafficRx64Bytes        Counter64,
    sm24tat4xbPortTrafficRx65to127Bytes      Counter64,
    sm24tat4xbPortTrafficRx128to255Bytes     Counter64,
    sm24tat4xbPortTrafficRx256to511Bytes     Counter64,
    sm24tat4xbPortTrafficRx512to1023Bytes    Counter64,
    sm24tat4xbPortTrafficRx1024to1526Bytes    Counter64,
    sm24tat4xbPortTrafficRxExceecd1527Bytes      Counter64,
    sm24tat4xbPortTrafficRxQ0            Counter64,
    sm24tat4xbPortTrafficRxQ1            Counter64,
    sm24tat4xbPortTrafficRxQ2            Counter64,
    sm24tat4xbPortTrafficRxQ3            Counter64,
    sm24tat4xbPortTrafficRxQ4            Counter64,
    sm24tat4xbPortTrafficRxQ5            Counter64,
    sm24tat4xbPortTrafficRxQ6            Counter64,
    sm24tat4xbPortTrafficRxQ7            Counter64,
    sm24tat4xbPortTrafficRxDrops         Counter64,
    sm24tat4xbPortTrafficRxCRCorAlignment    Counter64,
    sm24tat4xbPortTrafficRxUndersize         Counter64,
    sm24tat4xbPortTrafficRxOversize          Counter64,
    sm24tat4xbPortTrafficRxFragments         Counter64,
    sm24tat4xbPortTrafficRxJabber        Counter64,
    sm24tat4xbPortTrafficRxFiltered          Counter64,
    sm24tat4xbPortTrafficTxPackets        Counter64,
    sm24tat4xbPortTrafficTxOctets        Counter64,
    sm24tat4xbPortTrafficTxUnicast        Counter64,
    sm24tat4xbPortTrafficTxMulticast         Counter64,
    sm24tat4xbPortTrafficTxBroadcast         Counter64,
    sm24tat4xbPortTrafficTxPause         Counter64,
    sm24tat4xbPortTrafficTx64Bytes        Counter64,
    sm24tat4xbPortTrafficTx65to127Bytes      Counter64,
    sm24tat4xbPortTrafficTx128to255Bytes     Counter64,
    sm24tat4xbPortTrafficTx256to511Bytes     Counter64,
    sm24tat4xbPortTrafficTx512to1023Bytes    Counter64,
    sm24tat4xbPortTrafficTx1024to1526Bytes    Counter64,
    sm24tat4xbPortTrafficTxExceecd1527Bytes      Counter64,
    sm24tat4xbPortTrafficTxQ0            Counter64,
    sm24tat4xbPortTrafficTxQ1            Counter64,
    sm24tat4xbPortTrafficTxQ2            Counter64,
    sm24tat4xbPortTrafficTxQ3            Counter64,
    sm24tat4xbPortTrafficTxQ4            Counter64,
    sm24tat4xbPortTrafficTxQ5            Counter64,
    sm24tat4xbPortTrafficTxQ6            Counter64,
    sm24tat4xbPortTrafficTxQ7            Counter64,
    sm24tat4xbPortTrafficTxDrops         Counter64,
    sm24tat4xbPortTrafficTxLateOrExcColl     Counter64
}

sm24tat4xbPortTrafficStatisticsPort OBJECT-TYPE
    SYNTAX      Integer32 (1..4095)
    MAX-ACCESS  not-accessible
    STATUS      current
    DESCRIPTION
        " "
    ::= { sm24tat4xbPortTrafficStatisticsEntry 1 }

sm24tat4xbPortTrafficStatisticsClear OBJECT-TYPE
    SYNTAX      Integer32(0|1)
    MAX-ACCESS  read-write
    STATUS      current
    DESCRIPTION
        " "
    ::= { sm24tat4xbPortTrafficStatisticsEntry 2 }

sm24tat4xbPortTrafficRxPackets OBJECT-TYPE
    SYNTAX      Counter64
    MAX-ACCESS  read-only
    STATUS      current
    DESCRIPTION
        " "
    ::= { sm24tat4xbPortTrafficStatisticsEntry 3 }

sm24tat4xbPortTrafficRxOctets OBJECT-TYPE
    SYNTAX      Counter64
    MAX-ACCESS  read-only
    STATUS      current
    DESCRIPTION
        " "
    ::= { sm24tat4xbPortTrafficStatisticsEntry 4 }

sm24tat4xbPortTrafficRxUnicast OBJECT-TYPE
    SYNTAX      Counter64
    MAX-ACCESS  read-only
    STATUS      current
    DESCRIPTION
        " "
    ::= { sm24tat4xbPortTrafficStatisticsEntry 5 }

sm24tat4xbPortTrafficRxMulticast OBJECT-TYPE
    SYNTAX      Counter64
    MAX-ACCESS  read-only
    STATUS      current
    DESCRIPTION
        " "
    ::= { sm24tat4xbPortTrafficStatisticsEntry 6 }

sm24tat4xbPortTrafficRxBroadcast OBJECT-TYPE
    SYNTAX      Counter64
    MAX-ACCESS  read-only
    STATUS      current
    DESCRIPTION
        " "
    ::= { sm24tat4xbPortTrafficStatisticsEntry 7 }

sm24tat4xbPortTrafficRxPause OBJECT-TYPE
    SYNTAX      Counter64
    MAX-ACCESS  read-only
    STATUS      current
    DESCRIPTION
        " "
    ::= { sm24tat4xbPortTrafficStatisticsEntry 8 }

sm24tat4xbPortTrafficRx64Bytes OBJECT-TYPE
    SYNTAX      Counter64
    MAX-ACCESS  read-only
    STATUS      current
    DESCRIPTION
        " "
    ::= { sm24tat4xbPortTrafficStatisticsEntry 9 }

sm24tat4xbPortTrafficRx65to127Bytes OBJECT-TYPE
    SYNTAX      Counter64
    MAX-ACCESS  read-only
    STATUS      current
    DESCRIPTION
        " "
    ::= { sm24tat4xbPortTrafficStatisticsEntry 10 }

sm24tat4xbPortTrafficRx128to255Bytes OBJECT-TYPE
    SYNTAX      Counter64
    MAX-ACCESS  read-only
    STATUS      current
    DESCRIPTION
        " "
    ::= { sm24tat4xbPortTrafficStatisticsEntry 11 }

sm24tat4xbPortTrafficRx256to511Bytes OBJECT-TYPE
    SYNTAX      Counter64
    MAX-ACCESS  read-only
    STATUS      current
    DESCRIPTION
        " "
    ::= { sm24tat4xbPortTrafficStatisticsEntry 12 }

sm24tat4xbPortTrafficRx512to1023Bytes OBJECT-TYPE
    SYNTAX      Counter64
    MAX-ACCESS  read-only
    STATUS      current
    DESCRIPTION
        " "
    ::= { sm24tat4xbPortTrafficStatisticsEntry 13 }

sm24tat4xbPortTrafficRx1024to1526Bytes OBJECT-TYPE
    SYNTAX      Counter64
    MAX-ACCESS  read-only
    STATUS      current
    DESCRIPTION
        " "
    ::= { sm24tat4xbPortTrafficStatisticsEntry 14 }

sm24tat4xbPortTrafficRxExceecd1527Bytes OBJECT-TYPE
    SYNTAX      Counter64
    MAX-ACCESS  read-only
    STATUS      current
    DESCRIPTION
        " "
    ::= { sm24tat4xbPortTrafficStatisticsEntry 15 }

sm24tat4xbPortTrafficRxQ0 OBJECT-TYPE
    SYNTAX      Counter64
    MAX-ACCESS  read-only
    STATUS      current
    DESCRIPTION
        " "
    ::= { sm24tat4xbPortTrafficStatisticsEntry 16 }

sm24tat4xbPortTrafficRxQ1 OBJECT-TYPE
    SYNTAX      Counter64
    MAX-ACCESS  read-only
    STATUS      current
    DESCRIPTION
        " "
    ::= { sm24tat4xbPortTrafficStatisticsEntry 17 }

sm24tat4xbPortTrafficRxQ2 OBJECT-TYPE
    SYNTAX      Counter64
    MAX-ACCESS  read-only
    STATUS      current
    DESCRIPTION
        " "
    ::= { sm24tat4xbPortTrafficStatisticsEntry 18 }

sm24tat4xbPortTrafficRxQ3 OBJECT-TYPE
    SYNTAX      Counter64
    MAX-ACCESS  read-only
    STATUS      current
    DESCRIPTION
        " "
    ::= { sm24tat4xbPortTrafficStatisticsEntry 19 }

sm24tat4xbPortTrafficRxQ4 OBJECT-TYPE
    SYNTAX      Counter64
    MAX-ACCESS  read-only
    STATUS      current
    DESCRIPTION
        " "
    ::= { sm24tat4xbPortTrafficStatisticsEntry 20 }

sm24tat4xbPortTrafficRxQ5 OBJECT-TYPE
    SYNTAX      Counter64
    MAX-ACCESS  read-only
    STATUS      current
    DESCRIPTION
        " "
    ::= { sm24tat4xbPortTrafficStatisticsEntry 21 }

sm24tat4xbPortTrafficRxQ6 OBJECT-TYPE
    SYNTAX      Counter64
    MAX-ACCESS  read-only
    STATUS      current
    DESCRIPTION
        " "
    ::= { sm24tat4xbPortTrafficStatisticsEntry 22 }

sm24tat4xbPortTrafficRxQ7 OBJECT-TYPE
    SYNTAX      Counter64
    MAX-ACCESS  read-only
    STATUS      current
    DESCRIPTION
        " "
    ::= { sm24tat4xbPortTrafficStatisticsEntry 23 }

sm24tat4xbPortTrafficRxDrops OBJECT-TYPE
    SYNTAX      Counter64
    MAX-ACCESS  read-only
    STATUS      current
    DESCRIPTION
        " "
    ::= { sm24tat4xbPortTrafficStatisticsEntry 24 }

sm24tat4xbPortTrafficRxCRCorAlignment OBJECT-TYPE
    SYNTAX      Counter64
    MAX-ACCESS  read-only
    STATUS      current
    DESCRIPTION
        " "
    ::= { sm24tat4xbPortTrafficStatisticsEntry 25 }

sm24tat4xbPortTrafficRxUndersize OBJECT-TYPE
    SYNTAX      Counter64
    MAX-ACCESS  read-only
    STATUS      current
    DESCRIPTION
        " "
    ::= { sm24tat4xbPortTrafficStatisticsEntry 26 }

sm24tat4xbPortTrafficRxOversize OBJECT-TYPE
    SYNTAX      Counter64
    MAX-ACCESS  read-only
    STATUS      current
    DESCRIPTION
        " "
    ::= { sm24tat4xbPortTrafficStatisticsEntry 27 }

sm24tat4xbPortTrafficRxFragments OBJECT-TYPE
    SYNTAX      Counter64
    MAX-ACCESS  read-only
    STATUS      current
    DESCRIPTION
        " "
    ::= { sm24tat4xbPortTrafficStatisticsEntry 28 }

sm24tat4xbPortTrafficRxJabber OBJECT-TYPE
    SYNTAX      Counter64
    MAX-ACCESS  read-only
    STATUS      current
    DESCRIPTION
        " "
    ::= { sm24tat4xbPortTrafficStatisticsEntry 29 }

sm24tat4xbPortTrafficRxFiltered OBJECT-TYPE
    SYNTAX      Counter64
    MAX-ACCESS  read-only
    STATUS      current
    DESCRIPTION
        " "
    ::= { sm24tat4xbPortTrafficStatisticsEntry 30 }

sm24tat4xbPortTrafficTxPackets OBJECT-TYPE
    SYNTAX      Counter64
    MAX-ACCESS  read-only
    STATUS      current
    DESCRIPTION
        " "
    ::= { sm24tat4xbPortTrafficStatisticsEntry 31 }

sm24tat4xbPortTrafficTxOctets OBJECT-TYPE
    SYNTAX      Counter64
    MAX-ACCESS  read-only
    STATUS      current
    DESCRIPTION
        " "
    ::= { sm24tat4xbPortTrafficStatisticsEntry 32 }

sm24tat4xbPortTrafficTxUnicast OBJECT-TYPE
    SYNTAX      Counter64
    MAX-ACCESS  read-only
    STATUS      current
    DESCRIPTION
        " "
    ::= { sm24tat4xbPortTrafficStatisticsEntry 33 }

sm24tat4xbPortTrafficTxMulticast OBJECT-TYPE
    SYNTAX      Counter64
    MAX-ACCESS  read-only
    STATUS      current
    DESCRIPTION
        " "
    ::= { sm24tat4xbPortTrafficStatisticsEntry 34 }

sm24tat4xbPortTrafficTxBroadcast OBJECT-TYPE
    SYNTAX      Counter64
    MAX-ACCESS  read-only
    STATUS      current
    DESCRIPTION
        " "
    ::= { sm24tat4xbPortTrafficStatisticsEntry 35 }

sm24tat4xbPortTrafficTxPause OBJECT-TYPE
    SYNTAX      Counter64
    MAX-ACCESS  read-only
    STATUS      current
    DESCRIPTION
        " "
    ::= { sm24tat4xbPortTrafficStatisticsEntry 36 }

sm24tat4xbPortTrafficTx64Bytes OBJECT-TYPE
    SYNTAX      Counter64
    MAX-ACCESS  read-only
    STATUS      current
    DESCRIPTION
        " "
    ::= { sm24tat4xbPortTrafficStatisticsEntry 37 }

sm24tat4xbPortTrafficTx65to127Bytes OBJECT-TYPE
    SYNTAX      Counter64
    MAX-ACCESS  read-only
    STATUS      current
    DESCRIPTION
        " "
    ::= { sm24tat4xbPortTrafficStatisticsEntry 38 }

sm24tat4xbPortTrafficTx128to255Bytes OBJECT-TYPE
    SYNTAX      Counter64
    MAX-ACCESS  read-only
    STATUS      current
    DESCRIPTION
        " "
    ::= { sm24tat4xbPortTrafficStatisticsEntry 39 }

sm24tat4xbPortTrafficTx256to511Bytes OBJECT-TYPE
    SYNTAX      Counter64
    MAX-ACCESS  read-only
    STATUS      current
    DESCRIPTION
        " "
    ::= { sm24tat4xbPortTrafficStatisticsEntry 40 }

sm24tat4xbPortTrafficTx512to1023Bytes OBJECT-TYPE
    SYNTAX      Counter64
    MAX-ACCESS  read-only
    STATUS      current
    DESCRIPTION
        " "
    ::= { sm24tat4xbPortTrafficStatisticsEntry 41 }

sm24tat4xbPortTrafficTx1024to1526Bytes OBJECT-TYPE
    SYNTAX      Counter64
    MAX-ACCESS  read-only
    STATUS      current
    DESCRIPTION
        " "
    ::= { sm24tat4xbPortTrafficStatisticsEntry 42 }

sm24tat4xbPortTrafficTxExceecd1527Bytes OBJECT-TYPE
    SYNTAX      Counter64
    MAX-ACCESS  read-only
    STATUS      current
    DESCRIPTION
        " "
    ::= { sm24tat4xbPortTrafficStatisticsEntry 43 }

sm24tat4xbPortTrafficTxQ0 OBJECT-TYPE
    SYNTAX      Counter64
    MAX-ACCESS  read-only
    STATUS      current
    DESCRIPTION
        " "
    ::= { sm24tat4xbPortTrafficStatisticsEntry 44 }

sm24tat4xbPortTrafficTxQ1 OBJECT-TYPE
    SYNTAX      Counter64
    MAX-ACCESS  read-only
    STATUS      current
    DESCRIPTION
        " "
    ::= { sm24tat4xbPortTrafficStatisticsEntry 45 }

sm24tat4xbPortTrafficTxQ2 OBJECT-TYPE
    SYNTAX      Counter64
    MAX-ACCESS  read-only
    STATUS      current
    DESCRIPTION
        " "
    ::= { sm24tat4xbPortTrafficStatisticsEntry 46 }

sm24tat4xbPortTrafficTxQ3 OBJECT-TYPE
    SYNTAX      Counter64
    MAX-ACCESS  read-only
    STATUS      current
    DESCRIPTION
        " "
    ::= { sm24tat4xbPortTrafficStatisticsEntry 47 }

sm24tat4xbPortTrafficTxQ4 OBJECT-TYPE
    SYNTAX      Counter64
    MAX-ACCESS  read-only
    STATUS      current
    DESCRIPTION
        " "
    ::= { sm24tat4xbPortTrafficStatisticsEntry 48 }

sm24tat4xbPortTrafficTxQ5 OBJECT-TYPE
    SYNTAX      Counter64
    MAX-ACCESS  read-only
    STATUS      current
    DESCRIPTION
        " "
    ::= { sm24tat4xbPortTrafficStatisticsEntry 49 }

sm24tat4xbPortTrafficTxQ6 OBJECT-TYPE
    SYNTAX      Counter64
    MAX-ACCESS  read-only
    STATUS      current
    DESCRIPTION
        " "
    ::= { sm24tat4xbPortTrafficStatisticsEntry 50 }


sm24tat4xbPortTrafficTxQ7 OBJECT-TYPE
    SYNTAX      Counter64
    MAX-ACCESS  read-only
    STATUS      current
    DESCRIPTION
        " "
    ::= { sm24tat4xbPortTrafficStatisticsEntry 51 }

sm24tat4xbPortTrafficTxDrops OBJECT-TYPE
    SYNTAX      Counter64
    MAX-ACCESS  read-only
    STATUS      current
    DESCRIPTION
        " "
    ::= { sm24tat4xbPortTrafficStatisticsEntry 52 }

sm24tat4xbPortTrafficTxLateOrExcColl OBJECT-TYPE
    SYNTAX      Counter64
    MAX-ACCESS  read-only
    STATUS      current
    DESCRIPTION
        " "
    ::= { sm24tat4xbPortTrafficStatisticsEntry 53 }


sm24tat4xbPortQoSStatistics                     OBJECT IDENTIFIER ::= { sm24tat4xbPort 3 }

sm24tat4xbPortQoSStatisticsClear OBJECT-TYPE
    SYNTAX      Integer32(0|1)
    MAX-ACCESS  read-only
    STATUS      current
    DESCRIPTION
        "default: 0
        0: none
        1: clear "
    ::= { sm24tat4xbPortQoSStatistics 1 }

sm24tat4xbPortQoSStatisticsTable OBJECT-TYPE
    SYNTAX      SEQUENCE OF SM24TAT4XBPortQoSStatisticsEntry
    MAX-ACCESS  not-accessible
    STATUS      current
    DESCRIPTION
        " "
    ::= { sm24tat4xbPortQoSStatistics 2 }

sm24tat4xbPortQoSStatisticsEntry OBJECT-TYPE
    SYNTAX      SM24TAT4XBPortQoSStatisticsEntry
    MAX-ACCESS  not-accessible
    STATUS      current
    DESCRIPTION
        " "
    INDEX    { sm24tat4xbPortQoSStatisticsPort  }
    ::= { sm24tat4xbPortQoSStatisticsTable 1 }

SM24TAT4XBPortQoSStatisticsEntry ::= SEQUENCE {
    sm24tat4xbPortQoSStatisticsPort      Integer32,
    sm24tat4xbPortQoSQ0Rx        Counter64,
    sm24tat4xbPortQoSQ0Tx        Counter64,
    sm24tat4xbPortQoSQ1Rx        Counter64,
    sm24tat4xbPortQoSQ1Tx        Counter64,
    sm24tat4xbPortQoSQ2Rx        Counter64,
    sm24tat4xbPortQoSQ2Tx        Counter64,
    sm24tat4xbPortQoSQ3Rx        Counter64,
    sm24tat4xbPortQoSQ3Tx        Counter64,
    sm24tat4xbPortQoSQ4Rx        Counter64,
    sm24tat4xbPortQoSQ4Tx        Counter64,
    sm24tat4xbPortQoSQ5Rx        Counter64,
    sm24tat4xbPortQoSQ5Tx        Counter64,
    sm24tat4xbPortQoSQ6Rx        Counter64,
    sm24tat4xbPortQoSQ6Tx        Counter64,
    sm24tat4xbPortQoSQ7Rx        Counter64,
    sm24tat4xbPortQoSQ7Tx        Counter64
}

sm24tat4xbPortQoSStatisticsPort OBJECT-TYPE
    SYNTAX      Integer32 (1..4095)
    MAX-ACCESS  not-accessible
    STATUS      current
    DESCRIPTION
        " "
    ::= { sm24tat4xbPortQoSStatisticsEntry 1 }

sm24tat4xbPortQoSQ0Rx OBJECT-TYPE
    SYNTAX      Counter64
    MAX-ACCESS  read-only
    STATUS      current
    DESCRIPTION
        " "
    ::= { sm24tat4xbPortQoSStatisticsEntry 2 }

sm24tat4xbPortQoSQ0Tx OBJECT-TYPE
    SYNTAX      Counter64
    MAX-ACCESS  read-only
    STATUS      current
    DESCRIPTION
        " "
    ::= { sm24tat4xbPortQoSStatisticsEntry 3 }

sm24tat4xbPortQoSQ1Rx OBJECT-TYPE
    SYNTAX      Counter64
    MAX-ACCESS  read-only
    STATUS      current
    DESCRIPTION
        " "
    ::= { sm24tat4xbPortQoSStatisticsEntry 4 }

sm24tat4xbPortQoSQ1Tx OBJECT-TYPE
    SYNTAX      Counter64
    MAX-ACCESS  read-only
    STATUS      current
    DESCRIPTION
        " "
    ::= { sm24tat4xbPortQoSStatisticsEntry 5 }

sm24tat4xbPortQoSQ2Rx OBJECT-TYPE
    SYNTAX      Counter64
    MAX-ACCESS  read-only
    STATUS      current
    DESCRIPTION
        " "
    ::= { sm24tat4xbPortQoSStatisticsEntry 6 }

sm24tat4xbPortQoSQ2Tx OBJECT-TYPE
    SYNTAX      Counter64
    MAX-ACCESS  read-only
    STATUS      current
    DESCRIPTION
        " "
    ::= { sm24tat4xbPortQoSStatisticsEntry 7 }

sm24tat4xbPortQoSQ3Rx OBJECT-TYPE
    SYNTAX      Counter64
    MAX-ACCESS  read-only
    STATUS      current
    DESCRIPTION
        " "
    ::= { sm24tat4xbPortQoSStatisticsEntry 8 }

sm24tat4xbPortQoSQ3Tx OBJECT-TYPE
    SYNTAX      Counter64
    MAX-ACCESS  read-only
    STATUS      current
    DESCRIPTION
        " "
    ::= { sm24tat4xbPortQoSStatisticsEntry 9 }

sm24tat4xbPortQoSQ4Rx OBJECT-TYPE
    SYNTAX      Counter64
    MAX-ACCESS  read-only
    STATUS      current
    DESCRIPTION
        " "
    ::= { sm24tat4xbPortQoSStatisticsEntry 10 }

sm24tat4xbPortQoSQ4Tx OBJECT-TYPE
    SYNTAX      Counter64
    MAX-ACCESS  read-only
    STATUS      current
    DESCRIPTION
        " "
    ::= { sm24tat4xbPortQoSStatisticsEntry 11 }

sm24tat4xbPortQoSQ5Rx OBJECT-TYPE
    SYNTAX      Counter64
    MAX-ACCESS  read-only
    STATUS      current
    DESCRIPTION
        " "
    ::= { sm24tat4xbPortQoSStatisticsEntry 12 }

sm24tat4xbPortQoSQ5Tx OBJECT-TYPE
    SYNTAX      Counter64
    MAX-ACCESS  read-only
    STATUS      current
    DESCRIPTION
        " "
    ::= { sm24tat4xbPortQoSStatisticsEntry 13 }

sm24tat4xbPortQoSQ6Rx OBJECT-TYPE
    SYNTAX      Counter64
    MAX-ACCESS  read-only
    STATUS      current
    DESCRIPTION
        " "
    ::= { sm24tat4xbPortQoSStatisticsEntry 14 }

sm24tat4xbPortQoSQ6Tx OBJECT-TYPE
    SYNTAX      Counter64
    MAX-ACCESS  read-only
    STATUS      current
    DESCRIPTION
        " "
    ::= { sm24tat4xbPortQoSStatisticsEntry 15 }

sm24tat4xbPortQoSQ7Rx OBJECT-TYPE
    SYNTAX      Counter64
    MAX-ACCESS  read-only
    STATUS      current
    DESCRIPTION
        " "
    ::= { sm24tat4xbPortQoSStatisticsEntry 16 }

sm24tat4xbPortQoSQ7Tx OBJECT-TYPE
    SYNTAX      Counter64
    MAX-ACCESS  read-only
    STATUS      current
    DESCRIPTION
        " "
    ::= { sm24tat4xbPortQoSStatisticsEntry 17 }

sm24tat4xbSFPInfoTable OBJECT-TYPE
    SYNTAX      SEQUENCE OF SM24TAT4XBSFPInfoEntry
    MAX-ACCESS  not-accessible
    STATUS      current
    DESCRIPTION
        " "
    ::= { sm24tat4xbPort 4 }

sm24tat4xbSFPInfoEntry OBJECT-TYPE
    SYNTAX      SM24TAT4XBSFPInfoEntry
    MAX-ACCESS  not-accessible
    STATUS      current
    DESCRIPTION
        " "
    INDEX    { sm24tat4xbSFPInfoIndex }
    ::= { sm24tat4xbSFPInfoTable 1 }

SM24TAT4XBSFPInfoEntry ::= SEQUENCE {
    sm24tat4xbSFPInfoIndex        Integer32,
    sm24tat4xbSFPInfoPort        DisplayString,
    sm24tat4xbSFPConnectorType        DisplayString,
    sm24tat4xbSFPFiberType        DisplayString,
    sm24tat4xbSFPTxCentralWavelength     DisplayString,
    sm24tat4xbSFPBaudRate        DisplayString,
    sm24tat4xbSFPVendorOUI        DisplayString,
    sm24tat4xbSFPVendorName          DisplayString,
    sm24tat4xbSFPVendorPN        DisplayString,
    sm24tat4xbSFPVendorRev        DisplayString,
    sm24tat4xbSFPVendorSN        DisplayString,
    sm24tat4xbSFPDateCode        DisplayString,
    sm24tat4xbSFPTemperature         DisplayString,
    sm24tat4xbSFPVcc             DisplayString,
    sm24tat4xbSFPMon1Bias        DisplayString,
    sm24tat4xbSFPMon2TxPWR        DisplayString,
    sm24tat4xbSFPMon3RxPWR        DisplayString
}

sm24tat4xbSFPInfoIndex OBJECT-TYPE
    SYNTAX      Integer32 (1..4095)
    MAX-ACCESS  not-accessible
    STATUS      current
    DESCRIPTION
        " "
    ::= { sm24tat4xbSFPInfoEntry 1 }

sm24tat4xbSFPInfoPort OBJECT-TYPE
    SYNTAX      DisplayString
    MAX-ACCESS  read-only
    STATUS      current
    DESCRIPTION
        " "
    ::= { sm24tat4xbSFPInfoEntry 2 }

sm24tat4xbSFPConnectorType OBJECT-TYPE
    SYNTAX      DisplayString
    MAX-ACCESS  read-only
    STATUS      current
    DESCRIPTION
        " "
    ::= { sm24tat4xbSFPInfoEntry 3 }

sm24tat4xbSFPFiberType OBJECT-TYPE
    SYNTAX      DisplayString
    MAX-ACCESS  read-only
    STATUS      current
    DESCRIPTION
        " "
    ::= { sm24tat4xbSFPInfoEntry 4 }

sm24tat4xbSFPTxCentralWavelength OBJECT-TYPE
    SYNTAX      DisplayString
    MAX-ACCESS  read-only
    STATUS      current
    DESCRIPTION
        " "
    ::= { sm24tat4xbSFPInfoEntry 5 }

sm24tat4xbSFPBaudRate OBJECT-TYPE
    SYNTAX      DisplayString
    MAX-ACCESS  read-only
    STATUS      current
    DESCRIPTION
        " "
    ::= { sm24tat4xbSFPInfoEntry 6 }

sm24tat4xbSFPVendorOUI OBJECT-TYPE
    SYNTAX      DisplayString
    MAX-ACCESS  read-only
    STATUS      current
    DESCRIPTION
        " "
    ::= { sm24tat4xbSFPInfoEntry 7 }

sm24tat4xbSFPVendorName OBJECT-TYPE
    SYNTAX      DisplayString
    MAX-ACCESS  read-only
    STATUS      current
    DESCRIPTION
        " "
    ::= { sm24tat4xbSFPInfoEntry 8 }

sm24tat4xbSFPVendorPN OBJECT-TYPE
    SYNTAX      DisplayString
    MAX-ACCESS  read-only
    STATUS      current
    DESCRIPTION
        " "
    ::= { sm24tat4xbSFPInfoEntry 9 }

sm24tat4xbSFPVendorRev OBJECT-TYPE
    SYNTAX      DisplayString
    MAX-ACCESS  read-only
    STATUS      current
    DESCRIPTION
        " "
    ::= { sm24tat4xbSFPInfoEntry 10 }

sm24tat4xbSFPVendorSN OBJECT-TYPE
    SYNTAX      DisplayString
    MAX-ACCESS  read-only
    STATUS      current
    DESCRIPTION
        " "
    ::= { sm24tat4xbSFPInfoEntry 11 }

sm24tat4xbSFPDateCode OBJECT-TYPE
    SYNTAX      DisplayString
    MAX-ACCESS  read-only
    STATUS      current
    DESCRIPTION
        " "
    ::= { sm24tat4xbSFPInfoEntry 12 }

sm24tat4xbSFPTemperature OBJECT-TYPE
    SYNTAX      DisplayString
    MAX-ACCESS  read-only
    STATUS      current
    DESCRIPTION
        " "
    ::= { sm24tat4xbSFPInfoEntry 13 }

sm24tat4xbSFPVcc OBJECT-TYPE
    SYNTAX      DisplayString
    MAX-ACCESS  read-only
    STATUS      current
    DESCRIPTION
        " "
    ::= { sm24tat4xbSFPInfoEntry 14 }

sm24tat4xbSFPMon1Bias OBJECT-TYPE
    SYNTAX      DisplayString
    MAX-ACCESS  read-only
    STATUS      current
    DESCRIPTION
        " "
    ::= { sm24tat4xbSFPInfoEntry 15 }

sm24tat4xbSFPMon2TxPWR OBJECT-TYPE
    SYNTAX      DisplayString
    MAX-ACCESS  read-only
    STATUS      current
    DESCRIPTION
        " "
    ::= { sm24tat4xbSFPInfoEntry 16 }

sm24tat4xbSFPMon3RxPWR OBJECT-TYPE
    SYNTAX      DisplayString
    MAX-ACCESS  read-only
    STATUS      current
    DESCRIPTION
        " "
    ::= { sm24tat4xbSFPInfoEntry 17 }


sm24tat4xbVoiceVLAN                         OBJECT IDENTIFIER ::= { sm24tat4xbConfiguration 2 }

sm24tat4xbVoiceVLANConf                     OBJECT IDENTIFIER ::= { sm24tat4xbVoiceVLAN 1 }

sm24tat4xbVoiceVLANMode OBJECT-TYPE
    SYNTAX      Integer32 (0|1)
    MAX-ACCESS  read-write
    STATUS      current
    DESCRIPTION
        " Voice VLAN mode operation.
        default: 0,
        0: disable
        1: enable"
    ::= { sm24tat4xbVoiceVLANConf 1 }

sm24tat4xbVoiceVLANVLANId OBJECT-TYPE
    SYNTAX      Integer32 (1..4094)
    MAX-ACCESS  read-write
    STATUS      current
    DESCRIPTION
        "Voice VLAN ID.
        default: 1000,
        range : 1-4094. "
    ::= { sm24tat4xbVoiceVLANConf 2 }

sm24tat4xbVoiceVLANAgingTime OBJECT-TYPE
    SYNTAX      Integer32 (10..10000000)
    MAX-ACCESS  read-write
    STATUS      current
    DESCRIPTION
        " Voice VLAN secure learning aging time.
        default: 86400,
        range : 10 - 10000000. "
    ::= { sm24tat4xbVoiceVLANConf 3 }

sm24tat4xbVoiceVLANTrafficClass OBJECT-TYPE
    SYNTAX      Integer32 (0..7)
    MAX-ACCESS  read-write
    STATUS      current
    DESCRIPTION
        " Voice VLAN traffic class, all traffic on the Voice VLAN
        will apply this class, available value is from 0(Low)
        to 7(High).
        default: 7. "
    ::= { sm24tat4xbVoiceVLANConf 4 }


sm24tat4xbVoiceVLANPortTable OBJECT-TYPE
    SYNTAX      SEQUENCE OF SM24TAT4XBVoiceVLANPortEntry
    MAX-ACCESS  not-accessible
    STATUS      current
    DESCRIPTION
        " Show Voice Vlan configuration. "
    ::= { sm24tat4xbVoiceVLANConf 5 }

sm24tat4xbVoiceVLANPortEntry OBJECT-TYPE
    SYNTAX      SM24TAT4XBVoiceVLANPortEntry
    MAX-ACCESS  not-accessible
    STATUS      current
    DESCRIPTION
        " "
    INDEX    { sm24tat4xbVoiceVLANPort  }
    ::= { sm24tat4xbVoiceVLANPortTable 1 }

SM24TAT4XBVoiceVLANPortEntry ::= SEQUENCE {
    sm24tat4xbVoiceVLANPort            Integer32,
    sm24tat4xbVoiceVLANPortMode        Integer32,
    sm24tat4xbVoiceVLANPortSecurity        Integer32,
    sm24tat4xbVoiceVLANPortDiscoveryProtocol    Integer32
}

sm24tat4xbVoiceVLANPort OBJECT-TYPE
    SYNTAX      Integer32 (1..4095)
    MAX-ACCESS  not-accessible
    STATUS      current
    DESCRIPTION
        " port, range : 1 - port number. "
    ::= { sm24tat4xbVoiceVLANPortEntry 1 }

sm24tat4xbVoiceVLANPortMode OBJECT-TYPE
    SYNTAX      Integer32 (0..2)
    MAX-ACCESS  read-write
    STATUS      current
    DESCRIPTION
        " Voice VLAN port mode.
        default: 0,
        0: Disable (Disjoin from Voice VLAN.)
        1: Auto (Enable auto detect mode. It detects whether there is VoIP phone attached to the specific port and configures the Voice VLAN members automatically.)
        2: Forced (Force join to Voice VLAN.)"
    ::= { sm24tat4xbVoiceVLANPortEntry 2 }

sm24tat4xbVoiceVLANPortSecurity OBJECT-TYPE
    SYNTAX      Integer32 (0|1)
    MAX-ACCESS  read-write
    STATUS      current
    DESCRIPTION
        " Voice VLAN port security mode.
        default: 0,
        0: Disable (Disjoin from Voice VLAN.)
        1: enable ( Enable Voice VLAN security mode. When the function is
             enabled, all non-telephone MAC address in Voice VLAN
             will be blocked 10 seconds.)"
    ::= { sm24tat4xbVoiceVLANPortEntry 3 }

sm24tat4xbVoiceVLANPortDiscoveryProtocol OBJECT-TYPE
    SYNTAX      Integer32 (0..2)
    MAX-ACCESS  read-write
    STATUS      current
    DESCRIPTION
        " Voice VLAN port discovery protocol.
        default: 0
        0: OUI (Detect telephony device by OUI address.)
        1: LLDP (Detect telephony device by LLDP.)
        2: Both (Both OUI and LLDP.) "
    ::= { sm24tat4xbVoiceVLANPortEntry 4 }


sm24tat4xbVoiceVLANOUI                      OBJECT IDENTIFIER ::= { sm24tat4xbVoiceVLAN 2 }

sm24tat4xbVoiceVLANOUICreate OBJECT-TYPE
    SYNTAX    Integer32(0|1)
    MAX-ACCESS    read-write
    STATUS    current
    DESCRIPTION
        "default: 0
        0 : None  (read only)
        1 : Create an OUI entry"
    ::= { sm24tat4xbVoiceVLANOUI 1 }

sm24tat4xbVoiceVLANOUITable OBJECT-TYPE
    SYNTAX      SEQUENCE OF SM24TAT4XBVoiceVLANOUIEntry
    MAX-ACCESS  not-accessible
    STATUS      current
    DESCRIPTION
        " Create Voice VLAN OUI entry. Modify OUI table will
        restart auto detect OUI process. "
    ::= { sm24tat4xbVoiceVLANOUI 2 }

sm24tat4xbVoiceVLANOUIEntry OBJECT-TYPE
    SYNTAX      SM24TAT4XBVoiceVLANOUIEntry
    MAX-ACCESS  not-accessible
    STATUS      current
    DESCRIPTION
        " "
    INDEX    { sm24tat4xbVoiceVLANOUIIndex  }
    ::= { sm24tat4xbVoiceVLANOUITable 1 }

SM24TAT4XBVoiceVLANOUIEntry ::= SEQUENCE {
    sm24tat4xbVoiceVLANOUIIndex     Integer32,
    sm24tat4xbVoiceVLANTelephonyOUI     DisplayString,
    sm24tat4xbVoiceVLANDescription      DisplayString,
    sm24tat4xbVoiceVLANOUIRowStatus     RowStatus
}

sm24tat4xbVoiceVLANOUIIndex OBJECT-TYPE
    SYNTAX      Integer32 (1..16)
    MAX-ACCESS  not-accessible
    STATUS      current
    DESCRIPTION
        " "
    ::= { sm24tat4xbVoiceVLANOUIEntry 1 }

sm24tat4xbVoiceVLANTelephonyOUI OBJECT-TYPE
    SYNTAX      DisplayString (SIZE (1..32))
    MAX-ACCESS  read-create
    STATUS      current
    DESCRIPTION
        "OUI address, format : 0a 1b 2c "
    ::= { sm24tat4xbVoiceVLANOUIEntry 2 }

sm24tat4xbVoiceVLANDescription OBJECT-TYPE
    SYNTAX      DisplayString (SIZE (1..32))
    MAX-ACCESS  read-create
    STATUS      current
    DESCRIPTION
        " Up to 32 characters describing OUI address. "
    ::= { sm24tat4xbVoiceVLANOUIEntry 3 }

sm24tat4xbVoiceVLANOUIRowStatus OBJECT-TYPE
    SYNTAX      RowStatus
    MAX-ACCESS  read-create
    STATUS      current
    DESCRIPTION
	    "This object indicates the status of this entry, and is used
	    to create/delete entries.  Any object in an entry of this table
	    may be modified while the value of the corresponding instance
	    of this object is active(1).
	    createAndGo, notReady not supported."
    ::= { sm24tat4xbVoiceVLANOUIEntry 4 }

--sm24tat4xbGARP                            OBJECT IDENTIFIER ::= { sm24tat4xbConfiguration 3 }

--sm24tat4xbGARPConfTable OBJECT-TYPE
--    SYNTAX      SEQUENCE OF SM24TAT4XBGARPConfEntry
--    MAX-ACCESS  not-accessible
--    STATUS      current
--    DESCRIPTION
--        " "
--    ::= { sm24tat4xbGARP 1 }

--sm24tat4xbGARPConfEntry OBJECT-TYPE
--    SYNTAX      SM24TAT4XBGARPConfEntry
--    MAX-ACCESS  not-accessible
--    STATUS      current
--    DESCRIPTION
--        " "
--    INDEX    { sm24tat4xbGARPConfPort  }
--    ::= { sm24tat4xbGARPConfTable 1 }

--SM24TAT4XBGARPConfEntry ::= SEQUENCE {
--    sm24tat4xbGARPConfPort        Integer32,
--    sm24tat4xbGARPJoinTimer      Integer32,
--    sm24tat4xbGARPLeaveTimer     Integer32,
--    sm24tat4xbGARPLeaveAllTimer      Integer32,
--    sm24tat4xbGARPApplicantion    Integer32,
--    sm24tat4xbGARPAttributeType      Integer32,
--    sm24tat4xbGARPApplicant      Integer32
--}

--sm24tat4xbGARPConfPort OBJECT-TYPE
--    SYNTAX      Integer32 (1..4095)
--    MAX-ACCESS  not-accessible
--    STATUS      current
--    DESCRIPTION
--        " "
--    ::= { sm24tat4xbGARPConfEntry 1 }

--sm24tat4xbGARPJoinTimer OBJECT-TYPE
--    SYNTAX      Integer32 (200..1000)
--    MAX-ACCESS  read-write
--    STATUS      current
--    DESCRIPTION
--    "default: 200, range : 200 - 1000 "
--    ::= { sm24tat4xbGARPConfEntry 2 }

--sm24tat4xbGARPLeaveTimer OBJECT-TYPE
--    SYNTAX      Integer32 (600..3000)
--    MAX-ACCESS  read-write
--    STATUS      current
--    DESCRIPTION
--    "default: 600 , range : 600 - 3000"
--    ::= { sm24tat4xbGARPConfEntry 3 }

--sm24tat4xbGARPLeaveAllTimer OBJECT-TYPE
--    SYNTAX      Integer32 (10000..50000)
--    MAX-ACCESS  read-write
--    STATUS      current
--    DESCRIPTION
--    "default: 10000, range : 10000 - 50000 "
--    ::= { sm24tat4xbGARPConfEntry 4 }

--sm24tat4xbGARPApplicantion OBJECT-TYPE
--    SYNTAX      Integer32(1)
--    MAX-ACCESS  read-write
--    STATUS      current
--    DESCRIPTION
--    "default: 1
--    1: GVRP"
--    ::= { sm24tat4xbGARPConfEntry 5 }

--sm24tat4xbGARPAttributeType OBJECT-TYPE
--    SYNTAX      Integer32(1)
--    MAX-ACCESS  read-write
--    STATUS      current
--    DESCRIPTION
--    "default: 1
--    1: VLAN"
--    ::= { sm24tat4xbGARPConfEntry 6 }

--sm24tat4xbGARPApplicant OBJECT-TYPE
--    SYNTAX      Integer32(0|1)
--    MAX-ACCESS  read-write
--    STATUS      current
--    DESCRIPTION
--    "default: 0
--    0: normal-participant
--    1: non-participant"
--    ::= { sm24tat4xbGARPConfEntry 7 }

--sm24tat4xbGARPStatisticsTable OBJECT-TYPE
--    SYNTAX      SEQUENCE OF SM24TAT4XBGARPStatisticsEntry
--    MAX-ACCESS  not-accessible
--    STATUS      current
--    DESCRIPTION
--    " Show the basic GARP port statistics. "
--    ::= { sm24tat4xbGARP 2 }

--sm24tat4xbGARPStatisticsEntry OBJECT-TYPE
--    SYNTAX      SM24TAT4XBGARPStatisticsEntry
--    MAX-ACCESS  not-accessible
--    STATUS      current
--    DESCRIPTION
--        " "
--    INDEX    { sm24tat4xbGARPStatisticsPort  }
--    ::= { sm24tat4xbGARPStatisticsTable 1 }

--SM24TAT4XBGARPStatisticsEntry ::= SEQUENCE {
--    sm24tat4xbGARPStatisticsPort         Integer32,
--    sm24tat4xbGARPStatisticsPeerMAC      DisplayString,
--    sm24tat4xbGARPStatisticsFailedCount      Counter32
--}

--sm24tat4xbGARPStatisticsPort OBJECT-TYPE
--    SYNTAX      Integer32 (1..4095)
--    MAX-ACCESS  not-accessible
--    STATUS      current
--    DESCRIPTION
--    " port, range : 1 - port number. "
--    ::= { sm24tat4xbGARPStatisticsEntry 1 }

--sm24tat4xbGARPStatisticsPeerMAC OBJECT-TYPE
--    SYNTAX      DisplayString
--    MAX-ACCESS  read-only
--    STATUS      current
--    DESCRIPTION
--    " Peer MAC is MAC address of the neighbour Switch from with GARP frame is received.  "
--    ::= { sm24tat4xbGARPStatisticsEntry 2 }

--sm24tat4xbGARPStatisticsFailedCount OBJECT-TYPE
--    SYNTAX      Counter32
--    MAX-ACCESS  read-only
--    STATUS      current
--    DESCRIPTION
--    " explain Failed count here. "
--    ::= { sm24tat4xbGARPStatisticsEntry 3 }

sm24tat4xbGVRP                            OBJECT IDENTIFIER ::= { sm24tat4xbConfiguration 4 }

sm24tat4xbGVRPConf                            OBJECT IDENTIFIER ::= { sm24tat4xbGVRP 1 }

sm24tat4xbGVRPMode OBJECT-TYPE
    SYNTAX      Integer32(0|1)
    MAX-ACCESS  read-write
    STATUS      current
    DESCRIPTION
        "default: 0,
        0: disable,
        1: enable. "
    ::= { sm24tat4xbGVRPConf 1 }

sm24tat4xbGVRPMaxVlan OBJECT-TYPE
    SYNTAX      Integer32(1..4095)
    MAX-ACCESS  read-write
    STATUS      current
    DESCRIPTION
        "Number of simultaniously VLANs that GVRP can control. "
    ::= { sm24tat4xbGVRPConf 2 }

sm24tat4xbGVRPJoinTime OBJECT-TYPE
    SYNTAX      Integer32(1..20)
    MAX-ACCESS  read-write
    STATUS      current
    DESCRIPTION
        "join-time in units of centi seconds. Range is 1-20. Default is 20. "
    ::= { sm24tat4xbGVRPConf 3 }

sm24tat4xbGVRPLeaveTime OBJECT-TYPE
    SYNTAX      Integer32(60..300)
    MAX-ACCESS  read-write
    STATUS      current
    DESCRIPTION
        "leave-time in units of centi seconds. Range is 60-300. Default is 60. "
    ::= { sm24tat4xbGVRPConf 4 }

sm24tat4xbGVRPLeaveAllTime OBJECT-TYPE
    SYNTAX      Integer32(1000..5000)
    MAX-ACCESS  read-write
    STATUS      current
    DESCRIPTION
        "leave-all-time in units of centi seconds Range is 1000-5000. Default is 1000"
    ::= { sm24tat4xbGVRPConf 5 }

sm24tat4xbGVRPConfTable OBJECT-TYPE
    SYNTAX      SEQUENCE OF SM24TAT4XBGVRPConfEntry
    MAX-ACCESS  not-accessible
    STATUS      current
    DESCRIPTION
        " "
    ::= { sm24tat4xbGVRPConf 6 }

sm24tat4xbGVRPConfEntry OBJECT-TYPE
    SYNTAX      SM24TAT4XBGVRPConfEntry
    MAX-ACCESS  not-accessible
    STATUS      current
    DESCRIPTION
        " "
    INDEX    { sm24tat4xbGVRPConfPort  }
    ::= { sm24tat4xbGVRPConfTable 1 }

SM24TAT4XBGVRPConfEntry ::= SEQUENCE {
    sm24tat4xbGVRPConfPort        Integer32,
    sm24tat4xbGVRPConfPortMode    Integer32
-- sm24tat4xbGVRPConfPortRRole      Integer32
}

sm24tat4xbGVRPConfPort OBJECT-TYPE
    SYNTAX      Integer32 (1..4095)
    MAX-ACCESS  not-accessible
    STATUS      current
    DESCRIPTION
        " "
    ::= { sm24tat4xbGVRPConfEntry 1 }

sm24tat4xbGVRPConfPortMode OBJECT-TYPE
    SYNTAX      Integer32(0|1)
    MAX-ACCESS  read-write
    STATUS      current
    DESCRIPTION
        "default: 0
        1: enable
        0: disable"
    ::= { sm24tat4xbGVRPConfEntry 2 }

--sm24tat4xbGVRPConfPortRRole OBJECT-TYPE
--    SYNTAX      Integer32(0|1)
--    MAX-ACCESS  read-write
--    STATUS      current
--    DESCRIPTION
--    "default: 0
--    1: enable
--    0: disable"
--    ::= { sm24tat4xbGVRPConfEntry 3 }

--sm24tat4xbGVRPStatisticsTable OBJECT-TYPE
--    SYNTAX      SEQUENCE OF SM24TAT4XBGVRPStatisticsEntry
--    MAX-ACCESS  not-accessible
--    STATUS      current
--    DESCRIPTION
--        " "
--    ::= { sm24tat4xbGVRP 2 }

--sm24tat4xbGVRPStatisticsEntry OBJECT-TYPE
--    SYNTAX      SM24TAT4XBGVRPStatisticsEntry
--    MAX-ACCESS  not-accessible
--    STATUS      current
--    DESCRIPTION
--        " "
--    INDEX    { sm24tat4xbGVRPStatisticsPort  }
--    ::= { sm24tat4xbGVRPStatisticsTable 1 }

--SM24TAT4XBGVRPStatisticsEntry ::= SEQUENCE {
--    sm24tat4xbGVRPStatisticsPort     Integer32,
--    sm24tat4xbGVRPStatisticsJoinTxCnt    Counter32,
--    sm24tat4xbGVRPStatisticsLeaveTxCnt    Counter32
--}

--sm24tat4xbGVRPStatisticsPort OBJECT-TYPE
--    SYNTAX      Integer32 (1..4095)
--    MAX-ACCESS  not-accessible
--    STATUS      current
--    DESCRIPTION
--        " "
--    ::= { sm24tat4xbGVRPStatisticsEntry 1 }

--sm24tat4xbGVRPStatisticsJoinTxCnt OBJECT-TYPE
--    SYNTAX      Counter32
--    MAX-ACCESS  read-only
--    STATUS      current
--    DESCRIPTION
--        " "
--    ::= { sm24tat4xbGVRPStatisticsEntry 2 }

--sm24tat4xbGVRPStatisticsLeaveTxCnt OBJECT-TYPE
--    SYNTAX      Counter32
--    MAX-ACCESS  read-only
--    STATUS      current
--    DESCRIPTION
--        " "
--    ::= { sm24tat4xbGVRPStatisticsEntry 3 }


sm24tat4xbMirroring                         OBJECT IDENTIFIER ::= { sm24tat4xbConfiguration 6 }

sm24tat4xbMonitorSession OBJECT-TYPE
    SYNTAX      Integer32(1..5)
    MAX-ACCESS  read-write
    STATUS      current
    DESCRIPTION
        "Monitor session."
    ::= { sm24tat4xbMirroring 1 }

sm24tat4xbPortToMirrorOn OBJECT-TYPE
    SYNTAX      Integer32
    MAX-ACCESS  read-write
    STATUS      current
    DESCRIPTION
        "default: 0
        0: disable,
        range : 1 - port number. "
    ::= { sm24tat4xbMirroring 2 }

sm24tat4xbMirrorTable OBJECT-TYPE
    SYNTAX      SEQUENCE OF SM24TAT4XBMirrorEntry
    MAX-ACCESS  not-accessible
    STATUS      current
    DESCRIPTION
        " "
    ::= { sm24tat4xbMirroring 3 }

sm24tat4xbMirrorEntry OBJECT-TYPE
    SYNTAX      SM24TAT4XBMirrorEntry
    MAX-ACCESS  not-accessible
    STATUS      current
    DESCRIPTION
        " "
    INDEX    { sm24tat4xbMirrorPort  }
    ::= { sm24tat4xbMirrorTable 1 }

SM24TAT4XBMirrorEntry ::= SEQUENCE {
    sm24tat4xbMirrorPort		Integer32,
    sm24tat4xbMirrorMode		Integer32
}

sm24tat4xbMirrorPort OBJECT-TYPE
    SYNTAX      Integer32 (1..4095)
    MAX-ACCESS  not-accessible
    STATUS      current
    DESCRIPTION
        " "
    ::= { sm24tat4xbMirrorEntry 1 }

sm24tat4xbMirrorMode OBJECT-TYPE
    SYNTAX      Integer32(0..3)
    MAX-ACCESS  read-write
    STATUS      current
    DESCRIPTION
        "default: 0
        0: disable
        1: rx only
        2: tx only
        3: enable
        Setting Tx mirroring for analyzer port has no effect. Tx mirroring ignored"
    ::= { sm24tat4xbMirrorEntry 2 }

sm24tat4xbTrapEventSeverity                         OBJECT IDENTIFIER ::= { sm24tat4xbConfiguration 7 }

sm24tat4xbTrapEventSeverityTable OBJECT-TYPE
    SYNTAX      SEQUENCE OF SM24TAT4XBTrapEventSeverityEntry
    MAX-ACCESS  not-accessible
    STATUS      current
    DESCRIPTION
        " "
    ::= { sm24tat4xbTrapEventSeverity 1 }

sm24tat4xbTrapEventSeverityEntry OBJECT-TYPE
    SYNTAX      SM24TAT4XBTrapEventSeverityEntry
    MAX-ACCESS  not-accessible
    STATUS      current
    DESCRIPTION
        " "
    INDEX    { sm24tat4xbTrapEventSeverityIndex }
    ::= { sm24tat4xbTrapEventSeverityTable 1 }

SM24TAT4XBTrapEventSeverityEntry ::= SEQUENCE {
    sm24tat4xbTrapEventSeverityIndex    Integer32,
    sm24tat4xbTrapEventSeverityGroupName    DisplayString,
    sm24tat4xbTrapEventSeverityLevel    Integer32,
    sm24tat4xbTrapEventSeveritySyslog    Integer32,
    sm24tat4xbTrapEventSeverityTrap     Integer32,
    sm24tat4xbTrapEventSeveritySMTP     Integer32
}

sm24tat4xbTrapEventSeverityIndex OBJECT-TYPE
    SYNTAX      Integer32(1..65535)
    MAX-ACCESS  not-accessible
    STATUS      current
    DESCRIPTION
        " "
    ::= { sm24tat4xbTrapEventSeverityEntry 1 }

sm24tat4xbTrapEventSeverityGroupName OBJECT-TYPE
    SYNTAX      DisplayString
    MAX-ACCESS  read-only
    STATUS      current
    DESCRIPTION
        "Group Name"
    ::= { sm24tat4xbTrapEventSeverityEntry 2 }

sm24tat4xbTrapEventSeverityLevel OBJECT-TYPE
    SYNTAX      Integer32
    MAX-ACCESS  not-accessible
    STATUS      current
    DESCRIPTION
        "0:Emergency
        1:Alert
        2:Critical
        3:Error
        4:Warning
        5:Notice
        6:Information
        7:Debug"
    ::= { sm24tat4xbTrapEventSeverityEntry 3 }

sm24tat4xbTrapEventSeveritySyslog OBJECT-TYPE
    SYNTAX      Integer32
    MAX-ACCESS  not-accessible
    STATUS      current
    DESCRIPTION
        "0:disable
        1:enable"
    ::= { sm24tat4xbTrapEventSeverityEntry 4 }

sm24tat4xbTrapEventSeverityTrap OBJECT-TYPE
    SYNTAX      Integer32
    MAX-ACCESS  not-accessible
    STATUS      current
    DESCRIPTION
        "0:disable
        1:enable"
    ::= { sm24tat4xbTrapEventSeverityEntry 5 }

sm24tat4xbTrapEventSeveritySMTP OBJECT-TYPE
    SYNTAX      Integer32
    MAX-ACCESS  not-accessible
    STATUS      current
    DESCRIPTION
        "0:disable
        1:enable"
    ::= { sm24tat4xbTrapEventSeverityEntry 6 }

-- =======================================================================================================================
sm24tat4xbSMTP                         OBJECT IDENTIFIER ::= { sm24tat4xbConfiguration 8 }

sm24tat4xbSMTPMailServer OBJECT-TYPE
    SYNTAX      DisplayString
    MAX-ACCESS  read-write
    STATUS      current
    DESCRIPTION
        " Up to 47 characters describing email server. "
    ::= { sm24tat4xbSMTP 1 }

sm24tat4xbSMTPUserName OBJECT-TYPE
    SYNTAX      DisplayString
    MAX-ACCESS  read-write
    STATUS      current
    DESCRIPTION
        " Up to 47 characters describing user name. "
    ::= { sm24tat4xbSMTP 2 }

sm24tat4xbSMTPPassword OBJECT-TYPE
    SYNTAX      DisplayString
    MAX-ACCESS  read-write
    STATUS      current
    DESCRIPTION
        " Up to 47 characters describing password. "
    ::= { sm24tat4xbSMTP 3 }

sm24tat4xbSMTPSender OBJECT-TYPE
    SYNTAX      DisplayString
    MAX-ACCESS  read-write
    STATUS      current
    DESCRIPTION
        " Up to 47 characters describing sender. "
    ::= { sm24tat4xbSMTP 5 }

sm24tat4xbSMTPReturnPath OBJECT-TYPE
    SYNTAX      DisplayString
    MAX-ACCESS  read-write
    STATUS      current
    DESCRIPTION
        " Up to 47 characters describing return path. "
    ::= { sm24tat4xbSMTP 6 }

sm24tat4xbSMTPEmailAddress1 OBJECT-TYPE
    SYNTAX      DisplayString
    MAX-ACCESS  read-write
    STATUS      current
    DESCRIPTION
        " Up to 47 characters describing mail address. "
    ::= { sm24tat4xbSMTP 7 }

sm24tat4xbSMTPEmailAddress2 OBJECT-TYPE
    SYNTAX      DisplayString
    MAX-ACCESS  read-write
    STATUS      current
    DESCRIPTION
        " Up to 47 characters describing mail address. "
    ::= { sm24tat4xbSMTP 8 }

sm24tat4xbSMTPEmailAddress3 OBJECT-TYPE
    SYNTAX      DisplayString
    MAX-ACCESS  read-write
    STATUS      current
    DESCRIPTION
        " Up to 47 characters describing mail address. "
    ::= { sm24tat4xbSMTP 9 }

sm24tat4xbSMTPEmailAddress4 OBJECT-TYPE
    SYNTAX      DisplayString
    MAX-ACCESS  read-write
    STATUS      current
    DESCRIPTION
        " Up to 47 characters describing mail address. "
    ::= { sm24tat4xbSMTP 10 }

sm24tat4xbSMTPEmailAddress5 OBJECT-TYPE
    SYNTAX      DisplayString
    MAX-ACCESS  read-write
    STATUS      current
    DESCRIPTION
        " Up to 47 characters describing mail address. "
    ::= { sm24tat4xbSMTP 11 }

sm24tat4xbSMTPEmailAddress6 OBJECT-TYPE
    SYNTAX      DisplayString
    MAX-ACCESS  read-write
    STATUS      current
    DESCRIPTION
        " Up to 47 characters describing mail address. "
    ::= { sm24tat4xbSMTP 12 }

-- =======================================================================================================================
sm24tat4xbACLConf                          OBJECT IDENTIFIER ::= { sm24tat4xbConfiguration 9 }

-- RowStatus Info:  createAndGo, notReady not supported.
-- =======================================================================================================================
-- Textual Conventions for the sm24tat4xb Acl Mib
-- =======================================================================================================================
--
    sm24tat4xbACL             OBJECT IDENTIFIER  ::= { sm24tat4xbACLConf 1 }
    sm24tat4xbACLACE          OBJECT IDENTIFIER  ::= { sm24tat4xbACLConf 3 }

--
-- =======================================================================================================================
-- Start sm24tat4xbACLPortConf group
-- =======================================================================================================================
--sm24tat4xbACLPortConfTable

    sm24tat4xbACLPortConfTable OBJECT-TYPE
        SYNTAX      SEQUENCE OF     SM24TAT4XBACLPortConfEntry
        MAX-ACCESS  not-accessible
        STATUS      current
        DESCRIPTION
            "The ACL Port Conf Table.
            INDEX for this table is ifIndex which is
            equivalent to the panel port number."
        ::= {     sm24tat4xbACL 1 }

    sm24tat4xbACLPortConfEntry OBJECT-TYPE
        SYNTAX      SM24TAT4XBACLPortConfEntry
        MAX-ACCESS  not-accessible
        STATUS      current
        DESCRIPTION
            "The ACL Port Conf Entry. "
        INDEX    {     ifIndex  }
        ::= {     sm24tat4xbACLPortConfTable 1 }

    SM24TAT4XBACLPortConfEntry         ::=
        SEQUENCE {
         sm24tat4xbACLPortConfPolicyID    Integer32,
         sm24tat4xbACLPortConfAction      INTEGER,
         sm24tat4xbACLPortConfRateLimiterID    Integer32,
         sm24tat4xbACLPortConfPortRedirect    Integer32,
         sm24tat4xbACLPortConfMirror      AdminMode,
         sm24tat4xbACLPortConfLogging     AdminMode,
         sm24tat4xbACLPortConfShutdown    AdminMode,
         sm24tat4xbACLPortConfState        AdminMode,
         sm24tat4xbACLPortConfCounter     Counter32
         }

    sm24tat4xbACLPortConfPolicyID OBJECT-TYPE
        SYNTAX    Integer32 (0..127)
        MAX-ACCESS    read-write
        STATUS    current
        DESCRIPTION
            "The policy to apply to this port.
            default: 0, range : 0 - 127. "
        ::= {     sm24tat4xbACLPortConfEntry 2 }

    sm24tat4xbACLPortConfAction OBJECT-TYPE
        SYNTAX      INTEGER { deny(0), permit(1) }
        MAX-ACCESS  read-write
        STATUS      current
        DESCRIPTION
            "Whether forwarding is permitted ('Permit') or denied ('Deny').
            default: 1,
            0: Deny,
            1: Permit."
        ::= {     sm24tat4xbACLPortConfEntry 3 }

    sm24tat4xbACLPortConfRateLimiterID OBJECT-TYPE
        SYNTAX      Integer32 (0..16)
        MAX-ACCESS  read-write
        STATUS      current
        DESCRIPTION
            "The rate limiter to apply on this port.
            0: Disable,
            range : 0 - 16. "
        ::= {     sm24tat4xbACLPortConfEntry 4 }

    sm24tat4xbACLPortConfPortRedirect OBJECT-TYPE
        SYNTAX      Integer32 (0..4095)
        MAX-ACCESS  read-write
        STATUS      current
        DESCRIPTION
            "Port frames are redirected on.
            0: Disable,
            range : 0 - end port number. "
        ::= {     sm24tat4xbACLPortConfEntry 5 }

    sm24tat4xbACLPortConfMirror OBJECT-TYPE
        SYNTAX      AdminMode
        MAX-ACCESS  read-write
        STATUS      current
        DESCRIPTION
            "The mirror operation of this port."
        ::= {     sm24tat4xbACLPortConfEntry 6 }

    sm24tat4xbACLPortConfLogging OBJECT-TYPE
        SYNTAX      AdminMode
        MAX-ACCESS  read-write
        STATUS      current
        DESCRIPTION
            "Specify the logging operation of this port."
        ::= {     sm24tat4xbACLPortConfEntry 7 }

    sm24tat4xbACLPortConfShutdown OBJECT-TYPE
        SYNTAX      AdminMode
        MAX-ACCESS  read-write
        STATUS      current
        DESCRIPTION
            "Specify the port shut down operation of this port."
        DEFVAL  { disable }
        ::= {     sm24tat4xbACLPortConfEntry 8 }

    sm24tat4xbACLPortConfState OBJECT-TYPE
        SYNTAX      AdminMode
        MAX-ACCESS  read-write
        STATUS      current
        DESCRIPTION
            "Specify the port state of this port."
        DEFVAL  { enable }
        ::= {     sm24tat4xbACLPortConfEntry 9 }

    sm24tat4xbACLPortConfCounter OBJECT-TYPE
        SYNTAX      Counter32
        MAX-ACCESS  read-only
        STATUS      current
        DESCRIPTION
            "Counts the number of frames that match this ACE. "
        ::= {     sm24tat4xbACLPortConfEntry 10 }

--
-- =======================================================================================================================
-- Start sm24tat4xbACLRateLimiter group
-- =======================================================================================================================
--sm24tat4xbACLRateLimiterTable

    sm24tat4xbACLRateLimiterTable OBJECT-TYPE
        SYNTAX      SEQUENCE OF     SM24TAT4XBACLRateLimiterEntry
        MAX-ACCESS  not-accessible
        STATUS      current
        DESCRIPTION
            "The ACL Rate Limiter Table."
        ::= {     sm24tat4xbACL 2 }

    sm24tat4xbACLRateLimiterEntry OBJECT-TYPE
        SYNTAX      SM24TAT4XBACLRateLimiterEntry
        MAX-ACCESS  not-accessible
        STATUS      current
        DESCRIPTION
            "The ACL Rate Limiter Entry. "
        INDEX    {     sm24tat4xbACLRateLimiterID  }
        ::= {     sm24tat4xbACLRateLimiterTable 1 }

    SM24TAT4XBACLRateLimiterEntry         ::= SEQUENCE {
         sm24tat4xbACLRateLimiterID    Integer32,
         sm24tat4xbACLRateLimiterRate     Integer32,
         sm24tat4xbACLRateLimiterUnit     Integer32
         }

    sm24tat4xbACLRateLimiterID OBJECT-TYPE
        SYNTAX      Integer32 (1..16)
        MAX-ACCESS  not-accessible
        STATUS      current
        DESCRIPTION
            "Rate Limiter ID.
            range : 1-16 "
        ::= {     sm24tat4xbACLRateLimiterEntry 1 }

    sm24tat4xbACLRateLimiterRate OBJECT-TYPE
        SYNTAX      Integer32(0..500000)
        MAX-ACCESS  read-write
        STATUS      current
        DESCRIPTION
            "default: 1,
            range :
            <0-500000> 10pps,The valid rate is 0, 10, 20, 30,
            ..., 5000000 in pps.
            <0-400000> 25kbps,The valid rate is 0, 25, 50, 75,...,
            10000000 in kbps."
        ::= {     sm24tat4xbACLRateLimiterEntry 2 }

    sm24tat4xbACLRateLimiterUnit OBJECT-TYPE
        SYNTAX      Integer32(0|1)
        MAX-ACCESS  read-write
        STATUS      current
        DESCRIPTION
            "Specify the rate unit.
            0: 10pps, 1: 25kbps.
            "
        ::= {     sm24tat4xbACLRateLimiterEntry 3 }

--
-- =======================================================================================================================
-- Start sm24tat4xbACLACE group
-- =======================================================================================================================
--sm24tat4xbACLACEClear

    sm24tat4xbACLACEClear OBJECT-TYPE
        SYNTAX      ActivateCmd
        MAX-ACCESS  read-write
        STATUS      current
        DESCRIPTION
            "Clear all ACE counters."
        ::= {     sm24tat4xbACLACE 1 }

--sm24tat4xbACLACETable

    sm24tat4xbACLACETable OBJECT-TYPE
        SYNTAX      SEQUENCE OF     SM24TAT4XBACLACEEntry
        MAX-ACCESS  not-accessible
        STATUS      current
        DESCRIPTION
            "Create ACL ACE entry. "
        ::= {     sm24tat4xbACLACE 2 }

    sm24tat4xbACLACEEntry OBJECT-TYPE
        SYNTAX      SM24TAT4XBACLACEEntry
        MAX-ACCESS  not-accessible
        STATUS      current
        DESCRIPTION
            "The ACLACE Table."
        INDEX    {     sm24tat4xbACLACEIndex  }
        ::= {     sm24tat4xbACLACETable 1 }

    SM24TAT4XBACLACEEntry         ::= SEQUENCE {
         sm24tat4xbACLACEIndex        Integer32,
         sm24tat4xbACLACEID            Integer32,
         sm24tat4xbACLACENextID        Integer32,
--        sm24tat4xbACLACELoopUp        AdminMode,
         sm24tat4xbACLACEIngressPort      DisplayString,
         sm24tat4xbACLACEPortPolicyNumber     Integer32,
         sm24tat4xbACLACEPortPolicyBitmask    Integer32,
         sm24tat4xbACLACEFrameType        INTEGER,
         sm24tat4xbACLACEAction        INTEGER,
         sm24tat4xbACLACEFilterPort        DisplayString,
         sm24tat4xbACLACEDenyPortRedirect     DisplayString,
         sm24tat4xbACLACERateLimiter      Integer32,
         sm24tat4xbACLACEMirror        AdminMode,
         sm24tat4xbACLACELogging          AdminMode,
         sm24tat4xbACLACEShutdown         AdminMode,
         sm24tat4xbACLACECounter          Counter32,
         sm24tat4xbACLACEVLAN8021QTagged      INTEGER,
         sm24tat4xbACLACEVLANVID          Integer32,
         sm24tat4xbACLACEVLANTagPriority      Integer32,
         sm24tat4xbACLACESMAC         DisplayString,
         sm24tat4xbACLACEDMACType         INTEGER,
         sm24tat4xbACLACEDMAC         DisplayString,
         sm24tat4xbACLACEEtherType        Integer32,
         sm24tat4xbACLACEArpOpCode        INTEGER,
         sm24tat4xbACLACEArpFlagsRequestReply INTEGER,
         sm24tat4xbACLACEArpFlagsArpSMac      INTEGER,
         sm24tat4xbACLACEArpFlagsRarpDmac     INTEGER,
         sm24tat4xbACLACEArpFlagsLength    INTEGER,
         sm24tat4xbACLACEArpFlagsIp        INTEGER,
         sm24tat4xbACLACEArpFlagsEthernet     INTEGER,
         sm24tat4xbACLACESIPType          INTEGER,
         sm24tat4xbACLACESIPIPAddress     IpAddress,
         sm24tat4xbACLACESIPIPMask        IpAddress,
         sm24tat4xbACLACEDIPType          INTEGER,
         sm24tat4xbACLACEDIPIPAddress     IpAddress,
         sm24tat4xbACLACEDIPIPMask        IpAddress,
         sm24tat4xbACLACEIPProtocol        INTEGER,
         sm24tat4xbACLACEIPProtocolValue      Integer32,
         sm24tat4xbACLACEIPFlagsTTL        INTEGER,
         sm24tat4xbACLACEIPFlagsFragment      INTEGER,
         sm24tat4xbACLACEIPFlagsOptions    INTEGER,
         sm24tat4xbACLACEICMPType         Integer32,
         sm24tat4xbACLACEICMPCode         Integer32,
         sm24tat4xbACLACESourcePort        DisplayString,
         sm24tat4xbACLACEDestPort         DisplayString,
         sm24tat4xbACLACETCPFlagsFin      INTEGER,
         sm24tat4xbACLACETCPFlagsSyn      INTEGER,
         sm24tat4xbACLACETCPFlagsRst      INTEGER,
         sm24tat4xbACLACETCPFlagsPsh      INTEGER,
         sm24tat4xbACLACETCPFlagsAck      INTEGER,
         sm24tat4xbACLACETCPFlagsUrg      INTEGER,
         sm24tat4xbACLACEIPv6SIPAddress    DisplayString,
         sm24tat4xbACLACEIPv6SIPBitmask    DisplayString,
         sm24tat4xbACLACEIPv6HopLimit     INTEGER,
         sm24tat4xbACLACESMACMask         DisplayString,
         sm24tat4xbACLACEDMACMask         DisplayString,
         sm24tat4xbACLACERowStatus        RowStatus
         }

    sm24tat4xbACLACEIndex OBJECT-TYPE
        SYNTAX      Integer32(1..256)
        MAX-ACCESS  not-accessible
        STATUS      current
        DESCRIPTION
            "The index. "
        ::= {     sm24tat4xbACLACEEntry 1 }

    sm24tat4xbACLACEID OBJECT-TYPE
        SYNTAX      Integer32(1..256)
        MAX-ACCESS  read-create
        STATUS      current
        DESCRIPTION
            "If the ACE ID is specified and an entry with this ACE ID
            already exists, the ACE will be modified. Otherwise, a
            new ACE will be added.
            range : 1 - 256. "
        ::= {     sm24tat4xbACLACEEntry 2 }

    sm24tat4xbACLACENextID OBJECT-TYPE
        SYNTAX      Integer32 (0..256)
        MAX-ACCESS  read-create
        STATUS      current
        DESCRIPTION
            "If the next ACE ID is non zero, the ACE will be placed
            before this ACE in the list. If the next ACE ID is zero,
            the ACE will be placed last in the list.
            range : 0 - 256. "
        ::= {     sm24tat4xbACLACEEntry 3 }

--    sm24tat4xbACLACELoopUp OBJECT-TYPE
--        SYNTAX      AdminMode
--        MAX-ACCESS  read-create
--        STATUS      current
--        DESCRIPTION
--            "Specify the second lookup operation of the ACE."
--        ::= {     sm24tat4xbACLACEEntry 4 }
--
    sm24tat4xbACLACEIngressPort OBJECT-TYPE
        SYNTAX      DisplayString
        MAX-ACCESS  read-create
        STATUS      current
        DESCRIPTION
            "Indicates the ingress port of the ACE. Possible values are:
            0: All,The ACE will match all ingress port.
            Port n: The ACE will match a specific ingress port."
        ::= {     sm24tat4xbACLACEEntry 5 }

    sm24tat4xbACLACEPortPolicyNumber OBJECT-TYPE
        SYNTAX      Integer32(0..127)
        MAX-ACCESS  read-create
        STATUS      current
        DESCRIPTION
            "policy value.
            range : 0 - 127.
            0: Any."
        ::= {     sm24tat4xbACLACEEntry 6 }

    sm24tat4xbACLACEPortPolicyBitmask OBJECT-TYPE
        SYNTAX      Integer32(0..127)
        MAX-ACCESS  read-create
        STATUS      current
        DESCRIPTION
            "When 'Specific' is selected for the policy filter,
            you can enter a specific policy bitmask.
            range : 0 - 127, 0: no data."
        ::= {     sm24tat4xbACLACEEntry 7 }

    sm24tat4xbACLACEFrameType OBJECT-TYPE
        SYNTAX      INTEGER {    any(0), etype(1), arp(2),
                    ipv4(3), ipv6(4) }
        MAX-ACCESS  read-create
        STATUS      current
        DESCRIPTION
            "Select the frame type for this ACE.
            When change the type Related oid will set default.
            0: any,
            1: etype,
            2: arp,
            3: ipv4,
            4: ipv6."
        ::= {     sm24tat4xbACLACEEntry 8 }

    sm24tat4xbACLACEAction OBJECT-TYPE
        SYNTAX      INTEGER { deny(0), permit(1), filter(2) }
        MAX-ACCESS  read-create
        STATUS      current
        DESCRIPTION
            "0: Deny
				    1: Permit
					2: Filter"
        ::= {     sm24tat4xbACLACEEntry 9 }

    sm24tat4xbACLACEFilterPort OBJECT-TYPE
        SYNTAX      DisplayString
        MAX-ACCESS  read-create
        STATUS      current
        DESCRIPTION
            "When 'Action' is 'Filter' can set.
            0: Disable,
            Port n: The ACE applies to this port number, where n is
            the number of the switch port.
            range: 0 - Port number.
            "
        ::= {     sm24tat4xbACLACEEntry 10 }

    sm24tat4xbACLACEDenyPortRedirect OBJECT-TYPE
        SYNTAX      DisplayString
        MAX-ACCESS  read-create
        STATUS      current
        DESCRIPTION
            "Frames that hit the ACE are redirected to the port
            number specified here.Disabled,indicates that the port
            redirect operation is disabled.
            When 'Action' is 'Deny' can set.
            0: disabled,
            Port no: The ACE applies to this port number, where n is
            the number of the switch port."
        ::= {     sm24tat4xbACLACEEntry 11 }

    sm24tat4xbACLACERateLimiter OBJECT-TYPE
        SYNTAX      Integer32(0..16)
        MAX-ACCESS  read-create
        STATUS      current
        DESCRIPTION
            "default: 0,
            0: Disable
            range : 0 - 16 "
        ::= {     sm24tat4xbACLACEEntry 12 }

    sm24tat4xbACLACEMirror OBJECT-TYPE
        SYNTAX      AdminMode
        MAX-ACCESS  read-create
        STATUS      current
        DESCRIPTION
            "default: 0,
            0: disable - Frames matching the ACE are not mirrored.
            1: enable - Frames matching the ACE are mirrored.
            "
        ::= {     sm24tat4xbACLACEEntry 13 }

    sm24tat4xbACLACELogging OBJECT-TYPE
        SYNTAX      AdminMode
        MAX-ACCESS  read-create
        STATUS      current
        DESCRIPTION
            "default: 0,
            0: disable - Frames matching the ACE are not logged.
            1: enable - Frames matching the ACE are stored in the
            system log."
        ::= {     sm24tat4xbACLACEEntry 14 }

    sm24tat4xbACLACEShutdown OBJECT-TYPE
        SYNTAX      AdminMode
        MAX-ACCESS  read-create
        STATUS      current
        DESCRIPTION
            "default: 0,
            0: disable - Port shut down is disabled for the AC.
            1: enable - If a frame matches the ACE, the ingress port
            will be disabled."
        ::= {     sm24tat4xbACLACEEntry 15 }

    sm24tat4xbACLACECounter OBJECT-TYPE
        SYNTAX      Counter32
        MAX-ACCESS  read-only
        STATUS      current
        DESCRIPTION
            "The counter indicates the number of times the ACE was
            hit by a frame. "
        ::= {     sm24tat4xbACLACEEntry 16 }

    sm24tat4xbACLACEVLAN8021QTagged OBJECT-TYPE
        SYNTAX      INTEGER { disable(0), enable(1), any(2) }
        MAX-ACCESS  read-create
        STATUS      current
        DESCRIPTION
            "Specify whether frames can hit the action according to
            the 802.1Q tagged.
            default: 2,
            0: disable - Untagged frame only.
            1: enable - Tagged frame only.
            2: Any - Any value is allowed.
            "
        ::= {     sm24tat4xbACLACEEntry 17 }

    sm24tat4xbACLACEVLANVID OBJECT-TYPE
        SYNTAX      Integer32(0..4095)
        MAX-ACCESS  read-create
        STATUS      current
        DESCRIPTION
            "Specify the VLAN ID filter for this ACE.
            The vid can't be set when 802.1Q Tagged is disabled.
            default: 0,
            0: Any - No VLAN ID filter is specified.
            range : 0 - 4095 "
        ::= {     sm24tat4xbACLACEEntry 18 }

    sm24tat4xbACLACEVLANTagPriority OBJECT-TYPE
        SYNTAX      Integer32(0..14)
        MAX-ACCESS  read-create
        STATUS      current
        DESCRIPTION
            "Specify the tag priority for this ACE.
            The tag priority can't be set when 802.1Q Tagged is disabled.
            range: 0-14
					0:0
					1:1
					2:2
					3:3
					4:4
					5:5
					6:6
					7:7
					8:0-1
					9:2-3
					10:4-5
					11:6-7
					12:0-3
					13:4-7
					14:Any
					"
        ::= {     sm24tat4xbACLACEEntry 19 }

    sm24tat4xbACLACESMAC OBJECT-TYPE
        SYNTAX      DisplayString
        MAX-ACCESS  read-create
        STATUS      current
        DESCRIPTION
            "Configure source MAC address for this ACE.
            <mac-address>: A frame that hits this ACE matches this
            source MAC address value. xx-xx-xx-xx-xx-xx.
            Any: Don't care."
        ::= {    sm24tat4xbACLACEEntry 20 }

    sm24tat4xbACLACEDMACType OBJECT-TYPE
        SYNTAX      INTEGER { any(0), mc(1), bc(2), uc(3) ,
                     macAddress(4) , noData(5) }
        MAX-ACCESS  read-create
        STATUS      current
        DESCRIPTION
            "DMAC Type.
            default: 0,
            0: Any - Don't care.
            1: Multicast - Frame must be multicast.
            2: Broadcast - Frame must be broadcast.
            3: Unicast - Frame must be unicast.
            4: mac address.
            5: no data."
        DEFVAL  { any }
        ::= {    sm24tat4xbACLACEEntry 21 }

    sm24tat4xbACLACEDMAC OBJECT-TYPE
        SYNTAX      DisplayString
        MAX-ACCESS  read-create
        STATUS      current
        DESCRIPTION
            "Configure destination MAC address for this ACE.
            <mac-address>: A frame that hits this ACE matches this
            destination MAC address value. xx-xx-xx-xx-xx-xx."
        ::= {     sm24tat4xbACLACEEntry 22 }

    sm24tat4xbACLACEEtherType OBJECT-TYPE
        SYNTAX      Integer32(-1..65535)
        MAX-ACCESS  read-create
        STATUS      current
        DESCRIPTION
            "0: Any
				    range : 0, or 1536(0x0600) - 65535(0xffff) but excluding 0x0800(IPv4) 0x0806(ARP) and
            0x86DD(IPv6).
            -1: No data. "
        ::= {     sm24tat4xbACLACEEntry 23 }

    sm24tat4xbACLACEArpOpCode OBJECT-TYPE
        SYNTAX      INTEGER { any(0), arp(1), rarp(2),
                     other(3), noData(4) }
        MAX-ACCESS  read-create
        STATUS      current
        DESCRIPTION
            "Configure ARP opcode for this ACE.
            default: 0,
            0: Any - Don't care.
            1: arp.
            2: rarp.
            3: other.
            4: No data."
        DEFVAL  { any }
        ::= {     sm24tat4xbACLACEEntry 24 }

    sm24tat4xbACLACEArpFlagsRequestReply OBJECT-TYPE
        SYNTAX      INTEGER { reply(0), request(1), any(2), noData(3)}
        MAX-ACCESS  read-create
        STATUS      current
        DESCRIPTION
            "Specify the available ARP/RARP opcode (OP) flag for this ACE.
            default: 2,
            0: Frame must have ARP Reply or RARP Reply OP flag.
            1: Frame must have ARP Request or RARP Request OP flag set.
            2: Any - Don't care.
            3: No data."
        DEFVAL  { any }
        ::= {     sm24tat4xbACLACEEntry 25 }

    sm24tat4xbACLACEArpFlagsArpSMac OBJECT-TYPE
        SYNTAX      INTEGER { notEqualSMAC(0), equalSMAC(1),
                     any(2), noData(3)}
        MAX-ACCESS  read-create
        STATUS      current
        DESCRIPTION
            "Specify whether frames can hit the action according to their
            sender hardware address field (SHA) settings.
            default: 2,
            0: ARP frames where SHA is not equal to the SMAC address.
            1: ARP frames where SHA is equal to the SMAC address.
            2: Any - Don't care.
            3: No data."
        DEFVAL  { any }
        ::= {     sm24tat4xbACLACEEntry 26 }

    sm24tat4xbACLACEArpFlagsRarpDmac OBJECT-TYPE
        SYNTAX      INTEGER { notEqualDMAC(0), equalDMAC(1),
                     any(2), noData(3)}
        MAX-ACCESS  read-create
        STATUS      current
        DESCRIPTION
            "Specify whether frames can hit the action according to
            their target hardware address field (THA) settings.
            default: 2,
            0: RARP frames where THA is not equal to the DMAC address.
            1: RARP frames where THA is equal to the DMAC address.
            2: Any - Don't care.
            3: No data."
        DEFVAL  { any }
        ::= {     sm24tat4xbACLACEEntry 27 }

    sm24tat4xbACLACEArpFlagsLength OBJECT-TYPE
        SYNTAX      INTEGER { notEqualEthIpV4 (0), equalEthIpV4(1),
                     any(2), noData(3)}
        MAX-ACCESS  read-create
        STATUS      current
        DESCRIPTION
            "Specify whether frames can hit the action according to
            their ARP/RARP hardware address length (HLN) and protocol
            address length (PLN) settings.
            default: 2,
            0: ARP/RARP frames where the HLN is not equal to
            Ethernet(0x06) or the (PLN) is not equal to IPv4(0x04).
            1: ARP/RARP frames where the HLN is equal to Ethernet (0x06)
            and the (PLN) is equal to IPv4(0x04).
            2: Any - Don't care.
            3: No data."
        DEFVAL  { any }
        ::= {     sm24tat4xbACLACEEntry 28 }

    sm24tat4xbACLACEArpFlagsIp OBJECT-TYPE
        SYNTAX      INTEGER { notEqualEth(0), equalEth(1),
                     any(2), noData(3)}
        MAX-ACCESS  read-create
        STATUS      current
        DESCRIPTION
            "Specify whether frames can hit the action according to
            their ARP/RARP hardware address space (HRD) settings.
            default: 2,
            0: ARP/RARP frames where the HLD is not equal to Ethernet(1).
            1: ARP/RARP frames where the HLD is equal to Ethernet(1).
            2: Any - Don't care.
            3: No data."
        DEFVAL  { any }
        ::= {     sm24tat4xbACLACEEntry 29 }

    sm24tat4xbACLACEArpFlagsEthernet OBJECT-TYPE
        SYNTAX      INTEGER { notEqualIp(0), equalIp(1),
                     any(2), noData(3)}
        MAX-ACCESS  read-create
        STATUS      current
        DESCRIPTION
            "Specify whether frames can hit the action
            according to their ARP/RARP protocol address space (PRO) settings.
            default: 2,
            0: ARP/RARP frames where the PRO is not equal to IP\n(0x800).
            1: ARP/RARP frames where the PRO is equal to IP(0x800).
            2: Any - Don't care.
            3: No data."
        DEFVAL  { any }
        ::= {     sm24tat4xbACLACEEntry 30 }

    sm24tat4xbACLACESIPType OBJECT-TYPE
        SYNTAX      INTEGER { any(0), ip(1), network(2), noData(3) }
        MAX-ACCESS  read-create
        STATUS      current
        DESCRIPTION
            "Configure source IP address for this ACE.
            default: 0,
            0: Any - Don't care.
            1: IP Address.
            2: Network.
            3: No data."
        DEFVAL  { any }
        ::= {     sm24tat4xbACLACEEntry 31 }

    sm24tat4xbACLACESIPIPAddress OBJECT-TYPE
        SYNTAX      IpAddress
        MAX-ACCESS  read-create
        STATUS      current
        DESCRIPTION
            "A frame that hits this ACE matches this source IP address
            value."
        ::= {     sm24tat4xbACLACEEntry 32 }

    sm24tat4xbACLACESIPIPMask OBJECT-TYPE
        SYNTAX      IpAddress
        MAX-ACCESS  read-create
        STATUS      current
        DESCRIPTION
            "Specific sender IP mask in dotted decimal notation."
        ::= {     sm24tat4xbACLACEEntry 33 }

    sm24tat4xbACLACEDIPType OBJECT-TYPE
        SYNTAX      INTEGER { any(0), ip(1), network(2), noData(3) }
        MAX-ACCESS  read-create
        STATUS      current
        DESCRIPTION
            "Configure destination IP address for this ACE.
            default: 0,
            0: Any - Don't care.
            1: IP Address.
            2: Network.
            3: No data."
        DEFVAL  { any }
        ::= {     sm24tat4xbACLACEEntry 34 }

    sm24tat4xbACLACEDIPIPAddress OBJECT-TYPE
        SYNTAX      IpAddress
        MAX-ACCESS  read-create
        STATUS      current
        DESCRIPTION
            "A frame that hits this ACE matches this destination IP
            address value."
        ::= {     sm24tat4xbACLACEEntry 35 }

    sm24tat4xbACLACEDIPIPMask OBJECT-TYPE
        SYNTAX      IpAddress
        MAX-ACCESS  read-create
        STATUS      current
        DESCRIPTION
            "Specific sender IP mask in dotted decimal notation."
        ::= {     sm24tat4xbACLACEEntry 36 }

    sm24tat4xbACLACEIPProtocol OBJECT-TYPE
        SYNTAX      INTEGER{ any(0), icmp(1), udp(2), tcp(3),
                    other(4), noData(5)}
        MAX-ACCESS  read-create
        STATUS      current
        DESCRIPTION
            "Specify the IP protocol filter for this ACE.
            default: 0,
            0: Any,
            1: ICMP,
            2: UDP,
            3: TCP,
            4: Other,
            5: no data."
        DEFVAL  { any }
        ::= {     sm24tat4xbACLACEEntry 37 }

    sm24tat4xbACLACEIPProtocolValue OBJECT-TYPE
        SYNTAX      Integer32(0..256)
        MAX-ACCESS  read-create
        STATUS      current
        DESCRIPTION
            "Configure IP protocol value for this ACE when IP Protocol
            is 'other'.
            default: 256,
            256: No data.
            range : 0 - 256"
        ::= {     sm24tat4xbACLACEEntry 38 }

    sm24tat4xbACLACEIPFlagsTTL OBJECT-TYPE
        SYNTAX      INTEGER { nonZero(0), zero(1), any(2), noData(3) }
        MAX-ACCESS  read-create
        STATUS      current
        DESCRIPTION
            "Specify the Time-to-Live settings for this ACE.
            default: 0,
            0: zero,
            1: Non-Zero
            2: Any,,
            3: No data."
        DEFVAL  { nonZero }
        ::= {     sm24tat4xbACLACEEntry 39 }

    sm24tat4xbACLACEIPFlagsFragment OBJECT-TYPE
        SYNTAX      INTEGER{yes(0), no(1), any(2), noData(3)}
        MAX-ACCESS  read-create
        STATUS      current
        DESCRIPTION
            "Specify the fragment offset settings for this ACE.
            default: 2,
            0: No,
            1: Yes,
            2: Any,
            3: No data."
        DEFVAL  { any }
        ::= {     sm24tat4xbACLACEEntry 40 }

    sm24tat4xbACLACEIPFlagsOptions OBJECT-TYPE
        SYNTAX      INTEGER{yes(0), no(1), any(2),  noData(3)}
        MAX-ACCESS  read-create
        STATUS      current
        DESCRIPTION
            "Specify the options flag setting for this ACE.
            default: 2,
            0: No,
            1: Yes,
            2: Any,
            3: No data."
        DEFVAL  { any }
        ::= {     sm24tat4xbACLACEEntry 41 }

    sm24tat4xbACLACEICMPType OBJECT-TYPE
        SYNTAX      Integer32(0..257)
        MAX-ACCESS  read-create
        STATUS      current
        DESCRIPTION
            "Configure ICMP type for this ACE.
            default: 256,
            256: Any - Don't care.
            257: No data.
            range : 0 - 257."
        ::= { sm24tat4xbACLACEEntry 42 }

    sm24tat4xbACLACEICMPCode OBJECT-TYPE
        SYNTAX      Integer32(0..257)
        MAX-ACCESS  read-create
        STATUS      current
        DESCRIPTION
            "Configure ICMP code for this ACE.
            default: 256,
            256: Any - Don't care.
            257: No data.
            range : 0 - 257."
        ::= {     sm24tat4xbACLACEEntry 43 }

    sm24tat4xbACLACESourcePort OBJECT-TYPE
        SYNTAX      DisplayString
        MAX-ACCESS  read-create
        STATUS      current
        DESCRIPTION
            "Configure Source UDP/TCP port range for this ACE.
            default: any,
            specific: 0~65535,
            range : 0 - 65535."
        ::= {     sm24tat4xbACLACEEntry 44 }

    sm24tat4xbACLACEDestPort OBJECT-TYPE
        SYNTAX      DisplayString
        MAX-ACCESS  read-create
        STATUS      current
        DESCRIPTION
            "Configure Destination UDP/TCP port range for this ACE.
            default: any,
            specific: 0~65535,
            range : 0 - 65535."
        ::= {     sm24tat4xbACLACEEntry 45 }

    sm24tat4xbACLACETCPFlagsFin OBJECT-TYPE
        SYNTAX      INTEGER { unset(0), set(1), any(2), noData(3) }
        MAX-ACCESS  read-create
        STATUS      current
        DESCRIPTION
            "Configure TCP (FIN) flags for this ACE.
            default: 2,
            0: TCP frames where the FIN field is unset.
            1: TCP frames where the FIN field is set.
            2: Any - Don't care.
            3: No data."
        DEFVAL  { any }
        ::= {     sm24tat4xbACLACEEntry 46 }

    sm24tat4xbACLACETCPFlagsSyn OBJECT-TYPE
        SYNTAX      INTEGER { unset(0), set(1), any(2), noData(3) }
        MAX-ACCESS  read-create
        STATUS      current
        DESCRIPTION
            "Configure TCP (SYN) flags for this ACE.
            default: 2,
            0: TCP frames where the SYN field is unset.
            1: TCP frames where the SYN field is set.
            2: Any - Don't care.
            3: No data."
        DEFVAL  { any }
        ::= {     sm24tat4xbACLACEEntry 47 }

    sm24tat4xbACLACETCPFlagsRst OBJECT-TYPE
        SYNTAX      INTEGER { unset(0), set(1), any(2), noData(3) }
        MAX-ACCESS  read-create
        STATUS      current
        DESCRIPTION
            "Configure TCP (RST) flags for this ACE.
            default: 2,
            0: TCP frames where the RST field is unset.
            1: TCP frames where the RST field is set.
            2: Any - Don't care.
            3: No data."
        DEFVAL  { any }
        ::= {     sm24tat4xbACLACEEntry 48 }

    sm24tat4xbACLACETCPFlagsPsh OBJECT-TYPE
        SYNTAX      INTEGER { unset(0), set(1), any(2), noData(3) }
        MAX-ACCESS  read-create
        STATUS      current
        DESCRIPTION
            "Configure TCP (PSH) flags for this ACE.
            default: 2,
            0: TCP frames where the PSH field is unset.
            1: TCP frames where the PSH field is set.
            2: Any - Don't care.
            3: No data."
        DEFVAL  { any }
        ::= {     sm24tat4xbACLACEEntry 49 }

    sm24tat4xbACLACETCPFlagsAck OBJECT-TYPE
        SYNTAX      INTEGER { unset(0), set(1), any(2), noData(3) }
        MAX-ACCESS  read-create
        STATUS      current
        DESCRIPTION
            "Configure TCP (ACK) flags for this ACE.
            default: 2,
            0: TCP frames where the ACK field is unset.
            1: TCP frames where the ACK field is set.
            2: Any - Don't care.
            3: No data."
        DEFVAL  { any }
        ::= {     sm24tat4xbACLACEEntry 50 }

    sm24tat4xbACLACETCPFlagsUrg OBJECT-TYPE
        SYNTAX      INTEGER { unset(0), set(1), any(2), noData(3) }
        MAX-ACCESS  read-create
        STATUS      current
        DESCRIPTION
            "Configure TCP (URG) flags for this ACE.
            default: 2,
            0: TCP frames where the URG field is unset.
            1: TCP frames where the URG field is set.
            2: Any - Don't care.
            3: No data."
        DEFVAL  { any }
        ::= {     sm24tat4xbACLACEEntry 51 }

    sm24tat4xbACLACEIPv6SIPAddress OBJECT-TYPE
        SYNTAX      DisplayString
        MAX-ACCESS  read-create
        STATUS      current
        DESCRIPTION
            "When 'Specific' is selected for the source IPv6 filter,
            you can enter a specific SIPv6 address.
            The field only supported last 32 bits for IPv6 address. "
        ::= {     sm24tat4xbACLACEEntry 52 }

    sm24tat4xbACLACEIPv6SIPBitmask OBJECT-TYPE
        SYNTAX      DisplayString
        MAX-ACCESS  read-create
        STATUS      current
        DESCRIPTION
            "When 'Specific' is selected for the source IPv6 filter,
            you can enter a specific SIPv6 mask.
            The field only supported last 32 bits for IPv6 address. "
        ::= {     sm24tat4xbACLACEEntry 53 }

    sm24tat4xbACLACEIPv6HopLimit OBJECT-TYPE
        SYNTAX      INTEGER { unset(0), set(1), any(2), noData(3) }
        MAX-ACCESS  read-create
        STATUS      current
        DESCRIPTION
            "Specify the hop limit settings for this ACE.
            default: 2,
            0: Where the Hop Limit field is unset.
            1: Where the Hop Limit field is set.
            2: Any - Don't care,
            3: No data."
        DEFVAL  { any }
        ::= {     sm24tat4xbACLACEEntry 54 }

    sm24tat4xbACLACESMACMask OBJECT-TYPE
        SYNTAX      DisplayString
        MAX-ACCESS  read-create
        STATUS      current
        DESCRIPTION
            "Configure source MAC address mask for this ACE.
            <mac-address>: A frame that hits this ACE matches this
            source MAC address value. xx-xx-xx-xx-xx-xx."
        ::= {    sm24tat4xbACLACEEntry 56 }

    sm24tat4xbACLACEDMACMask OBJECT-TYPE
        SYNTAX      DisplayString
        MAX-ACCESS  read-create
        STATUS      current
        DESCRIPTION
            "Configure destination MAC address mask for this ACE.
            <mac-address>: A frame that hits this ACE matches this
            destination MAC address value. xx-xx-xx-xx-xx-xx."
        ::= {     sm24tat4xbACLACEEntry 57 }

    sm24tat4xbACLACERowStatus OBJECT-TYPE
        SYNTAX      RowStatus
        MAX-ACCESS  read-create
        STATUS      current
        DESCRIPTION
            "This object indicates the status of this entry, and is
            used to create/delete entries.  Any object in an entry of
            this table may be modified while the value of the
            corresponding instance of this object is active(1).
            createAndGo, notReady not supported."
        ::= {     sm24tat4xbACLACEEntry 58 }

--
-- =======================================================================================================================
-- Start sm24tat4xbACLStatus group
-- =======================================================================================================================
--sm24tat4xbACLStatusTable

    sm24tat4xbACLStatusTable OBJECT-TYPE
        SYNTAX      SEQUENCE OF     SM24TAT4XBACLStatusEntry
        MAX-ACCESS  not-accessible
        STATUS      current
        DESCRIPTION
            " ACL ACE Status entry. "
        ::= {     sm24tat4xbACL 4 }

    sm24tat4xbACLStatusEntry OBJECT-TYPE
        SYNTAX      SM24TAT4XBACLStatusEntry
        MAX-ACCESS  not-accessible
        STATUS      current
        DESCRIPTION
            "The ACL Status Entry."
        INDEX    {    sm24tat4xbACLStatusIndex  }
        ::= {     sm24tat4xbACLStatusTable 1 }

    SM24TAT4XBACLStatusEntry         ::= SEQUENCE {
         sm24tat4xbACLStatusIndex      Integer32,
         sm24tat4xbACLStatusUser        DisplayString,
         sm24tat4xbACLStatusID         Integer32,
         sm24tat4xbACLStatusIngressPort    DisplayString,
         sm24tat4xbACLStatusFrameType      DisplayString,
         sm24tat4xbACLStatusAction     DisplayString,
         sm24tat4xbACLStatusRateLimiter    DisplayString,
         sm24tat4xbACLStatusPortRedirect    DisplayString,
         sm24tat4xbACLStatusMirror     DisplayString,
         sm24tat4xbACLStatusCPU        DisplayString,
         sm24tat4xbACLStatusCPUOnce    DisplayString,
         sm24tat4xbACLStatusCounter    Counter32,
         sm24tat4xbACLStatusConflict    DisplayString
         }

    sm24tat4xbACLStatusIndex OBJECT-TYPE
        SYNTAX      Integer32(1..256)
        MAX-ACCESS  not-accessible
        STATUS      current
        DESCRIPTION
            "The ACL status index. "
        ::= {     sm24tat4xbACLStatusEntry 1 }

    sm24tat4xbACLStatusUser OBJECT-TYPE
        SYNTAX      DisplayString
        MAX-ACCESS  read-only
        STATUS      current
        DESCRIPTION
            "Indicates the ACL user.
            S : Static,
            IPMG : IP Management,
            IPSG : IP Source Guard,
            IPMC : IPMC,
            ARPI : Arp Inspection,
            UPnP : UPnP,
            DHCP : DHCP. "
        ::= {     sm24tat4xbACLStatusEntry 2 }

    sm24tat4xbACLStatusID OBJECT-TYPE
        SYNTAX      Integer32(1..256)
        MAX-ACCESS  read-only
        STATUS      current
        DESCRIPTION
            "ACE ID.
            range : 1 - 256. "
        ::= {     sm24tat4xbACLStatusEntry 3 }

    sm24tat4xbACLStatusIngressPort OBJECT-TYPE
        SYNTAX      DisplayString
        MAX-ACCESS  read-only
        STATUS      current
        DESCRIPTION
            "Indicates the ingress port of the ACE. Possible values are:
            All: The ACE will match all ingress port.
            Port: The ACE will match a specific ingress port. "
        ::= {     sm24tat4xbACLStatusEntry 4 }

    sm24tat4xbACLStatusFrameType OBJECT-TYPE
        SYNTAX      DisplayString
        MAX-ACCESS  read-only
        STATUS      current
        DESCRIPTION
            "Indicates the frame type of the ACE.
            Any: The ACE will match any frame type.
            EType: The ACE will match Ethernet Type frames.
            Note that an Ethernet Type based ACE will not get matched
            by IP and ARP frames.
            ARP: The ACE will match ARP/RARP frames.
            IPv4: The ACE will match all IPv4 frames.
            IPv4/ICMP: The ACE will match IPv4 frames with ICMP protocol.
            IPv4/UDP: The ACE will match IPv4 frames with UDP protocol.
            IPv4/TCP: The ACE will match IPv4 frames with TCP protocol.
            IPv4/Other: The ACE will match IPv4 frames, which are not
            ICMP/UDP/TCP.
            IPv6: The ACE will match all IPv6 standard frames. "
        ::= {     sm24tat4xbACLStatusEntry 5 }

    sm24tat4xbACLStatusAction OBJECT-TYPE
        SYNTAX      DisplayString
        MAX-ACCESS  read-only
        STATUS      current
        DESCRIPTION
            "Indicates the forwarding action of the ACE. "
        ::= {     sm24tat4xbACLStatusEntry 6 }

    sm24tat4xbACLStatusRateLimiter OBJECT-TYPE
        SYNTAX      DisplayString
        MAX-ACCESS  read-only
        STATUS      current
        DESCRIPTION
            "Indicates the rate limiter number of the ACE. "
        ::= {     sm24tat4xbACLStatusEntry 7 }

    sm24tat4xbACLStatusPortRedirect OBJECT-TYPE
        SYNTAX      DisplayString
        MAX-ACCESS  read-only
        STATUS      current
        DESCRIPTION
            "Indicates the port redirect operation of the ACE.
            Frames matching the ACE are redirected to the port number. "
        ::= {     sm24tat4xbACLStatusEntry 8 }

    sm24tat4xbACLStatusMirror OBJECT-TYPE
        SYNTAX      DisplayString
        MAX-ACCESS  read-only
        STATUS      current
        DESCRIPTION
            "Specify the mirror operation of this port."
        ::= {     sm24tat4xbACLStatusEntry 9 }

    sm24tat4xbACLStatusCPU OBJECT-TYPE
        SYNTAX      DisplayString
        MAX-ACCESS  read-only
        STATUS      current
        DESCRIPTION
            "Forward packet that matched the specific ACE to CPU. "
        ::= {     sm24tat4xbACLStatusEntry 10 }

    sm24tat4xbACLStatusCPUOnce OBJECT-TYPE
        SYNTAX      DisplayString
        MAX-ACCESS  read-only
        STATUS      current
        DESCRIPTION
            "Forward first packet that matched the specific ACE to CPU. "
        ::= {     sm24tat4xbACLStatusEntry 11 }

    sm24tat4xbACLStatusCounter OBJECT-TYPE
        SYNTAX      Counter32
        MAX-ACCESS  read-only
        STATUS      current
        DESCRIPTION
            "The counter indicates the number of times the ACE was hit
            by a frame. "
        ::= {     sm24tat4xbACLStatusEntry 12 }

    sm24tat4xbACLStatusConflict OBJECT-TYPE
        SYNTAX      DisplayString
        MAX-ACCESS  read-only
        STATUS      current
        DESCRIPTION
            "Indicates the hardware status of the specific ACE.
            The specific ACE is not applied to the hardware due to
            hardware limitations. "
        ::= {     sm24tat4xbACLStatusEntry 13 }


-- =======================================================================================================================
-- sm24tat4xbAclConformance
-- =======================================================================================================================
sm24tat4xbAclConformance OBJECT IDENTIFIER ::= { sm24tat4xbACL 200 }

sm24tat4xbAclCompliances OBJECT IDENTIFIER ::= { sm24tat4xbAclConformance 1 }

sm24tat4xbAclGroups    OBJECT IDENTIFIER ::= { sm24tat4xbAclConformance 2 }

sm24tat4xbACLPortConfGroup OBJECT-GROUP
    OBJECTS {
        -- sm24tat4xbACLPortConfTable
         sm24tat4xbACLPortConfPolicyID,
         sm24tat4xbACLPortConfAction,
         sm24tat4xbACLPortConfRateLimiterID,
         sm24tat4xbACLPortConfPortRedirect,
         sm24tat4xbACLPortConfMirror,
         sm24tat4xbACLPortConfLogging,
         sm24tat4xbACLPortConfShutdown,
         sm24tat4xbACLPortConfState,
         sm24tat4xbACLPortConfCounter
        }
     STATUS  current
     DESCRIPTION
        "The collection of objects which are used to indicate
        sm24tat4xb ACL information."
    ::= { sm24tat4xbAclGroups 1 }

sm24tat4xbACLRateLimiterGroup OBJECT-GROUP
    OBJECTS {
        -- sm24tat4xbACLRateLimiterTable
         sm24tat4xbACLRateLimiterRate,
         sm24tat4xbACLRateLimiterUnit
        }
     STATUS  current
     DESCRIPTION
        "The collection of objects which are used to indicate
        sm24tat4xb ACL information."
    ::= { sm24tat4xbAclGroups 2 }

sm24tat4xbACLACEGroup OBJECT-GROUP
    OBJECTS {
        -- sm24tat4xbACLACEClear
         sm24tat4xbACLACEClear,

        -- sm24tat4xbACLACETable
         sm24tat4xbACLACEID,
         sm24tat4xbACLACENextID,
--        sm24tat4xbACLACELoopUp,
         sm24tat4xbACLACEIngressPort,
         sm24tat4xbACLACEPortPolicyNumber,
         sm24tat4xbACLACEPortPolicyBitmask,
         sm24tat4xbACLACEFrameType,
         sm24tat4xbACLACEAction,
         sm24tat4xbACLACEFilterPort,
         sm24tat4xbACLACEDenyPortRedirect,
         sm24tat4xbACLACERateLimiter,
         sm24tat4xbACLACEMirror,
         sm24tat4xbACLACELogging,
         sm24tat4xbACLACEShutdown,
         sm24tat4xbACLACECounter,
         sm24tat4xbACLACEVLAN8021QTagged,
         sm24tat4xbACLACEVLANVID,
         sm24tat4xbACLACEVLANTagPriority,
         sm24tat4xbACLACESMAC,
         sm24tat4xbACLACEDMACType,
         sm24tat4xbACLACEDMAC,
         sm24tat4xbACLACEEtherType,
         sm24tat4xbACLACEArpOpCode,
         sm24tat4xbACLACEArpFlagsRequestReply,
         sm24tat4xbACLACEArpFlagsArpSMac,
         sm24tat4xbACLACEArpFlagsRarpDmac,
         sm24tat4xbACLACEArpFlagsLength,
         sm24tat4xbACLACEArpFlagsIp,
         sm24tat4xbACLACEArpFlagsEthernet,
         sm24tat4xbACLACESIPType,
         sm24tat4xbACLACESIPIPAddress,
         sm24tat4xbACLACESIPIPMask,
         sm24tat4xbACLACEDIPType,
         sm24tat4xbACLACEDIPIPAddress,
         sm24tat4xbACLACEDIPIPMask,
         sm24tat4xbACLACEIPProtocol,
         sm24tat4xbACLACEIPProtocolValue,
         sm24tat4xbACLACEIPFlagsTTL,
         sm24tat4xbACLACEIPFlagsFragment,
         sm24tat4xbACLACEIPFlagsOptions,
         sm24tat4xbACLACEICMPType,
         sm24tat4xbACLACEICMPCode,
         sm24tat4xbACLACESourcePort,
         sm24tat4xbACLACEDestPort,
         sm24tat4xbACLACETCPFlagsFin,
         sm24tat4xbACLACETCPFlagsSyn,
         sm24tat4xbACLACETCPFlagsRst,
         sm24tat4xbACLACETCPFlagsPsh,
         sm24tat4xbACLACETCPFlagsAck,
         sm24tat4xbACLACETCPFlagsUrg,
         sm24tat4xbACLACEIPv6SIPAddress,
         sm24tat4xbACLACEIPv6SIPBitmask,
         sm24tat4xbACLACEIPv6HopLimit,
         sm24tat4xbACLACERowStatus
        }
     STATUS  current
     DESCRIPTION
        "The collection of objects which are used to indicate
        sm24tat4xb ACL information."
    ::= { sm24tat4xbAclGroups 3 }

sm24tat4xbACLStatusGroup OBJECT-GROUP
    OBJECTS {
        -- sm24tat4xbACLStatusTable
         sm24tat4xbACLStatusUser,
         sm24tat4xbACLStatusID,
         sm24tat4xbACLStatusIngressPort,
         sm24tat4xbACLStatusFrameType,
         sm24tat4xbACLStatusAction,
         sm24tat4xbACLStatusRateLimiter,
         sm24tat4xbACLStatusPortRedirect,
         sm24tat4xbACLStatusMirror,
         sm24tat4xbACLStatusCPU,
         sm24tat4xbACLStatusCPUOnce,
         sm24tat4xbACLStatusCounter,
         sm24tat4xbACLStatusConflict
        }
     STATUS  current
     DESCRIPTION
        "The collection of objects which are used to indicate
        sm24tat4xb ACL information."
    ::= { sm24tat4xbAclGroups 4 }


-- =======================================================================================================================
-- =======================================================================================================================
 -- RowStatus Info:  createAndGo, notReady not supported.
-- =======================================================================================================================
-- Textual Conventions for the sm24tat4xb Qos Mib
-- =======================================================================================================================
--
sm24tat4xbQosConf            OBJECT IDENTIFIER ::= { sm24tat4xbConfiguration 10 }
    sm24tat4xbQos            OBJECT IDENTIFIER    ::= { sm24tat4xbQosConf  1  }
    sm24tat4xbQosPortClassification      OBJECT IDENTIFIER    ::= { sm24tat4xbQos 1 }
    sm24tat4xbQosPortPolicing        OBJECT IDENTIFIER    ::= { sm24tat4xbQos 2 }
--  sm24tat4xbQosQueuePolicing        OBJECT IDENTIFIER    ::= { sm24tat4xbQos 3 }
--  sm24tat4xbQosPortScheduler        OBJECT IDENTIFIER    ::= { sm24tat4xbQos 4 }
    sm24tat4xbQosEgressPortPCPRemarking  OBJECT IDENTIFIER    ::= { sm24tat4xbQos 6 }
    sm24tat4xbQosPortDSCP        OBJECT IDENTIFIER    ::= { sm24tat4xbQos 7 }
    sm24tat4xbQosDSCPBasedQoS        OBJECT IDENTIFIER    ::= { sm24tat4xbQos 8 }
    sm24tat4xbQosDSCPTranslation     OBJECT IDENTIFIER    ::= { sm24tat4xbQos 9 }
    sm24tat4xbQosDSCPClassification      OBJECT IDENTIFIER    ::= { sm24tat4xbQos 10 }
    sm24tat4xbQosControlList         OBJECT IDENTIFIER    ::= { sm24tat4xbQos 11 }
    sm24tat4xbQosStormControl        OBJECT IDENTIFIER    ::= { sm24tat4xbQos 12 }
    sm24tat4xbQosPortStormControl    OBJECT IDENTIFIER    ::= { sm24tat4xbQos 13 }
    sm24tat4xbQosWRED            OBJECT IDENTIFIER    ::= { sm24tat4xbQos 14 }
    sm24tat4xbQosQCLStatus        OBJECT IDENTIFIER    ::= { sm24tat4xbQos 15 }
    sm24tat4xbQosPortShapers         OBJECT IDENTIFIER    ::= { sm24tat4xbQos 16 }
    sm24tat4xbQosPortSchedulers      OBJECT IDENTIFIER    ::= { sm24tat4xbQos 17 }
--
-- =======================================================================================================================
-- Start sm24tat4xbQosPortClassification group
-- =======================================================================================================================
--sm24tat4xbQosPortClassificationTable

     sm24tat4xbQosPortClassificationTable OBJECT-TYPE
        SYNTAX      SEQUENCE OF     SM24TAT4XBQosPortClassificationEntry
        MAX-ACCESS  not-accessible
        STATUS      current
        DESCRIPTION
            "QoS Ingress Port Classification.
            INDEX for this table is ifIndex which is
            equivalent to the panel port number."
        ::= {     sm24tat4xbQosPortClassification  1 }

    sm24tat4xbQosPortClassificationEntry OBJECT-TYPE
        SYNTAX      SM24TAT4XBQosPortClassificationEntry
        MAX-ACCESS  not-accessible
        STATUS      current
        DESCRIPTION
            "The Qos Port Classification Table."
        INDEX    {     ifIndex  }
        ::= {     sm24tat4xbQosPortClassificationTable 1 }

    SM24TAT4XBQosPortClassificationEntry         ::= SEQUENCE {
        sm24tat4xbQosPortClassificationQoSClass    Integer32,
        sm24tat4xbQosPortClassificationDPlevel     Integer32,
        sm24tat4xbQosPortClassificationPCP         Integer32,
        sm24tat4xbQosPortClassificationDEI         Integer32,
        sm24tat4xbQosPortClassificationPCPClassification AdminMode,
        sm24tat4xbQosPortClassificationDSCPBased    AdminMode,
--          sm24tat4xbQosPortClassificationQCLAddr     INTEGER,
--          sm24tat4xbQosPortClassificationKeyType     KeyType,
        sm24tat4xbQosPortClassificationWredGroup    Integer32
        }

    sm24tat4xbQosPortClassificationQoSClass OBJECT-TYPE
        SYNTAX      Integer32(0..7)
        MAX-ACCESS  read-write
        STATUS      current
        DESCRIPTION
          "Controls the default QoS class, i.e., the QoS class for
            frames not classified
            in any way. There is a one to one mapping between
            QoS class, queue and
            priority. A QoS class of 0 (zero) has the lowest priority.
            NOTe: If the QoS class has been dynamically changed, then
            the actual QoS class
            is shown in parentheses after the configured QoS class.
            range: 0~7,
            default: 0."
        ::= {     sm24tat4xbQosPortClassificationEntry 2 }

    sm24tat4xbQosPortClassificationDPlevel OBJECT-TYPE
        SYNTAX      Integer32(0..3)
        MAX-ACCESS  read-write
        STATUS      current
        DESCRIPTION
            "DP level for frames not classified in any way.
            range: 0~3,
            default: 0."
        ::= {     sm24tat4xbQosPortClassificationEntry 3 }

    sm24tat4xbQosPortClassificationPCP OBJECT-TYPE
        SYNTAX      Integer32(0..7)
        MAX-ACCESS  read-write
        STATUS      current
        DESCRIPTION
          "Priority Code Point. It is a 3-bit field storing
            the priority level for the 802.1Q frame.
            range: 0~7,
            default: 0.
            "
        ::= {     sm24tat4xbQosPortClassificationEntry 4 }

    sm24tat4xbQosPortClassificationDEI OBJECT-TYPE
        SYNTAX      Integer32(0|1)
        MAX-ACCESS  read-write
        STATUS      current
        DESCRIPTION
          "Drop Eligible Indicator. It is a 1-bit field in the VLAN.
            range 0~1,
            default: 0.
          "
        ::= {     sm24tat4xbQosPortClassificationEntry 5 }

    sm24tat4xbQosPortClassificationPCPClassification OBJECT-TYPE
        SYNTAX      AdminMode
        MAX-ACCESS  read-write
        STATUS      current
        DESCRIPTION
          "Configure the classification mode for tagged frames.
          "
        DEFVAL  { disable }
        ::= {     sm24tat4xbQosPortClassificationEntry 6 }

    sm24tat4xbQosPortClassificationDSCPBased OBJECT-TYPE
        SYNTAX      AdminMode
        MAX-ACCESS  read-write
        STATUS      current
        DESCRIPTION
          "Click to Enable DSCP Based QoS Ingress Port Classification."
        DEFVAL  { disable }
        ::= {     sm24tat4xbQosPortClassificationEntry 7 }

--    sm24tat4xbQosPortClassificationQCLAddr OBJECT-TYPE
--        SYNTAX      INTEGER { sMacSip(0), dMacDip (1) }
--        MAX-ACCESS  read-write
--        STATUS      current
--        DESCRIPTION
--          "Controls the QCL address matching mode.
--            0: SMAC/SIP,
--            1: DMAC/DIP,
--          default: SMAC/SIP.
--          Only support SPARX_III."
--        DEFVAL  { sMacSip }
--        ::= {     sm24tat4xbQosPortClassificationEntry 8 }

--    sm24tat4xbQosPortClassificationKeyType OBJECT-TYPE
--        SYNTAX      KeyType
--        MAX-ACCESS  read-write
--        STATUS      current
--        DESCRIPTION
--          "The key type specifying the key generated for frames received
--            on the port.
--            0: Normal, Half key, match outer tag, SIP/DIP and SMAC/DMAC.
--            1: Double Tag: Quarter key, match inner and outer tag.
--            2: IP Address: Half key, match inner and outer tag, SIP and
--              DIP. For non-IP frames, match outer tag only.
--            3: MAC and IP Address: Full key, match inner and outer tag,
--              SMAC, DMAC, SIP and DIP.
--            Only support on SERVAL version."
--        DEFVAL  { normal }
--        ::= {     sm24tat4xbQosPortClassificationEntry 9 }

    sm24tat4xbQosPortClassificationWredGroup OBJECT-TYPE
        SYNTAX      Integer32
        MAX-ACCESS  read-write
        STATUS      current
        DESCRIPTION
          "Controls the WRED group membership. Range:1-3."
        ::= {     sm24tat4xbQosPortClassificationEntry 10 }

--sm24tat4xbQoSIngressPortTagClassificationTable
    sm24tat4xbQoSIngressPortTagClassificationTable OBJECT-TYPE
        SYNTAX      SEQUENCE OF     SM24TAT4XBQoSIngressPortTagClassificationEntry
        MAX-ACCESS  not-accessible
        STATUS      current
        DESCRIPTION
            "Show QoS Ingress Port Tag Classification.
            INDEX for this table is ifIndex which is
            equivalent to the panel port number."
        ::= {     sm24tat4xbQosPortClassification 2 }

    sm24tat4xbQoSIngressPortTagClassificationEntry OBJECT-TYPE
        SYNTAX      SM24TAT4XBQoSIngressPortTagClassificationEntry
        MAX-ACCESS  not-accessible
        STATUS      current
        DESCRIPTION
            "QoS Ingress Port Tag Classification entry."
        INDEX    {     ifIndex,
                  sm24tat4xbQoSIngressPortTagPCP,
                  sm24tat4xbQoSIngressPortTagDEI  }
        ::= {     sm24tat4xbQoSIngressPortTagClassificationTable 1 }

    SM24TAT4XBQoSIngressPortTagClassificationEntry         ::= SEQUENCE {
        sm24tat4xbQoSIngressPortTagPCP            INTEGER,
        sm24tat4xbQoSIngressPortTagDEI            INTEGER,
        sm24tat4xbQoSIngressPortTagQosClass          Integer32,
        sm24tat4xbQoSIngressPortTagDPLevel        Integer32
        }

    sm24tat4xbQoSIngressPortTagPCP OBJECT-TYPE
        SYNTAX      INTEGER { pcp0(1),
                     pcp1(2),
                     pcp2(3),
                     pcp3(4),
                     pcp4(5),
                     pcp5(6),
                     pcp6(7),
                     pcp7(8) }
        MAX-ACCESS  not-accessible
        STATUS      current
        DESCRIPTION
            "range: 1-8,
            PCP0:1, PCP1:2..."
        ::= {     sm24tat4xbQoSIngressPortTagClassificationEntry 2 }

    sm24tat4xbQoSIngressPortTagDEI OBJECT-TYPE
        SYNTAX      INTEGER { dei0(1), dei1(2) }
        MAX-ACCESS  not-accessible
        STATUS      current
        DESCRIPTION
            "Ingress Port Tag dei,
            DEI0:1, DEI1:2."
        ::= {     sm24tat4xbQoSIngressPortTagClassificationEntry 3 }

    sm24tat4xbQoSIngressPortTagQosClass OBJECT-TYPE
        SYNTAX      Integer32(0..7)
        MAX-ACCESS  read-write
        STATUS      current
        DESCRIPTION
            "range: 0-7."
        ::= {     sm24tat4xbQoSIngressPortTagClassificationEntry 4 }

    sm24tat4xbQoSIngressPortTagDPLevel OBJECT-TYPE
        SYNTAX      Integer32(0..3)
        MAX-ACCESS  read-write
        STATUS      current
        DESCRIPTION
            "range: 0-3."
        ::= {     sm24tat4xbQoSIngressPortTagClassificationEntry 5 }


--
-- =======================================================================================================================
-- Start sm24tat4xbQosPortPolicing group
-- =======================================================================================================================
--sm24tat4xbQosPortPolicingTable
    sm24tat4xbQosPortPolicingTable OBJECT-TYPE
        SYNTAX      SEQUENCE OF     SM24TAT4XBQosPortPolicingEntry
        MAX-ACCESS  not-accessible
        STATUS      current
        DESCRIPTION
            "The Policer settings.
            INDEX for this table is ifIndex which is
            equivalent to the panel port number."
        ::= {     sm24tat4xbQosPortPolicing 1 }

    sm24tat4xbQosPortPolicingEntry OBJECT-TYPE
        SYNTAX      SM24TAT4XBQosPortPolicingEntry
        MAX-ACCESS  not-accessible
        STATUS      current
        DESCRIPTION
            "The Policer setting entry."
        INDEX    {     ifIndex  }
        ::= {     sm24tat4xbQosPortPolicingTable 1 }

    SM24TAT4XBQosPortPolicingEntry         ::= SEQUENCE {
        sm24tat4xbQosPortPolicingEnabled     AdminMode,
        sm24tat4xbQosPortPolicingRate        Integer32,
        sm24tat4xbQosPortPolicingUnit        Integer32,
        sm24tat4xbQosPortPolicingFlowControl     AdminMode
        }

    sm24tat4xbQosPortPolicingEnabled OBJECT-TYPE
        SYNTAX      AdminMode
        MAX-ACCESS  read-write
        STATUS      current
        DESCRIPTION
          "Controls whether the policer is enabled on this switch port."
        DEFVAL  { disable }
        ::= {     sm24tat4xbQosPortPolicingEntry 2 }

    sm24tat4xbQosPortPolicingRate OBJECT-TYPE
        SYNTAX      Integer32
        MAX-ACCESS  read-write
        STATUS      current
        DESCRIPTION
            "Controls the rate for the policer.
            default: 500(kbps)."
        ::= {     sm24tat4xbQosPortPolicingEntry 3 }

    sm24tat4xbQosPortPolicingUnit OBJECT-TYPE
        SYNTAX      Integer32
        MAX-ACCESS  read-write
        STATUS      current
        DESCRIPTION
            "Controls the unit of measure for the policer rate.
            0: kbps
            1: Mbps
		    2: fps
		    3: kfps
		    "
        ::= {     sm24tat4xbQosPortPolicingEntry 4 }

    sm24tat4xbQosPortPolicingFlowControl OBJECT-TYPE
        SYNTAX      AdminMode
        MAX-ACCESS  read-write
        STATUS      current
        DESCRIPTION
            "If flow control is enabled and the port is in flow control mode,
            then pause frames are sent instead of discarding frames."
        DEFVAL  { disable }
        ::= {     sm24tat4xbQosPortPolicingEntry 5 }

--
-- =======================================================================================================================
-- Start sm24tat4xbQosQueuePolicing group
-- =======================================================================================================================
--sm24tat4xbQosQueuePolicingTable
--    sm24tat4xbQosQueuePolicingTable OBJECT-TYPE
--        SYNTAX      SEQUENCE OF     SM24TAT4XBQosQueuePolicingEntry
--        MAX-ACCESS  not-accessible
--        STATUS      current
--        DESCRIPTION
--            "The Queue Policer settings.
--            INDEX for this table is ifIndex which is
--            equivalent to the panel port number."
--        ::= {     sm24tat4xbQosQueuePolicing 1 }
--
--    sm24tat4xbQosQueuePolicingEntry OBJECT-TYPE
--        SYNTAX      SM24TAT4XBQosQueuePolicingEntry
--        MAX-ACCESS  not-accessible
--        STATUS      current
--        DESCRIPTION
--            "The Qos Queue Policing Entry."
--        INDEX    {     ifIndex  }
--        ::= {     sm24tat4xbQosQueuePolicingTable 1 }
--
--    SM24TAT4XBQosQueuePolicingEntry         ::= SEQUENCE {
--        sm24tat4xbQosQueuePolicingQueue0Enable    AdminMode,
--        sm24tat4xbQosQueuePolicingQueue0Rate     Integer32,
--		sm24tat4xbQosQueuePolicingQueue0Unit     Integer32,
--        sm24tat4xbQosQueuePolicingQueue1Enable    AdminMode,
--        sm24tat4xbQosQueuePolicingQueue1Rate     Integer32,
--		sm24tat4xbQosQueuePolicingQueue1Unit     Integer32,
--        sm24tat4xbQosQueuePolicingQueue2Enable    AdminMode,
--        sm24tat4xbQosQueuePolicingQueue2Rate     Integer32,
--        sm24tat4xbQosQueuePolicingQueue2Unit     Integer32,
--        sm24tat4xbQosQueuePolicingQueue3Enable    AdminMode,
--        sm24tat4xbQosQueuePolicingQueue3Rate     Integer32,
--        sm24tat4xbQosQueuePolicingQueue3Unit     Integer32,
--        sm24tat4xbQosQueuePolicingQueue4Enable    AdminMode,
--        sm24tat4xbQosQueuePolicingQueue4Rate     Integer32,
--		sm24tat4xbQosQueuePolicingQueue4Unit     Integer32,
--        sm24tat4xbQosQueuePolicingQueue5Enable    AdminMode,
--        sm24tat4xbQosQueuePolicingQueue5Rate     Integer32,
--		sm24tat4xbQosQueuePolicingQueue5Unit     Integer32,
--        sm24tat4xbQosQueuePolicingQueue6Enable    AdminMode,
--        sm24tat4xbQosQueuePolicingQueue6Rate     Integer32,
--		sm24tat4xbQosQueuePolicingQueue6Unit     Integer32,
--        sm24tat4xbQosQueuePolicingQueue7Enable    AdminMode,
--        sm24tat4xbQosQueuePolicingQueue7Rate     Integer32,
--		sm24tat4xbQosQueuePolicingQueue7Unit     Integer32
--        }
--
--    sm24tat4xbQosQueuePolicingQueue0Enable OBJECT-TYPE
--        SYNTAX      AdminMode
--        MAX-ACCESS  read-write
--        STATUS      current
--        DESCRIPTION
--            "Controls whether the queue 0 policer is enabled on this switch port."
--        DEFVAL  { disable }
--        ::= {     sm24tat4xbQosQueuePolicingEntry 3 }
--
--    sm24tat4xbQosQueuePolicingQueue0Rate OBJECT-TYPE
--        SYNTAX      Integer32
--        MAX-ACCESS  read-write
--        STATUS      current
--        DESCRIPTION
--            "Controls whether the queue 0 policer is enabled on this switch port.
--            default: 500(Kbps)"
--        ::= {     sm24tat4xbQosQueuePolicingEntry 4 }
--
--    sm24tat4xbQosQueuePolicingQueue0Unit OBJECT-TYPE
--        SYNTAX      Integer32(0|1)
--        MAX-ACCESS  read-write
--        STATUS      current
--        DESCRIPTION
--            "Controls the unit of measure for the queue policer rate as kbps or Mbps.
--            range:
--		    0:kbs
--		    1:Mbps
--            default: 0(kbps)"
--        ::= {     sm24tat4xbQosQueuePolicingEntry 5 }
--
--    sm24tat4xbQosQueuePolicingQueue1Enable OBJECT-TYPE
--        SYNTAX      AdminMode
--        MAX-ACCESS  read-write
--        STATUS      current
--        DESCRIPTION
--            "Controls whether the queue 1 policer is enabled on this switch port."
--        DEFVAL  { disable }
--        ::= {     sm24tat4xbQosQueuePolicingEntry 6 }
--
--    sm24tat4xbQosQueuePolicingQueue1Rate OBJECT-TYPE
--        SYNTAX      Integer32
--        MAX-ACCESS  read-write
--        STATUS      current
--        DESCRIPTION
--            "Controls whether the queue 1 policer is enabled on this switch port.,
--            default: 500(Kbps)"
--        ::= {     sm24tat4xbQosQueuePolicingEntry 7 }
--
--    sm24tat4xbQosQueuePolicingQueue1Unit OBJECT-TYPE
--        SYNTAX      Integer32(0|1)
--        MAX-ACCESS  read-write
--        STATUS      current
--        DESCRIPTION
--            "Controls the unit of measure for the queue policer rate as kbps or Mbps.
--            range:
--		    0:kbs
--		    1:Mbps
--            default: 0(kbps)"
--        ::= {     sm24tat4xbQosQueuePolicingEntry 8 }
--
--    sm24tat4xbQosQueuePolicingQueue2Enable OBJECT-TYPE
--        SYNTAX      AdminMode
--        MAX-ACCESS  read-write
--        STATUS      current
--        DESCRIPTION
--            "Controls whether the queue 2 policer is enabled on this switch port."
--        DEFVAL  { disable }
--        ::= {     sm24tat4xbQosQueuePolicingEntry 9 }
--
--    sm24tat4xbQosQueuePolicingQueue2Rate OBJECT-TYPE
--        SYNTAX      Integer32
--        MAX-ACCESS  read-write
--        STATUS      current
--        DESCRIPTION
--            "Controls whether the queue 2 policer is enabled on this switch port.
--            default: 500(Kbps)"
--        ::= {     sm24tat4xbQosQueuePolicingEntry 10 }
--
--    sm24tat4xbQosQueuePolicingQueue2Unit OBJECT-TYPE
--        SYNTAX      Integer32(0|1)
--        MAX-ACCESS  read-write
--        STATUS      current
--        DESCRIPTION
--            "Controls the unit of measure for the queue policer rate as kbps or Mbps.
--            range:
--		    0:kbs
--		    1:Mbps
--            default: 0(kbps)"
--        ::= {     sm24tat4xbQosQueuePolicingEntry 11 }
--
--    sm24tat4xbQosQueuePolicingQueue3Enable OBJECT-TYPE
--        SYNTAX      AdminMode
--        MAX-ACCESS  read-write
--        STATUS      current
--        DESCRIPTION
--            "Controls whether the queue 3 policer is enabled on this switch port."
--        DEFVAL  { disable }
--        ::= {     sm24tat4xbQosQueuePolicingEntry 12 }
--
--    sm24tat4xbQosQueuePolicingQueue3Rate OBJECT-TYPE
--        SYNTAX      Integer32
--        MAX-ACCESS  read-write
--        STATUS      current
--        DESCRIPTION
--            "Controls whether the queue 3 policer is enabled on this switch port.
--            default: 500(Kbps)"
--        ::= {     sm24tat4xbQosQueuePolicingEntry 13 }
--
--    sm24tat4xbQosQueuePolicingQueue3Unit OBJECT-TYPE
--        SYNTAX      Integer32(0|1)
--        MAX-ACCESS  read-write
--        STATUS      current
--        DESCRIPTION
--            "Controls the unit of measure for the queue policer rate as kbps or Mbps.
--            range:
--		    0:kbs
--		    1:Mbps
--            default: 0(kbps)"
--        ::= {     sm24tat4xbQosQueuePolicingEntry 14 }
--
--    sm24tat4xbQosQueuePolicingQueue4Enable OBJECT-TYPE
--        SYNTAX      AdminMode
--        MAX-ACCESS  read-write
--        STATUS      current
--        DESCRIPTION
--            "Controls whether the queue 4 policer is enabled on this switch port."
--        DEFVAL  { disable }
--        ::= {     sm24tat4xbQosQueuePolicingEntry 15 }
--
--    sm24tat4xbQosQueuePolicingQueue4Rate OBJECT-TYPE
--        SYNTAX      Integer32
--        MAX-ACCESS  read-write
--        STATUS      current
--        DESCRIPTION
--            "Controls whether the queue 4 policer is enabled on this switch port.
--            default: 500(Kbps)"
--        ::= {     sm24tat4xbQosQueuePolicingEntry 16 }
--
--    sm24tat4xbQosQueuePolicingQueue4Unit OBJECT-TYPE
--        SYNTAX      Integer32(0|1)
--        MAX-ACCESS  read-write
--        STATUS      current
--        DESCRIPTION
--            "Controls the unit of measure for the queue policer rate as kbps or Mbps.
--            range:
--		    0:kbs
--		    1:Mbps
--            default: 0(kbps)"
--        ::= {     sm24tat4xbQosQueuePolicingEntry 17 }
--
--    sm24tat4xbQosQueuePolicingQueue5Enable OBJECT-TYPE
--        SYNTAX      AdminMode
--        MAX-ACCESS  read-write
--        STATUS      current
--        DESCRIPTION
--            "Controls whether the queue 5 policer is enabled on this switch port."
--        DEFVAL  { disable }
--        ::= {     sm24tat4xbQosQueuePolicingEntry 18 }
--
--    sm24tat4xbQosQueuePolicingQueue5Rate OBJECT-TYPE
--        SYNTAX      Integer32
--        MAX-ACCESS  read-write
--        STATUS      current
--        DESCRIPTION
--            "Controls whether the queue 5 policer is enabled on this switch port.
--            default: 500(Kbps)"
--        ::= {     sm24tat4xbQosQueuePolicingEntry 19 }
--
--    sm24tat4xbQosQueuePolicingQueue5Unit OBJECT-TYPE
--        SYNTAX      Integer32(0|1)
--        MAX-ACCESS  read-write
--        STATUS      current
--        DESCRIPTION
--            "Controls the unit of measure for the queue policer rate as kbps or Mbps.
--            range:
--		    0:kbs
--		    1:Mbps
--            default: 0(kbps)"
--        ::= {     sm24tat4xbQosQueuePolicingEntry 20 }
--
--    sm24tat4xbQosQueuePolicingQueue6Enable OBJECT-TYPE
--        SYNTAX      AdminMode
--        MAX-ACCESS  read-write
--        STATUS      current
--        DESCRIPTION
--            "Controls whether the queue 6 policer is enabled on this switch port."
--        DEFVAL  { disable }
--        ::= {     sm24tat4xbQosQueuePolicingEntry 21 }
--
--    sm24tat4xbQosQueuePolicingQueue6Rate OBJECT-TYPE
--        SYNTAX      Integer32
--        MAX-ACCESS  read-write
--        STATUS      current
--        DESCRIPTION
--            "Controls whether the queue 6 policer is enabled on this switch port.
--            default: 500(Kbps)"
--        ::= {     sm24tat4xbQosQueuePolicingEntry 22 }
--
--    sm24tat4xbQosQueuePolicingQueue6Unit OBJECT-TYPE
--        SYNTAX      Integer32(0|1)
--        MAX-ACCESS  read-write
--        STATUS      current
--        DESCRIPTION
--            "Controls the unit of measure for the queue policer rate as kbps or Mbps.
--            range:
--		    0:kbs
--		    1:Mbps
--            default: 0(kbps)"
--        ::= {     sm24tat4xbQosQueuePolicingEntry 23 }
--
--    sm24tat4xbQosQueuePolicingQueue7Enable OBJECT-TYPE
--        SYNTAX      AdminMode
--        MAX-ACCESS  read-write
--        STATUS      current
--        DESCRIPTION
--            "Controls whether the queue 7 policer is enabled on this switch port."
--        DEFVAL  { disable }
--        ::= {     sm24tat4xbQosQueuePolicingEntry 24 }
--
--    sm24tat4xbQosQueuePolicingQueue7Rate OBJECT-TYPE
--        SYNTAX      Integer32
--        MAX-ACCESS  read-write
--        STATUS      current
--        DESCRIPTION
--            "Controls whether the queue 7 policer is enabled on this switch port.
--            default: 500(Kbps)"
--        ::= {     sm24tat4xbQosQueuePolicingEntry 25 }
--
--    sm24tat4xbQosQueuePolicingQueue7Unit OBJECT-TYPE
--        SYNTAX      Integer32(0|1)
--        MAX-ACCESS  read-write
--        STATUS      current
--        DESCRIPTION
--            "Controls the unit of measure for the queue policer rate as kbps or Mbps.
--            range:
--		    0:kbs
--		    1:Mbps
--            default: 0(kbps)"
--        ::= {     sm24tat4xbQosQueuePolicingEntry 26 }
--
--
-- =======================================================================================================================
-- Start sm24tat4xbQosPortScheduler group
-- =======================================================================================================================
--sm24tat4xbQosPortSchedulerModeTable

--     sm24tat4xbQosPortSchedulerModeTable OBJECT-TYPE
--        SYNTAX      SEQUENCE OF     SM24TAT4XBQosPortSchedulerModeEntry
--        MAX-ACCESS  not-accessible
--        STATUS      current
--        DESCRIPTION
--            "The basic QoS Port Scheduler Mode settings.
--            INDEX for this table is ifIndex which is
--            equivalent to the panel port number."
--        ::= {     sm24tat4xbQosPortScheduler  1 }
--
--    sm24tat4xbQosPortSchedulerModeEntry OBJECT-TYPE
--        SYNTAX      SM24TAT4XBQosPortSchedulerModeEntry
--        MAX-ACCESS  not-accessible
--        STATUS      current
--        DESCRIPTION
--            "The Qos Port Scheduler Mode entry."
--        INDEX    {     ifIndex  }
--        ::= {     sm24tat4xbQosPortSchedulerModeTable 1 }
--
--    SM24TAT4XBQosPortSchedulerModeEntry         ::= SEQUENCE {
--        sm24tat4xbQosSchedulerMode        Integer32,
--        sm24tat4xbQosSchedulerShaper      AdminMode,
--        sm24tat4xbQosSchedulerShaperRate      Integer32
--        }
--
--    sm24tat4xbQosSchedulerMode OBJECT-TYPE
--        SYNTAX      Integer32
--        MAX-ACCESS  read-write
--        STATUS      current
--        DESCRIPTION
--            "Controls whether the scheduler mode is Strict Priority or Weighted
--            on this switch port.
--            0:Strict Priority,
--		    2: 2 Queues Weighted
--		    3: 3 Queues Weighted: only Jaguar2 support
--		    4: 4 Queues Weighted: only Jaguar2 support
--		    5: 5 Queues Weighted: only Jaguar2 support
--            6: 6 Queues Weighted
--		    7: 7 Queues Weighted: only Jaguar2 support
--		    8: 8 Queues Weighted: only Jaguar2 support"
--        ::= {     sm24tat4xbQosPortSchedulerModeEntry 2 }
--
--    sm24tat4xbQosSchedulerShaper OBJECT-TYPE
--        SYNTAX      AdminMode
--        MAX-ACCESS  read-write
--        STATUS      current
--        DESCRIPTION
--            "Controls whether the port shaper is enabled."
--        DEFVAL  { disable }
--        ::= {     sm24tat4xbQosPortSchedulerModeEntry 3 }
--
--    sm24tat4xbQosSchedulerShaperRate OBJECT-TYPE
--        SYNTAX      Integer32
--        MAX-ACCESS  read-write
--        STATUS      current
--        DESCRIPTION
--            "Controls the rate for the port shaper.
--            default: 500 kbps."
--        ::= {     sm24tat4xbQosPortSchedulerModeEntry 4 }
--
--sm24tat4xbQosPortSchedulerTable
--    sm24tat4xbQosPortSchedulerTable OBJECT-TYPE
--        SYNTAX      SEQUENCE OF     SM24TAT4XBQosPortSchedulerEntry
--        MAX-ACCESS  not-accessible
--        STATUS      current
--        DESCRIPTION
--            "Show Qos Port Scheduler.
--            INDEX for this table is ifIndex which is
--            equivalent to the panel port number."
--        ::= {     sm24tat4xbQosPortScheduler 2 }
--
--    sm24tat4xbQosPortSchedulerEntry OBJECT-TYPE
--        SYNTAX      SM24TAT4XBQosPortSchedulerEntry
--        MAX-ACCESS  not-accessible
--        STATUS      current
--        DESCRIPTION
--            "The Qos Port Scheduler Entry."
--        INDEX    {     ifIndex,
--                  sm24tat4xbQosSchedulerPortQueue}
--        ::= {     sm24tat4xbQosPortSchedulerTable 1 }
--
--    SM24TAT4XBQosPortSchedulerEntry         ::= SEQUENCE {
--        sm24tat4xbQosSchedulerPortQueue          INTEGER,
--        sm24tat4xbQosSchedulerPortQueueShaper        AdminMode,
--        sm24tat4xbQosSchedulerPortQueueShaperRate    Integer32,
--        sm24tat4xbQosSchedulerPortQueueShaperExcess      AdminMode,
--        sm24tat4xbQosSchedulerPortQueueSchedulerWeight    Integer32,
--        sm24tat4xbQosSchedulerPortQueueSchedulerPercent  DisplayString
--        }
--
--    sm24tat4xbQosSchedulerPortQueue OBJECT-TYPE
--        SYNTAX      INTEGER { q0(1),
--                     q1(2),
--                     q2(3),
--                     q3(4),
--                     q4(5),
--                     q5(6),
--                     q6(7),
--                     q7(8) }
--        MAX-ACCESS  not-accessible
--        STATUS      current
--        DESCRIPTION
--            "range: 1-8.
--            Q0: 1, Q1: 2, ..."
--        ::= {     sm24tat4xbQosPortSchedulerEntry 2 }
--
--    sm24tat4xbQosSchedulerPortQueueShaper OBJECT-TYPE
--        SYNTAX     AdminMode
--        MAX-ACCESS  read-write
--        STATUS      current
--        DESCRIPTION
--            "Qos scheduler admin state."
--        DEFVAL  { disable }
--        ::= {     sm24tat4xbQosPortSchedulerEntry 3 }
--
--    sm24tat4xbQosSchedulerPortQueueShaperRate OBJECT-TYPE
--        SYNTAX      Integer32(100..1000000)
--        MAX-ACCESS  read-write
--        STATUS      current
--        DESCRIPTION
--            "range: 100..1000000 kbps. "
--        ::= {     sm24tat4xbQosPortSchedulerEntry 4 }
--
--    sm24tat4xbQosSchedulerPortQueueShaperExcess OBJECT-TYPE
--        SYNTAX      AdminMode
--        MAX-ACCESS  read-write
--        STATUS      current
--        DESCRIPTION
--            "admin state sm24tat4xbQosSchedulerPortQueueShaperExcess"
--        DEFVAL  { disable }
--        ::= {     sm24tat4xbQosPortSchedulerEntry 5 }
--
--    sm24tat4xbQosSchedulerPortQueueSchedulerWeight OBJECT-TYPE
--        SYNTAX      Integer32(0..100)
--        MAX-ACCESS  read-write
--        STATUS      current
--        DESCRIPTION
--            "range: 1-100,
--            default: 17.
--            Only use in Q0 - Q5.  Q6 & Q7 show 0"
--        ::= {     sm24tat4xbQosPortSchedulerEntry 6 }
--
--    sm24tat4xbQosSchedulerPortQueueSchedulerPercent OBJECT-TYPE
--        SYNTAX      DisplayString
--        MAX-ACCESS  read-only
--        STATUS      current
--        DESCRIPTION
--            "Only use in Q0 - Q5. Q6 & Q7 show empty"
--        ::= {     sm24tat4xbQosPortSchedulerEntry 7 }
--
-- =======================================================================================================================
-- Start sm24tat4xbQosEgressPortPCPRemarking group
-- =======================================================================================================================
--sm24tat4xbQosEgressPortPCPRemarkingTable
    sm24tat4xbQosEgressPortPCPRemarkingTable OBJECT-TYPE
        SYNTAX      SEQUENCE OF     SM24TAT4XBQosEgressPortPCPRemarkingEntry
        MAX-ACCESS  not-accessible
        STATUS      current
        DESCRIPTION
            "The basic Qos Egress Port PCP Remarking
            Configuration settings.
            INDEX for this table is ifIndex which is
            equivalent to the panel port number."
        ::= {     sm24tat4xbQosEgressPortPCPRemarking  1 }

    sm24tat4xbQosEgressPortPCPRemarkingEntry OBJECT-TYPE
        SYNTAX      SM24TAT4XBQosEgressPortPCPRemarkingEntry
        MAX-ACCESS  not-accessible
        STATUS      current
        DESCRIPTION
            "The Qos Egress Port PCP Remarking Entry."
        INDEX    {     ifIndex  }
        ::= {     sm24tat4xbQosEgressPortPCPRemarkingTable 1 }

    SM24TAT4XBQosEgressPortPCPRemarkingEntry         ::= SEQUENCE {
        sm24tat4xbQosEgressPortPCPRemarkingMode            INTEGER
        }

    sm24tat4xbQosEgressPortPCPRemarkingMode OBJECT-TYPE
        SYNTAX      INTEGER { keep(0), specific(1), mapped(2) }
        MAX-ACCESS  read-write
        STATUS      current
        DESCRIPTION
            "the tag remarking mode for this port.
            0:Keep, Use classified PCP/DEI values.
            1:Specific, Use default PCP/DEI values.
            2:Mapped, Use mapped versions of QoS class and DP level."
        ::= {     sm24tat4xbQosEgressPortPCPRemarkingEntry 2 }

--sm24tat4xbQosEgressPortPCPRemarkingSpecificTable
    sm24tat4xbQosEgressPortPCPRemarkingSpecificTable OBJECT-TYPE
        SYNTAX      SEQUENCE OF     SM24TAT4XBQosEgressPortPCPRemarkingSpecificEntry
        MAX-ACCESS  not-accessible
        STATUS      current
        DESCRIPTION
            "The basic Qos Egress Port PCP Remarking Specific
            Configuration settings.
            INDEX for this table is ifIndex which is
            equivalent to the panel port number."
        ::= {     sm24tat4xbQosEgressPortPCPRemarking  2 }

    sm24tat4xbQosEgressPortPCPRemarkingSpecificEntry OBJECT-TYPE
        SYNTAX      SM24TAT4XBQosEgressPortPCPRemarkingSpecificEntry
        MAX-ACCESS  not-accessible
        STATUS      current
        DESCRIPTION
            "The Qos Egress Port PCP Remarking Specific Entry."
        INDEX    {     ifIndex  }
        ::= {     sm24tat4xbQosEgressPortPCPRemarkingSpecificTable 1 }

    SM24TAT4XBQosEgressPortPCPRemarkingSpecificEntry         ::= SEQUENCE {
        sm24tat4xbQosEgressPortPCPRemarkingSpecificPCP        Integer32,
        sm24tat4xbQosEgressPortPCPRemarkingSpecificDEI        AdminMode
        }

    sm24tat4xbQosEgressPortPCPRemarkingSpecificPCP OBJECT-TYPE
        SYNTAX      Integer32(0..7)
        MAX-ACCESS  read-write
        STATUS      current
        DESCRIPTION
            "Controls the specific PCP
            Range : 0-7"
        ::= {     sm24tat4xbQosEgressPortPCPRemarkingSpecificEntry 2 }

    sm24tat4xbQosEgressPortPCPRemarkingSpecificDEI OBJECT-TYPE
        SYNTAX      AdminMode
        MAX-ACCESS  read-write
        STATUS      current
        DESCRIPTION
            "controls the admin state of DEI"
        ::= {     sm24tat4xbQosEgressPortPCPRemarkingSpecificEntry 3 }

--sm24tat4xbQosPortEgressTagRemarkingMapDPTable
--    sm24tat4xbQosPortEgressTagRemarkingMapDPTable OBJECT-TYPE
--        SYNTAX      SEQUENCE OF     SM24TAT4XBQosPortEgressTagRemarkingMapDPEntry
--        MAX-ACCESS  not-accessible
--        STATUS      current
--        DESCRIPTION
--            "Show Qos Port Egress Tag Remarking Map DP.
--            INDEX for this table is ifIndex which is
--            equivalent to the panel port number."
--        ::= {     sm24tat4xbQosPortEgressTagRemarking 3 }

--    sm24tat4xbQosPortEgressTagRemarkingMapDPEntry OBJECT-TYPE
--        SYNTAX      SM24TAT4XBQosPortEgressTagRemarkingMapDPEntry
--        MAX-ACCESS  not-accessible
--        STATUS      current
--        DESCRIPTION
--            "The Qos Port Egress Tag Remarking Map DP Entry."
--        INDEX    {     ifIndex,
--                  sm24tat4xbQosPortEgressTagRemarkingClassifiedDPLevel}
--        ::= {     sm24tat4xbQosPortEgressTagRemarkingMapDPTable 1 }

--    SM24TAT4XBQosPortEgressTagRemarkingMapDPEntry         ::= SEQUENCE {
--        sm24tat4xbQosPortEgressTagRemarkingClassifiedDPLevel      Integer32,
--        sm24tat4xbQosPortEgressTagRemarkingDPLevel        AdminMode
--        }

--    sm24tat4xbQosPortEgressTagRemarkingClassifiedDPLevel OBJECT-TYPE
--        SYNTAX      Integer32(1..4)
--        MAX-ACCESS  not-accessible
--        STATUS      current
--        DESCRIPTION
--            "range: 1-4."
--        ::= {     sm24tat4xbQosPortEgressTagRemarkingMapDPEntry 2 }

--    sm24tat4xbQosPortEgressTagRemarkingDPLevel OBJECT-TYPE
--        SYNTAX      AdminMode
--        MAX-ACCESS  read-write
--        STATUS      current
--        DESCRIPTION
--            "admin state of Tag remark"
--        ::= {     sm24tat4xbQosPortEgressTagRemarkingMapDPEntry 3 }

--sm24tat4xbQosEgressPortPCPRemarkingMappedTable
    sm24tat4xbQosEgressPortPCPRemarkingMappedTable OBJECT-TYPE
        SYNTAX      SEQUENCE OF     SM24TAT4XBQosEgressPortPCPRemarkingMappedEntry
        MAX-ACCESS  not-accessible
        STATUS      current
        DESCRIPTION
            "Show Qos Egress Port PCP Remarking Mapped.
            INDEX for this table is ifIndex which is
            equivalent to the panel port number."
        ::= {     sm24tat4xbQosEgressPortPCPRemarking 4 }

    sm24tat4xbQosEgressPortPCPRemarkingMappedEntry OBJECT-TYPE
        SYNTAX      SM24TAT4XBQosEgressPortPCPRemarkingMappedEntry
        MAX-ACCESS  not-accessible
        STATUS      current
        DESCRIPTION
            "The Qos Egress Port PCP Remarking Mapped Entry."
        INDEX    {     ifIndex,
                  sm24tat4xbQosEgressPortPCPRemarkingMappedQueuePriority,
                  sm24tat4xbQosEgressPortPCPRemarkingMappedDPLevel  }
        ::= {     sm24tat4xbQosEgressPortPCPRemarkingMappedTable 1 }

    SM24TAT4XBQosEgressPortPCPRemarkingMappedEntry         ::= SEQUENCE {
        sm24tat4xbQosEgressPortPCPRemarkingMappedQueuePriority      INTEGER,
        sm24tat4xbQosEgressPortPCPRemarkingMappedDPLevel        INTEGER,
        sm24tat4xbQosEgressPortPCPRemarkingMappedPCP            Integer32,
        sm24tat4xbQosEgressPortPCPRemarkingMappedDEI            Integer32
        }

    sm24tat4xbQosEgressPortPCPRemarkingMappedQueuePriority OBJECT-TYPE
        SYNTAX      INTEGER {
            class0(1),
            class1(2),
            class2(3),
            class3(4),
            class4(5),
            class5(6),
            class6(7),
            class7(8)
            }
        MAX-ACCESS  not-accessible
        STATUS      current
        DESCRIPTION
            "range: 1-8,
            QoS Class0: 1, QoS Class1: 2..."
        ::= {     sm24tat4xbQosEgressPortPCPRemarkingMappedEntry 2 }

    sm24tat4xbQosEgressPortPCPRemarkingMappedDPLevel OBJECT-TYPE
        SYNTAX      INTEGER { level0(1), level1(2) }
        MAX-ACCESS  not-accessible
        STATUS      current
        DESCRIPTION
            "range: 1-2,
            DP Level0: 1, DP Level1: 2."
        ::= {     sm24tat4xbQosEgressPortPCPRemarkingMappedEntry 3 }

    sm24tat4xbQosEgressPortPCPRemarkingMappedPCP OBJECT-TYPE
        SYNTAX      Integer32(0..7)
        MAX-ACCESS  read-write
        STATUS      current
        DESCRIPTION
            "range: 0-7."
        ::= {     sm24tat4xbQosEgressPortPCPRemarkingMappedEntry 4 }

    sm24tat4xbQosEgressPortPCPRemarkingMappedDEI OBJECT-TYPE
        SYNTAX      Integer32 (0|1)
        MAX-ACCESS  read-write
        STATUS      current
        DESCRIPTION
            "range: 0-1."
        ::= {     sm24tat4xbQosEgressPortPCPRemarkingMappedEntry 5 }

--
-- =======================================================================================================================
-- Start sm24tat4xbQosPortDSCP group
-- =======================================================================================================================
--sm24tat4xbQosPortDSCPTable
    sm24tat4xbQosPortDSCPTable OBJECT-TYPE
        SYNTAX      SEQUENCE OF     SM24TAT4XBQosPortDSCPEntry
        MAX-ACCESS  not-accessible
        STATUS      current
        DESCRIPTION
            "The basic QoS Port DSCP Configuration settings.
            INDEX for this table is ifIndex which is
            equivalent to the panel port number."
        ::= {     sm24tat4xbQosPortDSCP 1 }

    sm24tat4xbQosPortDSCPEntry OBJECT-TYPE
        SYNTAX      SM24TAT4XBQosPortDSCPEntry
        MAX-ACCESS  not-accessible
        STATUS      current
        DESCRIPTION
            "The Qos Port DSCP Entry."
        INDEX    {     ifIndex  }
        ::= {     sm24tat4xbQosPortDSCPTable 1 }

    SM24TAT4XBQosPortDSCPEntry         ::= SEQUENCE {
        sm24tat4xbQosPortDSCPIngressTranslate    AdminMode,
        sm24tat4xbQosPortDSCPIngressClassify     INTEGER,
        sm24tat4xbQosPortDSCPEgressRewrite        INTEGER
        }

    sm24tat4xbQosPortDSCPIngressTranslate OBJECT-TYPE
        SYNTAX      AdminMode
        MAX-ACCESS  read-write
        STATUS      current
        DESCRIPTION
          "Configure DSCP ingress translation mode."
        DEFVAL  { disable }
        ::= {     sm24tat4xbQosPortDSCPEntry 2 }

    sm24tat4xbQosPortDSCPIngressClassify OBJECT-TYPE
        SYNTAX      INTEGER { disable (0), dscp (1), selected (2), all(3) }
        MAX-ACCESS  read-write
        STATUS      current
        DESCRIPTION
            "Classification for a port have 4 different values.
            0: disable,
            1: DSCP=0,
            2: Selected,
            3: All."
        DEFVAL  { disable }
        ::= {     sm24tat4xbQosPortDSCPEntry 3 }

    sm24tat4xbQosPortDSCPEgressRewrite OBJECT-TYPE
        SYNTAX      INTEGER { disable (0),enable (1),
                     remap (2) }
        MAX-ACCESS  read-write
        STATUS      current
        DESCRIPTION
            "Configure the port egress rewriting mode.
            0: Disable,1: Enable,2: Remap,range: 0-2"
        ::= {     sm24tat4xbQosPortDSCPEntry 4 }

--
-- =======================================================================================================================
-- Start sm24tat4xbQosDSCPBasedQoS group
-- =======================================================================================================================
    sm24tat4xbQosDSCPBasedQoSTable OBJECT-TYPE
        SYNTAX      SEQUENCE OF     SM24TAT4XBQosDSCPBasedQoSEntry
        MAX-ACCESS  not-accessible
        STATUS      current
        DESCRIPTION
            "configure the basic Qos DSCP-Based QoS Ingress Classification settings for all switches."
        ::= {     sm24tat4xbQosDSCPBasedQoS 1 }

    sm24tat4xbQosDSCPBasedQoSEntry OBJECT-TYPE
        SYNTAX      SM24TAT4XBQosDSCPBasedQoSEntry
        MAX-ACCESS  not-accessible
        STATUS      current
        DESCRIPTION
            "The Qos DSCP Based QoS Entry."
        INDEX    {     sm24tat4xbQosDSCPBasedQoSList  }
        ::= {     sm24tat4xbQosDSCPBasedQoSTable 1 }

    SM24TAT4XBQosDSCPBasedQoSEntry         ::= SEQUENCE {
        sm24tat4xbQosDSCPBasedQoSList      Integer32,
        sm24tat4xbQosDSCPBasedQoSDSCP      DisplayString,
        sm24tat4xbQosDSCPBasedQoSTrust     AdminMode,
        sm24tat4xbQosDSCPBasedQoSQueuePriority Integer32,
        sm24tat4xbQosDSCPBasedQoSDPL        Integer32
        }

    sm24tat4xbQosDSCPBasedQoSList OBJECT-TYPE
        SYNTAX      Integer32(1..64)
        MAX-ACCESS  not-accessible
        STATUS      current
        DESCRIPTION
          "DSCP mapping table index(1-64)."
        ::= {     sm24tat4xbQosDSCPBasedQoSEntry 1 }

    sm24tat4xbQosDSCPBasedQoSDSCP OBJECT-TYPE
        SYNTAX      DisplayString
        MAX-ACCESS  read-only
        STATUS      current
        DESCRIPTION
          "Maximum number of supported DSCP values are 64."
        ::= {     sm24tat4xbQosDSCPBasedQoSEntry 2 }

    sm24tat4xbQosDSCPBasedQoSTrust OBJECT-TYPE
        SYNTAX      AdminMode
        MAX-ACCESS  read-write
        STATUS      current
        DESCRIPTION
          "Controls whether a specific DSCP value is trusted. Only frames with
            trusted DSCP values are mapped to a specific QoS class
            and Drop Precedence
            Level. Frames with untrusted DSCP values are
            treated as a non-IP frame."
        DEFVAL  { disable }
          ::= {     sm24tat4xbQosDSCPBasedQoSEntry 3 }

    sm24tat4xbQosDSCPBasedQoSQueuePriority OBJECT-TYPE
        SYNTAX      Integer32(0..7)
        MAX-ACCESS  read-write
        STATUS      current
        DESCRIPTION
          "QoS class.
            range: 0-7,
            default: 0."
        ::= {     sm24tat4xbQosDSCPBasedQoSEntry 4 }

    sm24tat4xbQosDSCPBasedQoSDPL OBJECT-TYPE
        SYNTAX      Integer32(0|1)
        MAX-ACCESS  read-write
        STATUS      current
        DESCRIPTION
          "Drop Precedence Level.
            range: 0-1,
            default: 0."
        ::= {     sm24tat4xbQosDSCPBasedQoSEntry 5 }

--
-- =======================================================================================================================
-- Start sm24tat4xbQosDSCPTranslation group
-- =======================================================================================================================
--sm24tat4xbQosDSCPTranslationTable
    sm24tat4xbQosDSCPTranslationTable OBJECT-TYPE
        SYNTAX      SEQUENCE OF     SM24TAT4XBQosDSCPTranslationEntry
        MAX-ACCESS  not-accessible
        STATUS      current
        DESCRIPTION
            "The basic QoS DSCP Translation settings for all switches."
        ::= {     sm24tat4xbQosDSCPTranslation  1 }

    sm24tat4xbQosDSCPTranslationEntry OBJECT-TYPE
        SYNTAX      SM24TAT4XBQosDSCPTranslationEntry
        MAX-ACCESS  not-accessible
        STATUS      current
        DESCRIPTION
            "The Qos DSCP Translation Entry."
        INDEX    {     sm24tat4xbQosDSCPTranslationList  }
        ::= {     sm24tat4xbQosDSCPTranslationTable 1 }

    SM24TAT4XBQosDSCPTranslationEntry         ::= SEQUENCE {
        sm24tat4xbQosDSCPTranslationList         Integer32,
        sm24tat4xbQosDSCPTranslationDSCPBasedId      DisplayString,
        sm24tat4xbQosDSCPTranslationIngressTranslate     Integer32,
        sm24tat4xbQosDSCPTranslationIngressClassify      AdminMode,
        sm24tat4xbQosDSCPTranslationEgressRemap      Integer32
--          sm24tat4xbQosDSCPTranslationEgressRemapDP1    Integer32
        }

    sm24tat4xbQosDSCPTranslationList OBJECT-TYPE
        SYNTAX      Integer32(1..64)
        MAX-ACCESS  not-accessible
        STATUS      current
        DESCRIPTION
          "DSCP translation table index(1-64)."
        ::= {     sm24tat4xbQosDSCPTranslationEntry 1 }

    sm24tat4xbQosDSCPTranslationDSCPBasedId OBJECT-TYPE
        SYNTAX      DisplayString
        MAX-ACCESS  read-only
        STATUS      current
        DESCRIPTION
          "Configure global ingress DSCP translation table."
        ::= {     sm24tat4xbQosDSCPTranslationEntry 2 }

    sm24tat4xbQosDSCPTranslationIngressTranslate OBJECT-TYPE
        SYNTAX      Integer32(0..63)
        MAX-ACCESS  read-write
        STATUS      current
        DESCRIPTION
          "DSCP at Ingress side can be translated to any of DSCP values.
            range: 0-63,
            default: 0."
        ::= {     sm24tat4xbQosDSCPTranslationEntry 3 }

    sm24tat4xbQosDSCPTranslationIngressClassify OBJECT-TYPE
        SYNTAX      AdminMode
        MAX-ACCESS  read-write
        STATUS      current
        DESCRIPTION
          "Configure DSCP ingress classification."
        DEFVAL  { disable }
        ::= {     sm24tat4xbQosDSCPTranslationEntry 4 }

    sm24tat4xbQosDSCPTranslationEgressRemap OBJECT-TYPE
        SYNTAX      Integer32(0..63)
        MAX-ACCESS  read-write
        STATUS      current
        DESCRIPTION
          "Select the DSCP value from select menu to which you want to remap.
            range: 0-63,
            default: 0."
        ::= {     sm24tat4xbQosDSCPTranslationEntry 5 }

--    sm24tat4xbQosDSCPTranslationEgressRemapDP1 OBJECT-TYPE
--        SYNTAX      Integer32(0..63)
--        MAX-ACCESS  read-write
--        STATUS      current
--        DESCRIPTION
--          "Select the DSCP value from select menu to which you want to remap.
--            range: 0-63,
--            default: 0.
--            Only support LUTON26."
--        ::= {     sm24tat4xbQosDSCPTranslationEntry 6 }

--
-- =======================================================================================================================
-- Start sm24tat4xbQosDSCPClassification group
-- =======================================================================================================================
--sm24tat4xbQosDSCPClassificationTable
    sm24tat4xbQosDSCPClassificationTable OBJECT-TYPE
        SYNTAX      SEQUENCE OF     SM24TAT4XBQosDSCPClassificationEntry
        MAX-ACCESS  not-accessible
        STATUS      current
        DESCRIPTION
            "The mapping of QoS class  to DSCP value."
        ::= {     sm24tat4xbQosDSCPClassification 1 }

    sm24tat4xbQosDSCPClassificationEntry OBJECT-TYPE
        SYNTAX      SM24TAT4XBQosDSCPClassificationEntry
        MAX-ACCESS  not-accessible
        STATUS      current
        DESCRIPTION
            "The Qos DSCP Classification Entry."
        INDEX    {     sm24tat4xbQosDSCPClassificationQoSClass  }
        ::= {     sm24tat4xbQosDSCPClassificationTable 1 }

    SM24TAT4XBQosDSCPClassificationEntry         ::= SEQUENCE {
        sm24tat4xbQosDSCPClassificationQoSClass    Integer32,
        sm24tat4xbQosDSCPClassificationDSCPDP0    Integer32,
		sm24tat4xbQosDSCPClassificationDSCPDP1    Integer32,
		sm24tat4xbQosDSCPClassificationDSCPDP2    Integer32,
		sm24tat4xbQosDSCPClassificationDSCPDP3    Integer32
        }

    sm24tat4xbQosDSCPClassificationQoSClass OBJECT-TYPE
        SYNTAX      Integer32(1..8)
        MAX-ACCESS  not-accessible
        STATUS      current
        DESCRIPTION
          "This page allows you to configure the mapping of QoS class
            and Drop Precedence Level to DSCP value.
            range: 1-8}"
        ::= {     sm24tat4xbQosDSCPClassificationEntry 1 }

    sm24tat4xbQosDSCPClassificationDSCPDP0 OBJECT-TYPE
        SYNTAX      Integer32(0..63)
        MAX-ACCESS  read-write
        STATUS      current
        DESCRIPTION
          "Select the classified DSCP value.
            range: 0-63,
            default: 0."
        ::= {     sm24tat4xbQosDSCPClassificationEntry 2 }

    sm24tat4xbQosDSCPClassificationDSCPDP1 OBJECT-TYPE
        SYNTAX      Integer32(0..63)
        MAX-ACCESS  read-write
        STATUS      current
        DESCRIPTION
          "Select the classified DSCP value.
            range: 0-63,
            default: 0."
        ::= {     sm24tat4xbQosDSCPClassificationEntry 3 }

    sm24tat4xbQosDSCPClassificationDSCPDP2 OBJECT-TYPE
        SYNTAX      Integer32(0..63)
        MAX-ACCESS  read-write
        STATUS      current
        DESCRIPTION
          "Select the classified DSCP value.
            range: 0-63,
            default: 0."
        ::= {     sm24tat4xbQosDSCPClassificationEntry 4 }

    sm24tat4xbQosDSCPClassificationDSCPDP3 OBJECT-TYPE
        SYNTAX      Integer32(0..63)
        MAX-ACCESS  read-write
        STATUS      current
        DESCRIPTION
          "Select the classified DSCP value.
            range: 0-63,
            default: 0."
        ::= {     sm24tat4xbQosDSCPClassificationEntry 5 }

--
-- =======================================================================================================================
-- Start sm24tat4xbQosControlList group
-- =======================================================================================================================
--sm24tat4xbQosQceTable

    sm24tat4xbQosQceTable OBJECT-TYPE
        SYNTAX      SEQUENCE OF     SM24TAT4XBQosQceEntry
        MAX-ACCESS  not-accessible
        STATUS      current
        DESCRIPTION
            "Create Qos QCE entry."
        ::= {     sm24tat4xbQosControlList 1 }

    sm24tat4xbQosQceEntry OBJECT-TYPE
        SYNTAX      SM24TAT4XBQosQceEntry
        MAX-ACCESS  not-accessible
        STATUS      current
        DESCRIPTION
            "Qos Qce Entry."
        INDEX    {     sm24tat4xbQosQceIndex  }
        ::= {     sm24tat4xbQosQceTable 1 }

    SM24TAT4XBQosQceEntry         ::= SEQUENCE {
        sm24tat4xbQosQceIndex        Integer32,
        sm24tat4xbQosQceID            Integer32,
        sm24tat4xbQosQceList         Integer32,
--          sm24tat4xbQosQcePortMembersSwitch    Integer32,
        sm24tat4xbQosQcePortMembers      DisplayString,
        sm24tat4xbQosQceTag          DisplayString,
        sm24tat4xbQosQceVID          DisplayString,
        sm24tat4xbQosPCP             DisplayString,
        sm24tat4xbQosDEI             DisplayString,
        sm24tat4xbQosSMAC            DisplayString,
        sm24tat4xbQosDMACType        DisplayString,
        sm24tat4xbQosDMACValue        DisplayString,
        sm24tat4xbQosQceInnerTag         DisplayString,
        sm24tat4xbQosQceInnerVID         DisplayString,
        sm24tat4xbQosInnerPCP        DisplayString,
        sm24tat4xbQosInnerDEI        DisplayString,
        sm24tat4xbQosFrameType        INTEGER,
        sm24tat4xbQosMacEtherType        DisplayString,
        sm24tat4xbQosLLCSSAPAddr         DisplayString,
        sm24tat4xbQosLLCDSAPAddr         DisplayString,
        sm24tat4xbQosLLCControl          DisplayString,
        sm24tat4xbQosSNAPPID         DisplayString,
        sm24tat4xbQosIpv4Protocol        DisplayString,
        sm24tat4xbQosIpv4ProtocolValue    Integer32,
        sm24tat4xbQosIpv4ProtocolUDPSPort    DisplayString,
        sm24tat4xbQosIpv4ProtocolUDPDPort    DisplayString,
        sm24tat4xbQosIpv4ProtocolTCPSPort    DisplayString,
        sm24tat4xbQosIpv4ProtocolTCPDPort    DisplayString,
        sm24tat4xbQosIpv4SourceIp        DisplayString,
        sm24tat4xbQosIpv4SourceMask      DisplayString,
        sm24tat4xbQosIpv4DestIp          DisplayString,
        sm24tat4xbQosIpv4DestMask        DisplayString,
        sm24tat4xbQosIpv4IPFragment      INTEGER,
        sm24tat4xbQosIpv4DSCP        DisplayString,
        sm24tat4xbQosIpv6Protocol        DisplayString,
        sm24tat4xbQosIpv6ProtocolValue    Integer32,
        sm24tat4xbQosIpv6ProtocolUDPSPort    DisplayString,
        sm24tat4xbQosIpv6ProtocolUDPDPort    DisplayString,
        sm24tat4xbQosIpv6ProtocolTCPSPort    DisplayString,
        sm24tat4xbQosIpv6ProtocolTCPDPort    DisplayString,
        sm24tat4xbQosIpv6SourceIp        DisplayString,
        sm24tat4xbQosIpv6SourceMask      DisplayString,
        sm24tat4xbQosIpv6DestIp          DisplayString,
        sm24tat4xbQosIpv6DestMask        DisplayString,
        sm24tat4xbQosIpv6DSCP        DisplayString,
        sm24tat4xbQosActionQueuePriority     Integer32,
        sm24tat4xbQosActionDPL        Integer32,
        sm24tat4xbQosActionDSCP          Integer32,
        sm24tat4xbQosActionPCP        Integer32,
        sm24tat4xbQosActionDEI        Integer32,
        sm24tat4xbQosActionPolicy        Integer32,
        sm24tat4xbQosActionIngressMapID      Integer32,
        sm24tat4xbQosQceRowStatus        RowStatus
        }

    sm24tat4xbQosQceIndex OBJECT-TYPE
        SYNTAX      Integer32(1..256)
        MAX-ACCESS  not-accessible
        STATUS      current
        DESCRIPTION
            "the index to this table."
        ::= {     sm24tat4xbQosQceEntry 1 }

    sm24tat4xbQosQceID OBJECT-TYPE
        SYNTAX      Integer32(1..256)
        MAX-ACCESS  read-only
        STATUS      current
        DESCRIPTION
            "If the QCE ID is specified and an entry with this QCE ID
            already exists, the QCE will be modified. Otherwise, a
            new QCE will be added.
            range : 1 - 256."
        ::= {     sm24tat4xbQosQceEntry 2 }

    sm24tat4xbQosQceList OBJECT-TYPE
        SYNTAX      Integer32(0..256)
        MAX-ACCESS  read-create
        STATUS      current
        DESCRIPTION
            "If the QCE List is non zero, the QCE will be placed in the list.
            If the QCE List is zero, the QCE will be placed last in the list.
            range : 0 - 256."
        ::= {     sm24tat4xbQosQceEntry 3 }

--    sm24tat4xbQosQcePortMembersSwitch OBJECT-TYPE
--        SYNTAX      Integer32
--        MAX-ACCESS  read-create
--        STATUS      current
--        DESCRIPTION
--            "Switch number for port members.
--            -1:Any.
--            Only support stacking switch."
--        ::= {     sm24tat4xbQosQceEntry 4 }

    sm24tat4xbQosQcePortMembers OBJECT-TYPE
        SYNTAX      DisplayString
        MAX-ACCESS  read-create
        STATUS      current
        DESCRIPTION
            "Indicates the ingress port of the QCE. Possible values are:
            All: The QCE will match all ingress port.
            Port: The QCE will match a specific ingress port.Format: 1,3-6."
        ::= {     sm24tat4xbQosQceEntry 5 }

    sm24tat4xbQosQceTag OBJECT-TYPE
        SYNTAX      DisplayString
        MAX-ACCESS  read-create
        STATUS      current
        DESCRIPTION
          "'Any', 'Untagged' or 'Tagged' or 'C-Tag' or 'S-Tag'"
        ::= {     sm24tat4xbQosQceEntry 6 }

    sm24tat4xbQosQceVID OBJECT-TYPE
        SYNTAX      DisplayString
        MAX-ACCESS  read-create
        STATUS      current
        DESCRIPTION
            "Valid value of VLAN ID can be any value in
            'Specific 1~4095' or 'range 1-4095' or 'Any'."
        ::= {     sm24tat4xbQosQceEntry 7 }

    sm24tat4xbQosPCP OBJECT-TYPE
        SYNTAX      DisplayString
        MAX-ACCESS  read-create
        STATUS      current
        DESCRIPTION
            "Priority Code Point: Valid value PCP are
            specific(0, 1, 2, 3, 4, 5, 6, 7)
            or range(0-1, 2-3, 4-5, 6-7, 0-3, 4-7) or 'Any'."
        ::= {     sm24tat4xbQosQceEntry 8 }

    sm24tat4xbQosDEI OBJECT-TYPE
        SYNTAX      DisplayString
        MAX-ACCESS  read-create
        STATUS      current
        DESCRIPTION
            "Drop Eligible Indicator: Valid value of DEI can be
            any of values between 0, 1 or 'Any'."
        ::= {     sm24tat4xbQosQceEntry 9 }

    sm24tat4xbQosSMAC  OBJECT-TYPE
        SYNTAX      DisplayString
        MAX-ACCESS  read-create
        STATUS      current
        DESCRIPTION
            "Source MAC address: xx-xx-xx-xx-xx-xx or 'Any'."
        ::= {     sm24tat4xbQosQceEntry 10 }

    sm24tat4xbQosDMACType OBJECT-TYPE
        SYNTAX      DisplayString
        MAX-ACCESS  read-create
        STATUS      current
        DESCRIPTION
            "Destination MAC type: possible values are 'UC'(unicast),
            'MC'(multicast), 'BC'(broadcast), 'SP'(Specific) or 'Any'."
        ::= {     sm24tat4xbQosQceEntry 11 }

    sm24tat4xbQosDMACValue OBJECT-TYPE
        SYNTAX      DisplayString
        MAX-ACCESS  read-create
        STATUS      current
        DESCRIPTION
            "when QosDMACType is 'SP'(specific) can set mac address.
            "
        ::= {     sm24tat4xbQosQceEntry 12 }

    sm24tat4xbQosQceInnerTag OBJECT-TYPE
        SYNTAX      DisplayString
        MAX-ACCESS  read-create
        STATUS      current
        DESCRIPTION
            "Value of Inner Tag field can be 'Any', 'Untagged' or 'Tagged' or
            'C-tagged' or 'S-tagged'."
        ::= {     sm24tat4xbQosQceEntry 13 }

    sm24tat4xbQosQceInnerVID OBJECT-TYPE
        SYNTAX      DisplayString
        MAX-ACCESS  read-create
        STATUS      current
        DESCRIPTION
            "Valid value of Inner VLAN ID can be any value in
            'Specific 1~4095' or 'range 1-4095' or 'Any'.
            "
        ::= {     sm24tat4xbQosQceEntry 14 }

    sm24tat4xbQosInnerPCP OBJECT-TYPE
        SYNTAX      DisplayString
        MAX-ACCESS  read-create
        STATUS      current
        DESCRIPTION
            "Valid value Inner PCP are specific(0, 1, 2, 3, 4, 5, 6, 7)
            or range(0-1, 2-3, 4-5, 6-7, 0-3, 4-7) or 'Any'.
            "
        ::= {     sm24tat4xbQosQceEntry 15 }

    sm24tat4xbQosInnerDEI OBJECT-TYPE
        SYNTAX      DisplayString
        MAX-ACCESS  read-create
        STATUS      current
        DESCRIPTION
            "Valid value of Inner DEI can be any of values between
            0, 1 or 'Any'.
            "
        ::= {     sm24tat4xbQosQceEntry 16 }

    sm24tat4xbQosFrameType OBJECT-TYPE
        SYNTAX      INTEGER {
                any(1),
                ethernet(2),
                llc(3),
                snap(4),
                ipv4(5),
                ipv6(6)
                }
        MAX-ACCESS  read-create
        STATUS      current
        DESCRIPTION
            "Frame Type can have any of the following values:
            1: Any,
            2: Ethernet,
            3: LLC,
            4: SNAP,
            5: IPv4,
            6: IPv6."
        ::= {     sm24tat4xbQosQceEntry 17 }

    sm24tat4xbQosMacEtherType OBJECT-TYPE
        SYNTAX      DisplayString
        MAX-ACCESS  read-create
        STATUS      current
        DESCRIPTION
            "Valid ethernet type can have a value within 0x600-0xFFFF or 'Any' ,
            but excluding 0x800(IPv4) and 0x86DD(IPv6),
            range: 0000-FFFF,
            default: Any."
        ::= {     sm24tat4xbQosQceEntry 18 }

    sm24tat4xbQosLLCSSAPAddr OBJECT-TYPE
        SYNTAX      DisplayString
        MAX-ACCESS  read-create
        STATUS      current
        DESCRIPTION
            "Valid SSAP(Source Service Access Point) can vary from
            0x00 to 0xFF or 'Any',
            range: 00-FF,
            default: Any."
        ::= {     sm24tat4xbQosQceEntry 19 }

    sm24tat4xbQosLLCDSAPAddr OBJECT-TYPE
        SYNTAX      DisplayString
        MAX-ACCESS  read-create
        STATUS      current
        DESCRIPTION
            "Valid DSAP(Destination Service Access Point) can
            vary from 0x00 to 0xFF or 'Any',
            range: 00-FF,
            default: Any."
        ::= {     sm24tat4xbQosQceEntry 20 }

    sm24tat4xbQosLLCControl OBJECT-TYPE
        SYNTAX      DisplayString
        MAX-ACCESS  read-create
        STATUS      current
        DESCRIPTION
            "Valid Control field can vary from 0x00 to 0xFF or 'Any',
            range: 00-FF,
            default: Any."
        ::= {     sm24tat4xbQosQceEntry 21 }

    sm24tat4xbQosSNAPPID OBJECT-TYPE
        SYNTAX      DisplayString
        MAX-ACCESS  read-create
        STATUS      current
        DESCRIPTION
            "Valid PID(a.k.a ethernet type) can have value within
            0x00-0xFFFF or 'Any',
            range: 0000-FFFF,
            default: Any."
        ::= {     sm24tat4xbQosQceEntry 22 }

    sm24tat4xbQosIpv4Protocol OBJECT-TYPE
        SYNTAX      DisplayString
        MAX-ACCESS  read-create
        STATUS      current
        DESCRIPTION
            "IP protocol number: (Other, TCP or UDP) or 'Any'."
        ::= {     sm24tat4xbQosQceEntry 23 }

    sm24tat4xbQosIpv4ProtocolValue  OBJECT-TYPE
        SYNTAX      Integer32(0..255)
        MAX-ACCESS  read-create
        STATUS      current
        DESCRIPTION
            "Ipv4 Protocol is Other.
            range: 0-255
            default: 0."
        ::= {     sm24tat4xbQosQceEntry 24 }

    sm24tat4xbQosIpv4ProtocolUDPSPort OBJECT-TYPE
        SYNTAX      DisplayString
        MAX-ACCESS  read-create
        STATUS      current
        DESCRIPTION
            "Source  TCP/UDP Port:(0-65535) or 'Any',
            specific or port range applicable for IP protocol UDP/TCP."
        ::= {     sm24tat4xbQosQceEntry 25 }

    sm24tat4xbQosIpv4ProtocolUDPDPort OBJECT-TYPE
        SYNTAX      DisplayString
        MAX-ACCESS  read-create
        STATUS      current
        DESCRIPTION
            "Destination TCP/UDP port:(0-65535) or 'Any',
            specific or port range applicable for IP protocol UDP/TCP."
        ::= {     sm24tat4xbQosQceEntry 26 }

    sm24tat4xbQosIpv4ProtocolTCPSPort OBJECT-TYPE
        SYNTAX      DisplayString
        MAX-ACCESS  read-create
        STATUS      current
        DESCRIPTION
            "Source TCP/UDP port:(0-65535) or 'Any',
            specific or port range applicable for IP protocol UDP/TCP."
        ::= {     sm24tat4xbQosQceEntry 27 }

    sm24tat4xbQosIpv4ProtocolTCPDPort OBJECT-TYPE
        SYNTAX      DisplayString
        MAX-ACCESS  read-create
        STATUS      current
        DESCRIPTION
            "Destination TCP/UDP port:(0-65535) or 'Any',
            specific or port range applicable for IP protocol UDP/TCP."
        ::= {     sm24tat4xbQosQceEntry 28 }

    sm24tat4xbQosIpv4SourceIp OBJECT-TYPE
        SYNTAX      DisplayString
        MAX-ACCESS  read-create
        STATUS      current
        DESCRIPTION
            "Specific Source IP address in value format or value 0.0.0.0 is 'Any'.
            if Ipv4 Mask value 0.0.0.0 is 'Any' ,IP address value also is 'Any'.
            (x.y.z.w),x=0 unless y.z.w also 0,x not is 127 or greater than 223."
        ::= {     sm24tat4xbQosQceEntry 29 }

    sm24tat4xbQosIpv4SourceMask OBJECT-TYPE
        SYNTAX      DisplayString
        MAX-ACCESS  read-create
        STATUS      current
        DESCRIPTION
            "Specific Source IP address in mask format or value 0.0.0.0 is 'Any'."
        ::= {     sm24tat4xbQosQceEntry 30 }

    sm24tat4xbQosIpv4DestIp OBJECT-TYPE
        SYNTAX      DisplayString
        MAX-ACCESS  read-create
        STATUS      current
        DESCRIPTION
            "Specific Destination IP address in value format or value 0.0.0.0 is 'Any'.
            if Ipv4 Mask value 0.0.0.0 is 'Any' ,IP address value also is 'Any'.
            (x.y.z.w),x=0 unless y.z.w also 0,x not is 127 or greater than 223."
        ::= {     sm24tat4xbQosQceEntry 31 }

    sm24tat4xbQosIpv4DestMask OBJECT-TYPE
        SYNTAX      DisplayString
        MAX-ACCESS  read-create
        STATUS      current
        DESCRIPTION
            "Specific Destination IP address in mask format or value 0.0.0.0 is 'Any'."
        ::= {     sm24tat4xbQosQceEntry 32 }

    sm24tat4xbQosIpv4IPFragment OBJECT-TYPE
        SYNTAX      INTEGER { any(0), no(1), yes(2) }
        MAX-ACCESS  read-create
        STATUS      current
        DESCRIPTION
            "IPv4 frame fragmented option:
            2: yes,
            1: no,
            0: any."
        ::= {     sm24tat4xbQosQceEntry 33 }

    sm24tat4xbQosIpv4DSCP OBJECT-TYPE
        SYNTAX      DisplayString
        MAX-ACCESS  read-create
        STATUS      current
        DESCRIPTION
            "Diffserv Code Point value (DSCP): It can be a specific value,
            range of values or 'Any'. DSCP values are in the range 0-63."
        ::= {     sm24tat4xbQosQceEntry 34 }

    sm24tat4xbQosIpv6Protocol OBJECT-TYPE
        SYNTAX      DisplayString
        MAX-ACCESS  read-create
        STATUS      current
        DESCRIPTION
            "IP protocol number: (Other, TCP or UDP) or 'Any'."
        ::= {     sm24tat4xbQosQceEntry 35 }

    sm24tat4xbQosIpv6ProtocolValue OBJECT-TYPE
        SYNTAX      Integer32(0..255)
        MAX-ACCESS  read-create
        STATUS      current
        DESCRIPTION
            "when IPv6 protocol is Other ,
            range: 0-255."
        ::= {     sm24tat4xbQosQceEntry 36 }

    sm24tat4xbQosIpv6ProtocolUDPSPort OBJECT-TYPE
        SYNTAX      DisplayString
        MAX-ACCESS  read-create
        STATUS      current
        DESCRIPTION
            "Source TCP/UDP port:(0-65535) or 'Any',
            specific or port range applicable for IP protocol UDP/TCP."
        ::= {     sm24tat4xbQosQceEntry 37 }

    sm24tat4xbQosIpv6ProtocolUDPDPort OBJECT-TYPE
        SYNTAX      DisplayString
        MAX-ACCESS  read-create
        STATUS      current
        DESCRIPTION
            "Destination TCP/UDP port:(0-65535) or 'Any',
            specific or port range applicable for IP protocol UDP/TCP."
        ::= {     sm24tat4xbQosQceEntry 38 }

    sm24tat4xbQosIpv6ProtocolTCPSPort OBJECT-TYPE
        SYNTAX      DisplayString
        MAX-ACCESS  read-create
        STATUS      current
        DESCRIPTION
            "Source TCP/UDP port:(0-65535) or 'Any',
            specific or port range applicable for IP protocol UDP/TCP."
        ::= {     sm24tat4xbQosQceEntry 39 }


    sm24tat4xbQosIpv6ProtocolTCPDPort OBJECT-TYPE
        SYNTAX      DisplayString
        MAX-ACCESS  read-create
        STATUS      current
        DESCRIPTION
            "Destination TCP/UDP port:(0-65535) or 'Any',
            specific or port range applicable for IP protocol UDP/TCP."
        ::= {     sm24tat4xbQosQceEntry 40 }

    sm24tat4xbQosIpv6SourceIp OBJECT-TYPE
        SYNTAX      DisplayString
        MAX-ACCESS  read-create
        STATUS      current
        DESCRIPTION
            "IPv6 source address: (a.b.c.d) or value 0.0.0.0 is 'Any', 32 LS bits."
        ::= {     sm24tat4xbQosQceEntry 41 }

    sm24tat4xbQosIpv6SourceMask OBJECT-TYPE
        SYNTAX      DisplayString
        MAX-ACCESS  read-create
        STATUS      current
        DESCRIPTION
            "IPv6 mask address: (a.b.c.d) or value 0.0.0.0 is 'Any', 32 LS bits."
        ::= {     sm24tat4xbQosQceEntry 42 }

    sm24tat4xbQosIpv6DestIp OBJECT-TYPE
        SYNTAX      DisplayString
        MAX-ACCESS  read-create
        STATUS      current
        DESCRIPTION
            "IPv6 destination address: (a.b.c.d) or value 0.0.0.0 is 'Any', 32 LS bits."
        ::= {     sm24tat4xbQosQceEntry 43 }

    sm24tat4xbQosIpv6DestMask OBJECT-TYPE
        SYNTAX      DisplayString
        MAX-ACCESS  read-create
        STATUS      current
        DESCRIPTION
            "IPv6 mask address: (a.b.c.d) or value 0.0.0.0 is 'Any', 32 LS bits."
        ::= {     sm24tat4xbQosQceEntry 44 }

    sm24tat4xbQosIpv6DSCP OBJECT-TYPE
        SYNTAX      DisplayString
        MAX-ACCESS  read-create
        STATUS      current
        DESCRIPTION
            "Diffserv Code Point value (DSCP): It can be a specific value,
            range of values or 'Any'. DSCP values are in the
            range 0-63 including BE,
            CS1-CS7, EF or AF11-AF43."
        ::= {     sm24tat4xbQosQceEntry 45 }

    sm24tat4xbQosActionQueuePriority  OBJECT-TYPE
        SYNTAX      Integer32(0..8)
        MAX-ACCESS  read-create
        STATUS      current
        DESCRIPTION
            "QoS class: (0-7) or 8: Default."
        ::= {     sm24tat4xbQosQceEntry 46 }

    sm24tat4xbQosActionDPL OBJECT-TYPE
        SYNTAX      Integer32 (0..4)
        MAX-ACCESS  read-create
        STATUS      current
        DESCRIPTION
            "range:0-4. 4: Default"
        ::= {     sm24tat4xbQosQceEntry 47 }

    sm24tat4xbQosActionDSCP OBJECT-TYPE
        SYNTAX      Integer32(0..64)
        MAX-ACCESS  read-create
        STATUS      current
        DESCRIPTION
            "Valid DSCP value can be (0-63, BE, CS1-CS7,
            EF or AF11-AF43) or 64: Default."
        ::= {     sm24tat4xbQosQceEntry 48 }

    sm24tat4xbQosActionPCP  OBJECT-TYPE
        SYNTAX      Integer32(0..8)
        MAX-ACCESS  read-create
        STATUS      current
        DESCRIPTION
            "pcp: (0-7) or 8: Default.
            "
        ::= {     sm24tat4xbQosQceEntry 49 }

    sm24tat4xbQosActionDEI OBJECT-TYPE
        SYNTAX      Integer32 (0..2)
        MAX-ACCESS  read-create
        STATUS      current
        DESCRIPTION
            "dei: (0-1) or 2: Default.
            "
        ::= {     sm24tat4xbQosQceEntry 50 }

    sm24tat4xbQosActionPolicy OBJECT-TYPE
        SYNTAX      Integer32(0..128)
        MAX-ACCESS  read-create
        STATUS      current
        DESCRIPTION
            "ACL Policy number: (0-127) or 'empty'(128). Default: empty.
            "
        ::= {     sm24tat4xbQosQceEntry 51 }

    sm24tat4xbQosActionIngressMapID OBJECT-TYPE
        SYNTAX      Integer32(-1..255)
        MAX-ACCESS  read-create
        STATUS      current
        DESCRIPTION
            "Classify Ingress Map ID:
            Range: 0-255
            Default: -1
            "
        ::= {     sm24tat4xbQosQceEntry 52 }

    sm24tat4xbQosQceRowStatus OBJECT-TYPE
        SYNTAX      RowStatus
        MAX-ACCESS  read-create
        STATUS      current
        DESCRIPTION
            "This object indicates the status of this entry, and is used
            to create/delete entries.  Any object in an entry of this table
            may be modified while the value of the corresponding instance
            of this object is active(1).
            createAndGo, notReady not supported."
        ::= {     sm24tat4xbQosQceEntry 53 }

--
-- =======================================================================================================================
-- Start  sm24tat4xbQosStormControl group
-- =======================================================================================================================
--sm24tat4xbQosStormControlTable
    sm24tat4xbQosStormControlTable OBJECT-TYPE
        SYNTAX      SEQUENCE OF     SM24TAT4XBQosStormControlEntry
        MAX-ACCESS  not-accessible
        STATUS      current
        DESCRIPTION
            "The basic QoS DSCP Translation settings for all switches."
        ::= {     sm24tat4xbQosStormControl  1 }

    sm24tat4xbQosStormControlEntry OBJECT-TYPE
        SYNTAX      SM24TAT4XBQosStormControlEntry
        MAX-ACCESS  not-accessible
        STATUS      current
        DESCRIPTION
            "The Qos Storm Control Entry."
        INDEX    {     sm24tat4xbQosStormControlFrameType  }
        ::= {     sm24tat4xbQosStormControlTable 1 }

    SM24TAT4XBQosStormControlEntry         ::= SEQUENCE {
        sm24tat4xbQosStormControlFrameType    INTEGER,
        sm24tat4xbQosStormControlEnabled      AdminMode,
        sm24tat4xbQosStormControlRate         Integer32,
        sm24tat4xbQosStormControlUnit         Integer32
        }

    sm24tat4xbQosStormControlFrameType OBJECT-TYPE
        SYNTAX      INTEGER { unicast(1), multicast (2), broadcast (3)}
        MAX-ACCESS  not-accessible
        STATUS      current
        DESCRIPTION
            "The settings in a particular row apply to the frame type listed here.
            1:Unicast,
            2:Multicast,
            3:Broadcast."
        ::= {     sm24tat4xbQosStormControlEntry 1 }

    sm24tat4xbQosStormControlEnabled OBJECT-TYPE
        SYNTAX      AdminMode
        MAX-ACCESS  read-write
        STATUS      current
        DESCRIPTION
          "Enable or disable the global storm policer for the given frame type."
        ::= {     sm24tat4xbQosStormControlEntry 2 }

    sm24tat4xbQosStormControlRate OBJECT-TYPE
        SYNTAX      Integer32
        MAX-ACCESS  read-write
        STATUS      current
        DESCRIPTION
            "Controls the rate for the global storm policer."
        ::= {     sm24tat4xbQosStormControlEntry 3 }

    sm24tat4xbQosStormControlUnit OBJECT-TYPE
        SYNTAX      Integer32
        MAX-ACCESS  read-write
        STATUS      current
        DESCRIPTION
            "Controls the unit of measure for the global storm policer rate as fps or kfps.
            0: kbps
            1: Mbps
            2: fps
            3: kfps"
        ::= {     sm24tat4xbQosStormControlEntry 4 }

--
-- =======================================================================================================================
-- Start  sm24tat4xbQosPortStormControl group
-- =======================================================================================================================
--sm24tat4xbQosPortStormControlTable
    sm24tat4xbQosPortStormControlTable OBJECT-TYPE
        SYNTAX      SEQUENCE OF     SM24TAT4XBQosPortStormControlEntry
        MAX-ACCESS  not-accessible
        STATUS      current
        DESCRIPTION
            "Configure the storm control settings.
            INDEX for this table is ifIndex which is
            equivalent to the panel port number."
        ::= {     sm24tat4xbQosPortStormControl  1 }

    sm24tat4xbQosPortStormControlEntry OBJECT-TYPE
        SYNTAX      SM24TAT4XBQosPortStormControlEntry
        MAX-ACCESS  not-accessible
        STATUS      current
        DESCRIPTION
            "The Qos Port Storm Control Entry."
        INDEX    {     ifIndex  }
        ::= {     sm24tat4xbQosPortStormControlTable 1 }

    SM24TAT4XBQosPortStormControlEntry         ::= SEQUENCE {
        sm24tat4xbQosPortStormControlUnicastEnabled    AdminMode,
        sm24tat4xbQosPortStormControlUnicastRate      Integer32,
        sm24tat4xbQosPortStormControlUnicastUnit      Integer32,
        sm24tat4xbQosPortStormControlBroadcastEnabled AdminMode,
        sm24tat4xbQosPortStormControlBroadcastRate    Integer32,
        sm24tat4xbQosPortStormControlBroadcastUnit    Integer32,
        sm24tat4xbQosPortStormControlUnknownEnabled    AdminMode,
        sm24tat4xbQosPortStormControlUnknownRate      Integer32,
        sm24tat4xbQosPortStormControlUnknownUnit      Integer32
        }

     sm24tat4xbQosPortStormControlUnicastEnabled OBJECT-TYPE
        SYNTAX      AdminMode
        MAX-ACCESS  read-write
        STATUS      current
        DESCRIPTION
          "Controls whether the storm control is enabled on this
            switch port."
        ::= {     sm24tat4xbQosPortStormControlEntry 2 }

    sm24tat4xbQosPortStormControlUnicastRate OBJECT-TYPE
        SYNTAX      Integer32
        MAX-ACCESS  read-write
        STATUS      current
        DESCRIPTION
            "Controls the rate for the storm control."
        ::= {     sm24tat4xbQosPortStormControlEntry 3 }

    sm24tat4xbQosPortStormControlUnicastUnit OBJECT-TYPE
        SYNTAX      Integer32
        MAX-ACCESS  read-write
        STATUS      current
        DESCRIPTION
            "Controls the unit of measure for the storm control rate.
            0: kbps
            1: Mbps
            2: fps
            3: kfps"
        ::= {     sm24tat4xbQosPortStormControlEntry 4 }

     sm24tat4xbQosPortStormControlBroadcastEnabled  OBJECT-TYPE
        SYNTAX      AdminMode
        MAX-ACCESS  read-write
        STATUS      current
        DESCRIPTION
          "Controls whether the storm control is enabled on this
            switch port."
        ::= {     sm24tat4xbQosPortStormControlEntry 5 }

    sm24tat4xbQosPortStormControlBroadcastRate OBJECT-TYPE
        SYNTAX      Integer32
        MAX-ACCESS  read-write
        STATUS      current
        DESCRIPTION
            "Controls the rate for the storm control."
        ::= {     sm24tat4xbQosPortStormControlEntry 6 }

    sm24tat4xbQosPortStormControlBroadcastUnit OBJECT-TYPE
        SYNTAX      Integer32
        MAX-ACCESS  read-write
        STATUS      current
        DESCRIPTION
            "Controls the unit of measure for the storm control rate.
            0: kbps
            1: Mbps
            2: fps
            3: kfps"
        ::= {     sm24tat4xbQosPortStormControlEntry 7 }

    sm24tat4xbQosPortStormControlUnknownEnabled  OBJECT-TYPE
        SYNTAX      AdminMode
        MAX-ACCESS  read-write
        STATUS      current
        DESCRIPTION
          "Controls whether the storm control is enabled on this
            switch port."
        ::= {     sm24tat4xbQosPortStormControlEntry 8 }

    sm24tat4xbQosPortStormControlUnknownRate OBJECT-TYPE
        SYNTAX      Integer32
        MAX-ACCESS  read-write
        STATUS      current
        DESCRIPTION
            "Controls the rate for the storm control."
        ::= {     sm24tat4xbQosPortStormControlEntry 9 }

    sm24tat4xbQosPortStormControlUnknownUnit OBJECT-TYPE
        SYNTAX      Integer32
        MAX-ACCESS  read-write
        STATUS      current
        DESCRIPTION
            "Controls the unit of measure for the storm control rate.
            0: kbps
            1: Mbps
            2: fps
            3: kfps"
        ::= {     sm24tat4xbQosPortStormControlEntry 10 }

--
-- =======================================================================================================================
-- Start  sm24tat4xbQosWRED group
-- =======================================================================================================================
--sm24tat4xbQosWREDTable
    sm24tat4xbQosWREDTable OBJECT-TYPE
        SYNTAX      SEQUENCE OF     SM24TAT4XBQosWREDEntry
        MAX-ACCESS  not-accessible
        STATUS      current
        DESCRIPTION
            "The basic QoS DSCP Translation settings for all switches."
        ::= {     sm24tat4xbQosWRED  1 }

    sm24tat4xbQosWREDEntry OBJECT-TYPE
        SYNTAX      SM24TAT4XBQosWREDEntry
        MAX-ACCESS  not-accessible
        STATUS      current
        DESCRIPTION
            "The Qos WRED Entry."
        INDEX    {     sm24tat4xbQosWREDQueue  }
        ::= {     sm24tat4xbQosWREDTable 1 }

    SM24TAT4XBQosWREDEntry         ::= SEQUENCE {
        sm24tat4xbQosWREDGroupIndex      Integer32,
        sm24tat4xbQosWREDQueue        Integer32,
        sm24tat4xbQosWREDDPL         Integer32,
        sm24tat4xbQosWREDEnable      AdminMode,
        sm24tat4xbQosWREDMinThreshold    Integer32,
        sm24tat4xbQosWREDMaxThreshold    Integer32,
        sm24tat4xbQosWREDMaxUnit     INTEGER
        }

    sm24tat4xbQosWREDGroupIndex OBJECT-TYPE
        SYNTAX      Integer32
        MAX-ACCESS  not-accessible
        STATUS      current
        DESCRIPTION
            "The group number for which the configuration
            below applies."
        ::= {     sm24tat4xbQosWREDEntry 1 }

    sm24tat4xbQosWREDQueue OBJECT-TYPE
        SYNTAX      Integer32(1..65535)
        MAX-ACCESS  not-accessible
        STATUS      current
        DESCRIPTION
            "The queue number (QoS class) for which the configuration
            below applies."
        ::= {     sm24tat4xbQosWREDEntry 2 }

    sm24tat4xbQosWREDDPL OBJECT-TYPE
        SYNTAX      Integer32
        MAX-ACCESS  not-accessible
        STATUS      current
        DESCRIPTION
            "The dpl number for which the configuration
            below applies."
        ::= {     sm24tat4xbQosWREDEntry 3 }


    sm24tat4xbQosWREDEnable OBJECT-TYPE
        SYNTAX      AdminMode
        MAX-ACCESS  read-write
        STATUS      current
        DESCRIPTION
          "Controls whether RED is enabled for this queue.
          "
        DEFVAL  { disable }
        ::= {     sm24tat4xbQosWREDEntry 4 }

    sm24tat4xbQosWREDMinThreshold OBJECT-TYPE
        SYNTAX      Integer32(0..100)
        MAX-ACCESS  read-write
        STATUS      current
        DESCRIPTION
            "Controls the lower RED fill level threshold. If the queue filling
            level is below this threshold, the drop probability is zero.
            range:0-100%,
            default: 0.
          "
        ::= {     sm24tat4xbQosWREDEntry 5 }

    sm24tat4xbQosWREDMaxThreshold OBJECT-TYPE
        SYNTAX      Integer32(0..100)
        MAX-ACCESS  read-write
        STATUS      current
        DESCRIPTION
            "Controls the upper RED drop probability or fill level threshold
            for frames marked with Drop Precedence Level 1 (yellow frames).
            range:0-100%,
            default: 50.
          "
        ::= {     sm24tat4xbQosWREDEntry 6 }

    sm24tat4xbQosWREDMaxUnit OBJECT-TYPE
        SYNTAX      INTEGER {dropProbability (0), fillLevel (1) }
        MAX-ACCESS  read-write
        STATUS      current
        DESCRIPTION
            "Selects the unit for Max.
            0: Drop Probability,
            1: Fill Level,
            default: Drop Probability.
          "
        DEFVAL  { dropProbability }
        ::= {     sm24tat4xbQosWREDEntry 7 }

--
-- =======================================================================================================================
-- Start  sm24tat4xbQosQCLStatus
-- =======================================================================================================================

--sm24tat4xbQosQCLStatusTable
    sm24tat4xbQosQCLStatusTable OBJECT-TYPE
        SYNTAX      SEQUENCE OF     SM24TAT4XBQosQCLStatusEntry
        MAX-ACCESS  not-accessible
        STATUS      current
        DESCRIPTION
            "The basic QoS DSCP Translation settings for all switches."
        ::= {     sm24tat4xbQosQCLStatus 1 }

    sm24tat4xbQosQCLStatusEntry OBJECT-TYPE
        SYNTAX      SM24TAT4XBQosQCLStatusEntry
        MAX-ACCESS  not-accessible
        STATUS      current
        DESCRIPTION
            "The Qos QCL Status Entry."
        INDEX    {     sm24tat4xbQosQCLStatusList  }
        ::= {     sm24tat4xbQosQCLStatusTable 1 }

    SM24TAT4XBQosQCLStatusEntry         ::= SEQUENCE {
    sm24tat4xbQosQCLStatusList        Integer32,
    sm24tat4xbQosQCLStatusUser        DisplayString,
    sm24tat4xbQosQCLStatusQCEId          DisplayString,
    sm24tat4xbQosQCLStatusFrameType      DisplayString,
    sm24tat4xbQosQCLStatusPortlist        DisplayString,
    sm24tat4xbQosQCLStatusActionQueuePriority DisplayString,
    sm24tat4xbQosQCLStatusActionDPL      DisplayString,
    sm24tat4xbQosQCLStatusActionDSCP     DisplayString,
    sm24tat4xbQosQCLStatusActionPCP      DisplayString,
    sm24tat4xbQosQCLStatusActionDEL      DisplayString,
    sm24tat4xbQosQCLStatusActionPolicy    DisplayString,
    sm24tat4xbQosQCLStatusConflict        DisplayString,
--      sm24tat4xbQosQCLStatusSwitch         Integer32,
		sm24tat4xbQosQCLStatusDMAC        DisplayString,
		sm24tat4xbQosQCLStatusSMAC        DisplayString,
		sm24tat4xbQosQCLStatusTag        DisplayString,
		sm24tat4xbQosQCLStatusVID        DisplayString,
		sm24tat4xbQosQCLStatusPCP        DisplayString,
		sm24tat4xbQosQCLStatusDEI        DisplayString
        }

    sm24tat4xbQosQCLStatusList OBJECT-TYPE
        SYNTAX      Integer32(1..4095)
        MAX-ACCESS  not-accessible
        STATUS      current
        DESCRIPTION
            "QCL table index."
        ::= {     sm24tat4xbQosQCLStatusEntry 1}

    sm24tat4xbQosQCLStatusUser OBJECT-TYPE
        SYNTAX      DisplayString
        MAX-ACCESS  read-only
        STATUS      current
        DESCRIPTION
            "Indicates the QCL user."
        ::= {     sm24tat4xbQosQCLStatusEntry 2 }

    sm24tat4xbQosQCLStatusQCEId OBJECT-TYPE
        SYNTAX      DisplayString
        MAX-ACCESS  read-only
        STATUS      current
        DESCRIPTION
          "Indicates the index of QCE."
        ::= {     sm24tat4xbQosQCLStatusEntry 3}

    sm24tat4xbQosQCLStatusFrameType OBJECT-TYPE
        SYNTAX      DisplayString
        MAX-ACCESS  read-only
        STATUS      current
        DESCRIPTION
            "Indicates the type of frame to look for incomming frames.
            Any: The QCE will match all frame type.
            Ethernet: Only Ethernet frames (with Ether Type 0x600-0xFFFF)
            are allowed.
            LLC: Only (LLC) frames are allowed.
            SNAP: Only (SNAP) frames are allowed.
            IPv4: The QCE will match only IPV4 frames.
            IPv6: The QCE will match only IPV6 frames."
        ::= {     sm24tat4xbQosQCLStatusEntry 4}

    sm24tat4xbQosQCLStatusPortlist OBJECT-TYPE
        SYNTAX      DisplayString
        MAX-ACCESS  read-only
        STATUS      current
        DESCRIPTION
            "Indicates the list of ports configured with the QCE."
        ::= {     sm24tat4xbQosQCLStatusEntry 5}

    sm24tat4xbQosQCLStatusActionQueuePriority OBJECT-TYPE
        SYNTAX      DisplayString
        MAX-ACCESS  read-only
        STATUS      current
        DESCRIPTION
            "Classified QoS class; if a frame matches the
            QCE it will be put in the  queue."
        ::= {     sm24tat4xbQosQCLStatusEntry 6}

    sm24tat4xbQosQCLStatusActionDPL OBJECT-TYPE
        SYNTAX      DisplayString
        MAX-ACCESS  read-only
        STATUS      current
        DESCRIPTION
            "Drop Precedence Level; if a frame matches the QCE then
            DP level will set to value displayed under DPL column."
        ::= {     sm24tat4xbQosQCLStatusEntry 7}

    sm24tat4xbQosQCLStatusActionDSCP OBJECT-TYPE
        SYNTAX      DisplayString
        MAX-ACCESS  read-only
        STATUS      current
        DESCRIPTION
            "If a frame matches the QCE then DSCP will be
            classified with the value
            displayed under DSCP column."
        ::= {     sm24tat4xbQosQCLStatusEntry 8}

    sm24tat4xbQosQCLStatusActionPCP OBJECT-TYPE
        SYNTAX      DisplayString
        MAX-ACCESS  read-only
        STATUS      current
        DESCRIPTION
            "Classify PCP value.
            Only support SERVAL."
        ::= {     sm24tat4xbQosQCLStatusEntry 9}

    sm24tat4xbQosQCLStatusActionDEL OBJECT-TYPE
        SYNTAX      DisplayString
        MAX-ACCESS  read-only
        STATUS      current
        DESCRIPTION
            "Classify DEI value.
            Only support SERVAL."
        ::= {     sm24tat4xbQosQCLStatusEntry 10}

    sm24tat4xbQosQCLStatusActionPolicy OBJECT-TYPE
        SYNTAX      DisplayString
        MAX-ACCESS  read-only
        STATUS      current
        DESCRIPTION
            "Classify ACL Policy number.
            "
        ::= {     sm24tat4xbQosQCLStatusEntry 11}

    sm24tat4xbQosQCLStatusConflict OBJECT-TYPE
        SYNTAX      DisplayString
        MAX-ACCESS  read-only
        STATUS      current
        DESCRIPTION
            "Displays Conflict status of QCL entries."
        ::= {     sm24tat4xbQosQCLStatusEntry 12}

--    sm24tat4xbQosQCLStatusSwitch OBJECT-TYPE
--        SYNTAX      Integer32
--        MAX-ACCESS  read-only
--        STATUS      current
--        DESCRIPTION
--            "Switch number for port members. -1:Any.
--            Only support stacking switch."
--        ::= {     sm24tat4xbQosQCLStatusEntry 13}

    sm24tat4xbQosQCLStatusDMAC OBJECT-TYPE
        SYNTAX      DisplayString
        MAX-ACCESS  read-only
        STATUS      current
        DESCRIPTION
            "Destination MAC address: Possible values are 'Unicast', 'Multicast', 'Broadcast' or 'Any'."
        ::= {     sm24tat4xbQosQCLStatusEntry 14}

    sm24tat4xbQosQCLStatusSMAC OBJECT-TYPE
        SYNTAX      DisplayString
        MAX-ACCESS  read-only
        STATUS      current
        DESCRIPTION
            "Source MAC address: xx-xx-xx-xx-xx-xx or 'Any'."
        ::= {     sm24tat4xbQosQCLStatusEntry 15}

    sm24tat4xbQosQCLStatusTag OBJECT-TYPE
        SYNTAX      DisplayString
        MAX-ACCESS  read-only
        STATUS      current
        DESCRIPTION
            "Value of Tag field can be 'Untagged', 'Tagged', 'C-Tagged', 'S-Tagged' or 'Any'."
        ::= {     sm24tat4xbQosQCLStatusEntry 16}

    sm24tat4xbQosQCLStatusVID OBJECT-TYPE
        SYNTAX      DisplayString
        MAX-ACCESS  read-only
        STATUS      current
        DESCRIPTION
            "Valid value of VLAN ID can be any value in the range 1-4095 or 'Any'"
        ::= {     sm24tat4xbQosQCLStatusEntry 17}

    sm24tat4xbQosQCLStatusPCP OBJECT-TYPE
        SYNTAX      DisplayString
        MAX-ACCESS  read-only
        STATUS      current
        DESCRIPTION
            "Valid value PCP are specific (0, 1, 2, 3, 4, 5, 6, 7) or range (0-1, 2-3, 4-5, 6-7, 0-3, 4-7) or 'Any'."
        ::= {     sm24tat4xbQosQCLStatusEntry 18}

    sm24tat4xbQosQCLStatusDEI OBJECT-TYPE
        SYNTAX      DisplayString
        MAX-ACCESS  read-only
        STATUS      current
        DESCRIPTION
            "Valid value of DEI can be '0', '1' or 'Any'."
        ::= {     sm24tat4xbQosQCLStatusEntry 19}

    sm24tat4xbQosPortShaperTable OBJECT-TYPE
        SYNTAX      SEQUENCE OF     SM24TAT4XBQosPortShaperEntry
        MAX-ACCESS  not-accessible
        STATUS      current
        DESCRIPTION
            "INDEX for this table is ifIndex which is
            equivalent to the panel port number."
        ::= {     sm24tat4xbQosPortShapers 1 }

    sm24tat4xbQosPortShaperEntry OBJECT-TYPE
        SYNTAX      SM24TAT4XBQosPortShaperEntry
        MAX-ACCESS  not-accessible
        STATUS      current
        DESCRIPTION
            "The Qos Port Shaper Entry."
        INDEX    {     ifIndex  }
        ::= {     sm24tat4xbQosPortShaperTable 1 }

    SM24TAT4XBQosPortShaperEntry         ::= SEQUENCE {
        sm24tat4xbQosPortShaperQueue0Enable    AdminMode,
        sm24tat4xbQosPortShaperQueue0Rate     Integer32,
        sm24tat4xbQosPortShaperQueue0Unit     Integer32,
        sm24tat4xbQosPortShaperQueue1Enable    AdminMode,
        sm24tat4xbQosPortShaperQueue1Rate     Integer32,
        sm24tat4xbQosPortShaperQueue1Unit     Integer32,
        sm24tat4xbQosPortShaperQueue2Enable    AdminMode,
        sm24tat4xbQosPortShaperQueue2Rate     Integer32,
        sm24tat4xbQosPortShaperQueue2Unit     Integer32,
        sm24tat4xbQosPortShaperQueue3Enable    AdminMode,
        sm24tat4xbQosPortShaperQueue3Rate     Integer32,
        sm24tat4xbQosPortShaperQueue3Unit     Integer32,
        sm24tat4xbQosPortShaperQueue4Enable    AdminMode,
        sm24tat4xbQosPortShaperQueue4Rate     Integer32,
        sm24tat4xbQosPortShaperQueue4Unit     Integer32,
        sm24tat4xbQosPortShaperQueue5Enable    AdminMode,
        sm24tat4xbQosPortShaperQueue5Rate     Integer32,
        sm24tat4xbQosPortShaperQueue5Unit     Integer32,
        sm24tat4xbQosPortShaperQueue6Enable    AdminMode,
        sm24tat4xbQosPortShaperQueue6Rate     Integer32,
        sm24tat4xbQosPortShaperQueue6Unit     Integer32,
        sm24tat4xbQosPortShaperQueue7Enable    AdminMode,
        sm24tat4xbQosPortShaperQueue7Rate     Integer32,
        sm24tat4xbQosPortShaperQueue7Unit     Integer32,
        sm24tat4xbQosPortShaperEnable     AdminMode,
        sm24tat4xbQosPortShaperRate        Integer32,
        sm24tat4xbQosPortShaperRateType    Integer32
        }

    sm24tat4xbQosPortShaperQueue0Enable OBJECT-TYPE
        SYNTAX      AdminMode
        MAX-ACCESS  read-write
        STATUS      current
        DESCRIPTION
            "Controls whether the queue shaper is enabled on this switch port."
        DEFVAL  { disable }
        ::= {     sm24tat4xbQosPortShaperEntry 3 }

    sm24tat4xbQosPortShaperQueue0Rate OBJECT-TYPE
        SYNTAX      Integer32
        MAX-ACCESS  read-write
        STATUS      current
        DESCRIPTION
            "Controls whether the queue shaper rate.
            default: 500(Kbps)"
        ::= {     sm24tat4xbQosPortShaperEntry 4 }

    sm24tat4xbQosPortShaperQueue0Unit OBJECT-TYPE
        SYNTAX      Integer32(0|1)
        MAX-ACCESS  read-write
        STATUS      current
        DESCRIPTION
            "Controls the unit of measure for the queue shaper rate as kbps or Mbps.
            range:
            0:kbs
            1:Mbps
            default: 0(kbps)"
        ::= {     sm24tat4xbQosPortShaperEntry 5 }

    sm24tat4xbQosPortShaperQueue1Enable OBJECT-TYPE
        SYNTAX      AdminMode
        MAX-ACCESS  read-write
        STATUS      current
        DESCRIPTION
            "Controls whether the queue shaper is enabled on this switch port."
        DEFVAL  { disable }
        ::= {     sm24tat4xbQosPortShaperEntry 6 }

    sm24tat4xbQosPortShaperQueue1Rate OBJECT-TYPE
        SYNTAX      Integer32
        MAX-ACCESS  read-write
        STATUS      current
        DESCRIPTION
            "Controls whether the queue shaper rate.
            default: 500(Kbps)"
        ::= {     sm24tat4xbQosPortShaperEntry 7 }

    sm24tat4xbQosPortShaperQueue1Unit OBJECT-TYPE
        SYNTAX      Integer32(0|1)
        MAX-ACCESS  read-write
        STATUS      current
        DESCRIPTION
            "Controls the unit of measure for the queue shaper rate as kbps or Mbps.
            range:
            0:kbs
            1:Mbps
            default: 0(kbps)"
        ::= {     sm24tat4xbQosPortShaperEntry 8 }

    sm24tat4xbQosPortShaperQueue2Enable OBJECT-TYPE
        SYNTAX      AdminMode
        MAX-ACCESS  read-write
        STATUS      current
        DESCRIPTION
            "Controls whether the queue shaper is enabled on this switch port."
        DEFVAL  { disable }
        ::= {     sm24tat4xbQosPortShaperEntry 9 }

    sm24tat4xbQosPortShaperQueue2Rate OBJECT-TYPE
        SYNTAX      Integer32
        MAX-ACCESS  read-write
        STATUS      current
        DESCRIPTION
            "Controls whether the queue shaper rate.
            default: 500(Kbps)"
        ::= {     sm24tat4xbQosPortShaperEntry 10 }

    sm24tat4xbQosPortShaperQueue2Unit OBJECT-TYPE
        SYNTAX      Integer32(0|1)
        MAX-ACCESS  read-write
        STATUS      current
        DESCRIPTION
            "Controls the unit of measure for the queue shaper rate as kbps or Mbps.
            range:
            0:kbs
            1:Mbps
            default: 0(kbps)"
        ::= {     sm24tat4xbQosPortShaperEntry 11 }

    sm24tat4xbQosPortShaperQueue3Enable OBJECT-TYPE
        SYNTAX      AdminMode
        MAX-ACCESS  read-write
        STATUS      current
        DESCRIPTION
            "Controls whether the queue shaper is enabled on this switch port."
        DEFVAL  { disable }
        ::= {     sm24tat4xbQosPortShaperEntry 12 }

    sm24tat4xbQosPortShaperQueue3Rate OBJECT-TYPE
        SYNTAX      Integer32
        MAX-ACCESS  read-write
        STATUS      current
        DESCRIPTION
            "Controls whether the queue shaper rate.
            default: 500(Kbps)"
        ::= {     sm24tat4xbQosPortShaperEntry 13 }

    sm24tat4xbQosPortShaperQueue3Unit OBJECT-TYPE
        SYNTAX      Integer32(0|1)
        MAX-ACCESS  read-write
        STATUS      current
        DESCRIPTION
            "Controls the unit of measure for the queue shaper rate as kbps or Mbps.
            range:
            0:kbs
            1:Mbps
            default: 0(kbps)"
        ::= {     sm24tat4xbQosPortShaperEntry 14 }

    sm24tat4xbQosPortShaperQueue4Enable OBJECT-TYPE
        SYNTAX      AdminMode
        MAX-ACCESS  read-write
        STATUS      current
        DESCRIPTION
            "Controls whether the queue shaper is enabled on this switch port."
        DEFVAL  { disable }
        ::= {     sm24tat4xbQosPortShaperEntry 15 }

    sm24tat4xbQosPortShaperQueue4Rate OBJECT-TYPE
        SYNTAX      Integer32
        MAX-ACCESS  read-write
        STATUS      current
        DESCRIPTION
            "Controls whether the queue shaper rate.
            default: 500(Kbps)"
        ::= {     sm24tat4xbQosPortShaperEntry 16 }

    sm24tat4xbQosPortShaperQueue4Unit OBJECT-TYPE
        SYNTAX      Integer32(0|1)
        MAX-ACCESS  read-write
        STATUS      current
        DESCRIPTION
            "Controls the unit of measure for the queue shaper rate as kbps or Mbps.
            range:
            0:kbs
            1:Mbps
            default: 0(kbps)"
        ::= {     sm24tat4xbQosPortShaperEntry 17 }

    sm24tat4xbQosPortShaperQueue5Enable OBJECT-TYPE
        SYNTAX      AdminMode
        MAX-ACCESS  read-write
        STATUS      current
        DESCRIPTION
            "Controls whether the queue shaper is enabled on this switch port."
        DEFVAL  { disable }
        ::= {     sm24tat4xbQosPortShaperEntry 18 }

    sm24tat4xbQosPortShaperQueue5Rate OBJECT-TYPE
        SYNTAX      Integer32
        MAX-ACCESS  read-write
        STATUS      current
        DESCRIPTION
            "Controls whether the queue shaper rate.
            default: 500(Kbps)"
        ::= {     sm24tat4xbQosPortShaperEntry 19 }

    sm24tat4xbQosPortShaperQueue5Unit OBJECT-TYPE
        SYNTAX      Integer32(0|1)
        MAX-ACCESS  read-write
        STATUS      current
        DESCRIPTION
            "Controls the unit of measure for the queue shaper rate as kbps or Mbps.
            range:
            0:kbs
            1:Mbps
            default: 0(kbps)"
        ::= {     sm24tat4xbQosPortShaperEntry 20 }

    sm24tat4xbQosPortShaperQueue6Enable OBJECT-TYPE
        SYNTAX      AdminMode
        MAX-ACCESS  read-write
        STATUS      current
        DESCRIPTION
            "Controls whether the queue shaper is enabled on this switch port."
        DEFVAL  { disable }
        ::= {     sm24tat4xbQosPortShaperEntry 21 }

    sm24tat4xbQosPortShaperQueue6Rate OBJECT-TYPE
        SYNTAX      Integer32
        MAX-ACCESS  read-write
        STATUS      current
        DESCRIPTION
            "Controls whether the queue shaper rate.
            default: 500(Kbps)"
        ::= {     sm24tat4xbQosPortShaperEntry 22 }

    sm24tat4xbQosPortShaperQueue6Unit OBJECT-TYPE
        SYNTAX      Integer32(0|1)
        MAX-ACCESS  read-write
        STATUS      current
        DESCRIPTION
            "Controls the unit of measure for the queue shaper rate as kbps or Mbps.
            range:
            0:kbs
            1:Mbps
            default: 0(kbps)"
        ::= {     sm24tat4xbQosPortShaperEntry 23 }

    sm24tat4xbQosPortShaperQueue7Enable OBJECT-TYPE
        SYNTAX      AdminMode
        MAX-ACCESS  read-write
        STATUS      current
        DESCRIPTION
            "Controls whether the queue shaper is enabled on this switch port."
        DEFVAL  { disable }
        ::= {     sm24tat4xbQosPortShaperEntry 24 }

    sm24tat4xbQosPortShaperQueue7Rate OBJECT-TYPE
        SYNTAX      Integer32
        MAX-ACCESS  read-write
        STATUS      current
        DESCRIPTION
            "Controls whether the queue shaper rate.
            default: 500(Kbps)"
        ::= {     sm24tat4xbQosPortShaperEntry 25 }

    sm24tat4xbQosPortShaperQueue7Unit OBJECT-TYPE
        SYNTAX      Integer32(0|1)
        MAX-ACCESS  read-write
        STATUS      current
        DESCRIPTION
            "Controls the unit of measure for the queue shaper rate as kbps or Mbps.
            range:
            0:kbs
            1:Mbps
            default: 0(kbps)"
        ::= {     sm24tat4xbQosPortShaperEntry 26 }

    sm24tat4xbQosPortShaperEnable OBJECT-TYPE
        SYNTAX      AdminMode
        MAX-ACCESS  read-write
        STATUS      current
        DESCRIPTION
            "Controls whether the port shaper is enabled."
        DEFVAL  { disable }
        ::= {     sm24tat4xbQosPortShaperEntry 27 }

    sm24tat4xbQosPortShaperRate OBJECT-TYPE
        SYNTAX      Integer32
        MAX-ACCESS  read-write
        STATUS      current
        DESCRIPTION
            "Controls the rate for the port shaper.
            default: 500 kbps."
        ::= {     sm24tat4xbQosPortShaperEntry 28 }

    sm24tat4xbQosPortShaperRateType OBJECT-TYPE
        SYNTAX      Integer32(0|1)
        MAX-ACCESS  read-write
        STATUS      current
        DESCRIPTION
            "The rate type of the port shaper.
            0:Line
            1:Data"
        ::= {     sm24tat4xbQosPortShaperEntry 29 }

    sm24tat4xbQosPortSchedulersTable OBJECT-TYPE
        SYNTAX      SEQUENCE OF     SM24TAT4XBQosPortSchedulersEntry
        MAX-ACCESS  not-accessible
        STATUS      current
        DESCRIPTION
            "INDEX for this table is ifIndex which is
            equivalent to the panel port number."
        ::= {     sm24tat4xbQosPortSchedulers 1 }

    sm24tat4xbQosPortSchedulersEntry OBJECT-TYPE
        SYNTAX      SM24TAT4XBQosPortSchedulersEntry
        MAX-ACCESS  not-accessible
        STATUS      current
        DESCRIPTION
            "The Qos Port Shaper Entry."
        INDEX    {     ifIndex  }
        ::= {     sm24tat4xbQosPortSchedulersTable 1 }

    SM24TAT4XBQosPortSchedulersEntry         ::= SEQUENCE {
        sm24tat4xbQosPortSchedulersMode     Integer32,
        sm24tat4xbQosPortSchedulersQ0Weight Integer32,
        sm24tat4xbQosPortSchedulersQ1Weight Integer32,
        sm24tat4xbQosPortSchedulersQ2Weight Integer32,
        sm24tat4xbQosPortSchedulersQ3Weight Integer32,
        sm24tat4xbQosPortSchedulersQ4Weight Integer32,
        sm24tat4xbQosPortSchedulersQ5Weight Integer32,
        sm24tat4xbQosPortSchedulersQ6Weight Integer32,
        sm24tat4xbQosPortSchedulersQ7Weight Integer32
        }

    sm24tat4xbQosPortSchedulersMode OBJECT-TYPE
        SYNTAX      Integer32(0|8)
        MAX-ACCESS  read-write
        STATUS      current
        DESCRIPTION
            "0:Strict Priority
            8:Weighted"
        ::= {     sm24tat4xbQosPortSchedulersEntry 2 }

    sm24tat4xbQosPortSchedulersQ0Weight OBJECT-TYPE
        SYNTAX      Integer32(1..100)
        MAX-ACCESS  read-write
        STATUS      current
        DESCRIPTION
            "Controls the weight for this queue. This value is restricted to 1-100."
        ::= {     sm24tat4xbQosPortSchedulersEntry 3 }

    sm24tat4xbQosPortSchedulersQ1Weight OBJECT-TYPE
        SYNTAX      Integer32(1..100)
        MAX-ACCESS  read-write
        STATUS      current
        DESCRIPTION
            "Controls the weight for this queue. This value is restricted to 1-100."
        ::= {     sm24tat4xbQosPortSchedulersEntry 4 }

    sm24tat4xbQosPortSchedulersQ2Weight OBJECT-TYPE
        SYNTAX      Integer32(1..100)
        MAX-ACCESS  read-write
        STATUS      current
        DESCRIPTION
            "Controls the weight for this queue. This value is restricted to 1-100."
        ::= {     sm24tat4xbQosPortSchedulersEntry 5 }

    sm24tat4xbQosPortSchedulersQ3Weight OBJECT-TYPE
        SYNTAX      Integer32(1..100)
        MAX-ACCESS  read-write
        STATUS      current
        DESCRIPTION
            "Controls the weight for this queue. This value is restricted to 1-100."
        ::= {     sm24tat4xbQosPortSchedulersEntry 6 }

    sm24tat4xbQosPortSchedulersQ4Weight OBJECT-TYPE
        SYNTAX      Integer32(1..100)
        MAX-ACCESS  read-write
        STATUS      current
        DESCRIPTION
            "Controls the weight for this queue. This value is restricted to 1-100."
        ::= {     sm24tat4xbQosPortSchedulersEntry 7 }

    sm24tat4xbQosPortSchedulersQ5Weight OBJECT-TYPE
        SYNTAX      Integer32(1..100)
        MAX-ACCESS  read-write
        STATUS      current
        DESCRIPTION
            "Controls the weight for this queue. This value is restricted to 1-100."
        ::= {     sm24tat4xbQosPortSchedulersEntry 8 }

    sm24tat4xbQosPortSchedulersQ6Weight OBJECT-TYPE
        SYNTAX      Integer32(1..100)
        MAX-ACCESS  read-write
        STATUS      current
        DESCRIPTION
            "Controls the weight for this queue. This value is restricted to 1-100."
        ::= {     sm24tat4xbQosPortSchedulersEntry 9 }

    sm24tat4xbQosPortSchedulersQ7Weight OBJECT-TYPE
        SYNTAX      Integer32(1..100)
        MAX-ACCESS  read-write
        STATUS      current
        DESCRIPTION
            "Controls the weight for this queue. This value is restricted to 1-100."
        ::= {     sm24tat4xbQosPortSchedulersEntry 10 }

-- =======================================================================================================================
--sm24tat4xbBroadcastStormProtection                          OBJECT IDENTIFIER ::= { sm24tat4xbConfiguration 11 }
--
--sm24tat4xbBroadcastStormProtectionConfigurationTable OBJECT-TYPE
--    SYNTAX      SEQUENCE OF SM24TAT4XBBroadcastStormProtectionConfigurationEntry
--    MAX-ACCESS  not-accessible
--    STATUS      current
--    DESCRIPTION
--    " Show Broadcast Storm Protection configurations. "
--    ::= { sm24tat4xbBroadcastStormProtection 1 }
--
--sm24tat4xbBroadcastStormProtectionConfigurationEntry OBJECT-TYPE
--    SYNTAX      SM24TAT4XBBroadcastStormProtectionConfigurationEntry
--    MAX-ACCESS  not-accessible
--    STATUS      current
--    DESCRIPTION
--        ""
--    INDEX    { sm24tat4xbBroadcastStormProtectionConfPort  }
--    ::= { sm24tat4xbBroadcastStormProtectionConfigurationTable 1 }
--
--SM24TAT4XBBroadcastStormProtectionConfigurationEntry ::= SEQUENCE {
--    sm24tat4xbBroadcastStormProtectionConfPort	    Integer32,
--    sm24tat4xbBroadcastStormProtectionConfMode	    INTEGER,
--    sm24tat4xbBroadcastStormProtectionConfAction	Integer32,
--    sm24tat4xbBroadcastStormProtectionConfPPS		Integer32,
--    sm24tat4xbBroadcastStormProtectionConfTimer	Integer32,
--    sm24tat4xbBroadcastStormProtectionConfstatus	DisplayString
--}
--
--sm24tat4xbBroadcastStormProtectionConfPort OBJECT-TYPE
--    SYNTAX      Integer32 (1..4095)
--    MAX-ACCESS  not-accessible
--    STATUS      current
--    DESCRIPTION
--    " port, range : 1 - port number. "
--    ::= { sm24tat4xbBroadcastStormProtectionConfigurationEntry 1 }
--
--sm24tat4xbBroadcastStormProtectionConfMode OBJECT-TYPE
--    SYNTAX      INTEGER { disable(0), enable(1)}
--    MAX-ACCESS  read-write
--    STATUS      current
--    DESCRIPTION
--    " Configure broadcast storm protection port mode.
--     0: disable,
--     1: enable
--     default: disable. "
--    ::= { sm24tat4xbBroadcastStormProtectionConfigurationEntry 2 }
--
--sm24tat4xbBroadcastStormProtectionConfAction OBJECT-TYPE
--    SYNTAX      Integer32 (0..2)
--    MAX-ACCESS  read-write
--    STATUS      current
--    DESCRIPTION
--    " Configure broadcast storm protection port action.
--     0: Shutdown port,
--     1: Shutdown port and Log,
--     2: Log Only,
--     default: Shutdown port. "
--    ::= { sm24tat4xbBroadcastStormProtectionConfigurationEntry 3 }
--
--sm24tat4xbBroadcastStormProtectionConfPPS OBJECT-TYPE
--    SYNTAX      Integer32 (0..1000000)
--    MAX-ACCESS  read-write
--    STATUS      current
--    DESCRIPTION
--    " Configure broadcast storm protection pps.
--     default: 0. "
--    ::= { sm24tat4xbBroadcastStormProtectionConfigurationEntry 4 }
--
--sm24tat4xbBroadcastStormProtectionConfTimer OBJECT-TYPE
--    SYNTAX      Integer32 (0..65535)
--    MAX-ACCESS  read-write
--    STATUS      current
--    DESCRIPTION
--    "Configure broadcast storm protection timer(seconds)
--    default: 300(seconds). "
--    ::= { sm24tat4xbBroadcastStormProtectionConfigurationEntry 5 }
--
--sm24tat4xbBroadcastStormProtectionConfstatus OBJECT-TYPE
--    SYNTAX      DisplayString
--    MAX-ACCESS  read-only
--    STATUS      current
--    DESCRIPTION
--    " Show broadcast storm protection status. "
--    ::= { sm24tat4xbBroadcastStormProtectionConfigurationEntry 6 }
--
-- =======================================================================================================================
sm24tat4xbLoopProtection                          OBJECT IDENTIFIER ::= { sm24tat4xbConfiguration 12 }

sm24tat4xbLoopProtectionConfig                        OBJECT IDENTIFIER ::= { sm24tat4xbLoopProtection 1 }

sm24tat4xbLoopProtectionGlobalEnable OBJECT-TYPE
    SYNTAX      Integer32(0|1)
    MAX-ACCESS  read-write
    STATUS      current
    DESCRIPTION
        "Configure loop protection mode.
        0: disable,
        1: enable,
        default: disable. "
    ::= { sm24tat4xbLoopProtectionConfig 1 }

sm24tat4xbLoopProtectionTranmisstionTime OBJECT-TYPE
    SYNTAX      Integer32(1..10)
    MAX-ACCESS  read-write
    STATUS      current
    DESCRIPTION
        "Configure loop protection transmit interval.
        default: 5,
        range: 1-10. "
    ::= { sm24tat4xbLoopProtectionConfig 2 }

sm24tat4xbLoopProtectionShutdownTime OBJECT-TYPE
    SYNTAX      Integer32(0..604800)
    MAX-ACCESS  read-write
    STATUS      current
    DESCRIPTION
        "Configure loop protection shutdown time.
        default: 180,
        range: 0-604800. "
    ::= { sm24tat4xbLoopProtectionConfig 3 }

sm24tat4xbLoopProtectionConfigurationTable OBJECT-TYPE
    SYNTAX      SEQUENCE OF SM24TAT4XBLoopProtectionConfigurationEntry
    MAX-ACCESS  not-accessible
    STATUS      current
    DESCRIPTION
        " Show Loop Protection configurations. "
    ::= { sm24tat4xbLoopProtectionConfig 4 }

sm24tat4xbLoopProtectionConfigurationEntry OBJECT-TYPE
    SYNTAX      SM24TAT4XBLoopProtectionConfigurationEntry
    MAX-ACCESS  not-accessible
    STATUS      current
    DESCRIPTION
        " "
    INDEX    { sm24tat4xbLoopProtectionConfPort  }
    ::= { sm24tat4xbLoopProtectionConfigurationTable 1 }

SM24TAT4XBLoopProtectionConfigurationEntry ::= SEQUENCE {
    sm24tat4xbLoopProtectionConfPort	    Integer32,
    sm24tat4xbLoopProtectionConfEnable	Integer32,
    sm24tat4xbLoopProtectionConfAction	Integer32,
    sm24tat4xbLoopProtectionConfTxmode	Integer32
}

sm24tat4xbLoopProtectionConfPort OBJECT-TYPE
    SYNTAX      Integer32 (1..4095)
    MAX-ACCESS  not-accessible
    STATUS      current
    DESCRIPTION
        " port, range : 1 - port number. "
    ::= { sm24tat4xbLoopProtectionConfigurationEntry 1 }

sm24tat4xbLoopProtectionConfEnable OBJECT-TYPE
    SYNTAX      Integer32(0|1)
    MAX-ACCESS  read-write
    STATUS      current
    DESCRIPTION
        "Configure loop protection port mode.
        0: disable,
        1: enable,
        default: enable. "
    ::= { sm24tat4xbLoopProtectionConfigurationEntry 2 }

sm24tat4xbLoopProtectionConfAction OBJECT-TYPE
    SYNTAX      Integer32(0..2)
    MAX-ACCESS  read-write
    STATUS      current
    DESCRIPTION
        " Configure loop protection port action.
        0: Shutdown port,
        1: Shutdown port and Log,
        2: Log Only,
        default: Shutdown port. "
    ::= { sm24tat4xbLoopProtectionConfigurationEntry 3 }

sm24tat4xbLoopProtectionConfTxmode OBJECT-TYPE
    SYNTAX      Integer32(0|1)
    MAX-ACCESS  read-write
    STATUS      current
    DESCRIPTION
        "Configure loop protection port transmit mode.
        0: disable,
        1: enable,
        default: enable. "
    ::= { sm24tat4xbLoopProtectionConfigurationEntry 4 }

sm24tat4xbLoopProtectionStatusTable OBJECT-TYPE
    SYNTAX      SEQUENCE OF SM24TAT4XBLoopProtectionStatusEntry
    MAX-ACCESS  not-accessible
    STATUS      current
    DESCRIPTION
        " Show Loop Protection Status. "
    ::= { sm24tat4xbLoopProtection 2 }

sm24tat4xbLoopProtectionStatusEntry OBJECT-TYPE
    SYNTAX      SM24TAT4XBLoopProtectionStatusEntry
    MAX-ACCESS  not-accessible
    STATUS      current
    DESCRIPTION
        " "
    INDEX    { sm24tat4xbLoopProtectionStatusPort  }
    ::= { sm24tat4xbLoopProtectionStatusTable 1 }

SM24TAT4XBLoopProtectionStatusEntry ::= SEQUENCE {
    sm24tat4xbLoopProtectionStatusPort	    Integer32,
    sm24tat4xbLoopProtectionStatusAction	    DisplayString,
    sm24tat4xbLoopProtectionStatusTransmit	    DisplayString,
    sm24tat4xbLoopProtectionStatusLoops	    Integer32,
    sm24tat4xbLoopProtectionStatusStatus	    DisplayString,
    sm24tat4xbLoopProtectionStatusLoop	    DisplayString,
    sm24tat4xbLoopProtectionStatusTimeLastLoop  DisplayString
}

sm24tat4xbLoopProtectionStatusPort OBJECT-TYPE
    SYNTAX      Integer32 (1..4095)
    MAX-ACCESS  not-accessible
    STATUS      current
    DESCRIPTION
        " port, range : 1 - port number. "
    ::= { sm24tat4xbLoopProtectionStatusEntry 1 }

sm24tat4xbLoopProtectionStatusAction OBJECT-TYPE
    SYNTAX      DisplayString
    MAX-ACCESS  read-only
    STATUS      current
    DESCRIPTION
        " The currently configured port action. "
    ::= { sm24tat4xbLoopProtectionStatusEntry 2 }

sm24tat4xbLoopProtectionStatusTransmit OBJECT-TYPE
    SYNTAX      DisplayString
    MAX-ACCESS  read-only
    STATUS      current
    DESCRIPTION
        " The currently configured port transmit mode. "
    ::= { sm24tat4xbLoopProtectionStatusEntry 3 }

sm24tat4xbLoopProtectionStatusLoops OBJECT-TYPE
    SYNTAX      Integer32 (0..1000000)
    MAX-ACCESS  read-only
    STATUS      current
    DESCRIPTION
        " The number of loops detected on this port. "
    ::= { sm24tat4xbLoopProtectionStatusEntry 4 }

sm24tat4xbLoopProtectionStatusStatus OBJECT-TYPE
    SYNTAX      DisplayString
    MAX-ACCESS  read-only
    STATUS      current
    DESCRIPTION
        " The current loop protection status of the port. "
    ::= { sm24tat4xbLoopProtectionStatusEntry 5 }

sm24tat4xbLoopProtectionStatusLoop OBJECT-TYPE
    SYNTAX      DisplayString
    MAX-ACCESS  read-only
    STATUS      current
    DESCRIPTION
        " Whether a loop is currently detected on the port. "
    ::= { sm24tat4xbLoopProtectionStatusEntry 6 }

sm24tat4xbLoopProtectionStatusTimeLastLoop OBJECT-TYPE
    SYNTAX      DisplayString
    MAX-ACCESS  read-only
    STATUS      current
    DESCRIPTION
        " The time of the last loop event detected. "
    ::= { sm24tat4xbLoopProtectionStatusEntry 7 }
-- =======================================================================================================================
sm24tat4xbPoe                                OBJECT IDENTIFIER ::= { sm24tat4xbConfiguration 13 }

sm24tat4xbPoeStatus                        OBJECT IDENTIFIER ::= { sm24tat4xbPoe 1 }

sm24tat4xbPoeStatusTable OBJECT-TYPE
    SYNTAX      SEQUENCE OF SM24TAT4XBPoeStatusEntry
    MAX-ACCESS  not-accessible
    STATUS      current
    DESCRIPTION
        " Configure PoE Scheduling Table. "
    ::= { sm24tat4xbPoeStatus 1 }

sm24tat4xbPoeStatusEntry OBJECT-TYPE
    SYNTAX      SM24TAT4XBPoeStatusEntry
    MAX-ACCESS  not-accessible
    STATUS      current
    DESCRIPTION
        " "
    INDEX    { sm24tat4xbPoeStatusLocalPort }
    ::= { sm24tat4xbPoeStatusTable 1 }

SM24TAT4XBPoeStatusEntry ::= SEQUENCE {
    sm24tat4xbPoeStatusLocalPort          Integer32,
    sm24tat4xbPoeStatusPDclass	      DisplayString,
    sm24tat4xbPoeStatusPowerRequested	  DisplayString,
    sm24tat4xbPoeStatusPowerAllocated     DisplayString,
    sm24tat4xbPoeStatusPowerUsed      DisplayString,
    sm24tat4xbPoeStatusCurrentUsed    DisplayString,
    sm24tat4xbPoeStatusPriority        DisplayString,
    sm24tat4xbPoeStatusPortStatus     DisplayString
}

sm24tat4xbPoeStatusLocalPort OBJECT-TYPE
    SYNTAX      Integer32 (1..10)
    MAX-ACCESS  not-accessible
    STATUS      current
    DESCRIPTION
        "Local port Index."
    ::= { sm24tat4xbPoeStatusEntry 1 }


sm24tat4xbPoeStatusPDclass OBJECT-TYPE
    SYNTAX      DisplayString
    MAX-ACCESS  read-only
    STATUS      current
    DESCRIPTION
        " Indicates the QCL user.
        0: Max. power 15.4 W,
        1: Max. power 4.0 W,
        2: Max. power 7.0 W,
        3: Max. power 15.4 W,
        4: Max. power 30.0 W. "
    ::= { sm24tat4xbPoeStatusEntry 2 }

sm24tat4xbPoeStatusPowerRequested OBJECT-TYPE
    SYNTAX      DisplayString
    MAX-ACCESS  read-only
    STATUS      current
    DESCRIPTION
      " The Power Requested shows the requested amount of power the PD wants to be reserved. "
    ::= { sm24tat4xbPoeStatusEntry 3}

sm24tat4xbPoeStatusPowerAllocated OBJECT-TYPE
    SYNTAX      DisplayString
    MAX-ACCESS  read-only
    STATUS      current
    DESCRIPTION
      " The Power Allocated shows the amount of power the switch has allocated for the PD. "
    ::= { sm24tat4xbPoeStatusEntry 4}

sm24tat4xbPoeStatusPowerUsed OBJECT-TYPE
    SYNTAX      DisplayString
    MAX-ACCESS  read-only
    STATUS      current
    DESCRIPTION
      " The Power Used shows how much power the PD currently is using. "
    ::= { sm24tat4xbPoeStatusEntry 5}

sm24tat4xbPoeStatusCurrentUsed OBJECT-TYPE
    SYNTAX      DisplayString
    MAX-ACCESS  read-only
    STATUS      current
    DESCRIPTION
      " The Power Used shows how much current the PD currently is using. "
    ::= { sm24tat4xbPoeStatusEntry 6}

sm24tat4xbPoeStatusPriority OBJECT-TYPE
    SYNTAX      DisplayString
    MAX-ACCESS  read-only
    STATUS      current
    DESCRIPTION
      " The Priority shows the port's priority configured by the user.  "
    ::= { sm24tat4xbPoeStatusEntry 7}

sm24tat4xbPoeStatusPortStatus OBJECT-TYPE
    SYNTAX      DisplayString
    MAX-ACCESS  read-only
    STATUS      current
    DESCRIPTION
      " The Port Status shows the port's status.  "
    ::= { sm24tat4xbPoeStatusEntry 8}

sm24tat4xbPoeStatusTotalTable OBJECT-TYPE
    SYNTAX      SEQUENCE OF SM24TAT4XBPoeStatusTotalEntry
    MAX-ACCESS  not-accessible
    STATUS      current
    DESCRIPTION
        " Configure PoE Scheduling Total Table. "
    ::= { sm24tat4xbPoeStatus 2 }

sm24tat4xbPoeStatusTotalEntry OBJECT-TYPE
    SYNTAX      SM24TAT4XBPoeStatusTotalEntry
    MAX-ACCESS  not-accessible
    STATUS      current
    DESCRIPTION
        " "
    INDEX    { sm24tat4xbPoeStatusSwitchIndex }
    ::= { sm24tat4xbPoeStatusTotalTable 1 }

SM24TAT4XBPoeStatusTotalEntry ::= SEQUENCE {
    sm24tat4xbPoeStatusSwitchIndex        Integer32,
    sm24tat4xbPoeStatusTotalPowerRequested    DisplayString,
    sm24tat4xbPoeStatusTotalPowerAllocated    DisplayString,
    sm24tat4xbPoeStatusTotalPowerUsed     DisplayString,
    sm24tat4xbPoeStatusTotalCurrentUsed    DisplayString
}

sm24tat4xbPoeStatusSwitchIndex OBJECT-TYPE
    SYNTAX      Integer32 (1..16)
    MAX-ACCESS  not-accessible
    STATUS      current
    DESCRIPTION
        "Switch Index."
    ::= { sm24tat4xbPoeStatusTotalEntry 1 }

sm24tat4xbPoeStatusTotalPowerRequested OBJECT-TYPE
    SYNTAX      DisplayString
    MAX-ACCESS  read-only
    STATUS      current
    DESCRIPTION
      " Total Power Requested."
    ::= { sm24tat4xbPoeStatusTotalEntry 2}

sm24tat4xbPoeStatusTotalPowerAllocated OBJECT-TYPE
    SYNTAX      DisplayString
    MAX-ACCESS  read-only
    STATUS      current
    DESCRIPTION
      " Total Power allocated."
    ::= { sm24tat4xbPoeStatusTotalEntry 3}

sm24tat4xbPoeStatusTotalPowerUsed OBJECT-TYPE
    SYNTAX      DisplayString
    MAX-ACCESS  read-only
    STATUS      current
    DESCRIPTION
      " Total Power Used."
    ::= { sm24tat4xbPoeStatusTotalEntry 4}

sm24tat4xbPoeStatusTotalCurrentUsed OBJECT-TYPE
    SYNTAX      DisplayString
    MAX-ACCESS  read-only
    STATUS      current
    DESCRIPTION
      " Total Current Used."
    ::= { sm24tat4xbPoeStatusTotalEntry 5}


sm24tat4xbPoePowerDelay                         OBJECT IDENTIFIER ::= { sm24tat4xbPoe 2 }

sm24tat4xbPoePowerDelayTable OBJECT-TYPE
    SYNTAX      SEQUENCE OF SM24TAT4XBPoePowerDelayEntry
    MAX-ACCESS  not-accessible
    STATUS      current
    DESCRIPTION
        " Configure PoE Power Delay mode. "
    ::= { sm24tat4xbPoePowerDelay 1 }

sm24tat4xbPoePowerDelayEntry OBJECT-TYPE
    SYNTAX      SM24TAT4XBPoePowerDelayEntry
    MAX-ACCESS  not-accessible
    STATUS      current
    DESCRIPTION
        " "
    INDEX    { sm24tat4xbPoePowerDelayPort  }
    ::= { sm24tat4xbPoePowerDelayTable 1 }

SM24TAT4XBPoePowerDelayEntry ::= SEQUENCE {
    sm24tat4xbPoePowerDelayPort	    Integer32,
    sm24tat4xbPoePowerDelayMode	    Integer32,
    sm24tat4xbPoePowerDelayTime	    Integer32
}

sm24tat4xbPoePowerDelayPort OBJECT-TYPE
    SYNTAX      Integer32 (1..4094)
    MAX-ACCESS  not-accessible
    STATUS      current
    DESCRIPTION
        " port, range : 1 - port number. "
    ::= { sm24tat4xbPoePowerDelayEntry 1 }

sm24tat4xbPoePowerDelayMode OBJECT-TYPE
    SYNTAX      Integer32(0|1)
    MAX-ACCESS  read-write
    STATUS      current
    DESCRIPTION
        "Turn on / off the power delay function,
        0: disable,
        1: enable,
        default: disable. "
    ::= { sm24tat4xbPoePowerDelayEntry 2 }

sm24tat4xbPoePowerDelayTime OBJECT-TYPE
    SYNTAX      Integer32(0..300)
    MAX-ACCESS  read-write
    STATUS      current
    DESCRIPTION
        "set Delay Time,
        default: 0,
        range: 0-300 sec. "
    ::= { sm24tat4xbPoePowerDelayEntry 3 }

sm24tat4xbPoeAutoPowerReset                         OBJECT IDENTIFIER ::= { sm24tat4xbPoe 3 }

sm24tat4xbPoeAutoPowerResetPingCheck OBJECT-TYPE
    SYNTAX      INTEGER { disable(0), enable(1) }
    MAX-ACCESS  read-write
    STATUS      current
    DESCRIPTION
        "connection between PoE port and power device.
        0: disable,
        1: enable,
        default: disable. "
    ::= { sm24tat4xbPoeAutoPowerReset 1 }

sm24tat4xbPoeAutoPowerResetTable OBJECT-TYPE
    SYNTAX      SEQUENCE OF SM24TAT4XBPoeAutoPowerResetEntry
    MAX-ACCESS  not-accessible
    STATUS      current
    DESCRIPTION
        " Configure PoE Auto Power Reset mode. "
    ::= { sm24tat4xbPoeAutoPowerReset 2 }

sm24tat4xbPoeAutoPowerResetEntry OBJECT-TYPE
    SYNTAX      SM24TAT4XBPoeAutoPowerResetEntry
    MAX-ACCESS  not-accessible
    STATUS      current
    DESCRIPTION
        " "
    INDEX    { sm24tat4xbPoeAutoPowerResetPort  }
    ::= { sm24tat4xbPoeAutoPowerResetTable 1 }

SM24TAT4XBPoeAutoPowerResetEntry ::= SEQUENCE {
    sm24tat4xbPoeAutoPowerResetPort	    Integer32,
    sm24tat4xbPoeAutoPowerResetPingIPAddress  DisplayString,
    sm24tat4xbPoeAutoPowerResetStartupTime    Integer32,
    sm24tat4xbPoeAutoPowerResetIntervalTime    Integer32,
    sm24tat4xbPoeAutoPowerResetRetryTime      Integer32,
    sm24tat4xbPoeAutoPowerResetFailureLog     DisplayString,
    sm24tat4xbPoeAutoPowerResetFailureAction  INTEGER,
    sm24tat4xbPoeAutoPowerResetRebootTime     Integer32,
    sm24tat4xbPoeAutoPowerResetMaxRebootTimes     Integer32
}

sm24tat4xbPoeAutoPowerResetPort OBJECT-TYPE
    SYNTAX      Integer32(1..4094)
    MAX-ACCESS  not-accessible
    STATUS      current
    DESCRIPTION
        " port, range : 1 - port number. "
    ::= { sm24tat4xbPoeAutoPowerResetEntry 1 }

sm24tat4xbPoeAutoPowerResetPingIPAddress OBJECT-TYPE
    SYNTAX      DisplayString
    MAX-ACCESS  read-write
    STATUS      current
    DESCRIPTION
        "IP Address the system should ping.
        default: 0.0.0.0 . "
    ::= { sm24tat4xbPoeAutoPowerResetEntry 2 }

sm24tat4xbPoeAutoPowerResetStartupTime OBJECT-TYPE
    SYNTAX      Integer32(30..600)
    MAX-ACCESS  read-write
    STATUS      current
    DESCRIPTION
        "When PD has been start up, the Switch will wait Start up time to do PoE Auto Checking. default: 60, range: 30-600 sec. "
    ::= { sm24tat4xbPoeAutoPowerResetEntry 3 }

sm24tat4xbPoeAutoPowerResetIntervalTime OBJECT-TYPE
    SYNTAX      Integer32(10..120)
    MAX-ACCESS  read-write
    STATUS      current
    DESCRIPTION
        "Device will send checking message to PD each interval time.
        default: 30,
        range: 10-120 sec.  "
    ::= { sm24tat4xbPoeAutoPowerResetEntry 4 }

sm24tat4xbPoeAutoPowerResetRetryTime OBJECT-TYPE
    SYNTAX      Integer32(1..5)
    MAX-ACCESS  read-write
    STATUS      current
    DESCRIPTION
        "It will retry to send detection again.
        default: 3,
        range: 1-5.  "
    ::= { sm24tat4xbPoeAutoPowerResetEntry 5 }

sm24tat4xbPoeAutoPowerResetFailureLog OBJECT-TYPE
    SYNTAX      DisplayString
    MAX-ACCESS  read-only
    STATUS      current
    DESCRIPTION
        "Failure loggings counter. "
    ::= { sm24tat4xbPoeAutoPowerResetEntry 6 }

sm24tat4xbPoeAutoPowerResetFailureAction OBJECT-TYPE
    SYNTAX      INTEGER { nothing(0), reboot(1) }
    MAX-ACCESS  read-write
    STATUS      current
    DESCRIPTION
        "It will retry to send detection again,
        0: Nothing,
        1: Reboot Remote PD,
        default: Nothing. "
    ::= { sm24tat4xbPoeAutoPowerResetEntry 7 }

sm24tat4xbPoeAutoPowerResetRebootTime OBJECT-TYPE
    SYNTAX      Integer32(3..120)
    MAX-ACCESS  read-write
    STATUS      current
    DESCRIPTION
        "When PD has been rebooted, the PoE port restored power after the specified time.
        default: 15,
        range: 3-120 sec. "
    ::= { sm24tat4xbPoeAutoPowerResetEntry 8 }

sm24tat4xbPoeAutoPowerResetMaxRebootTimes OBJECT-TYPE
    SYNTAX      Integer32(0..10)
    MAX-ACCESS  read-write
    STATUS      current
    DESCRIPTION
        "When Failure Action is Reboot Remote PD, it limits times of Reboot.
     default: 3,
     range: 0-10. 0 means without reboot limits."
    ::= { sm24tat4xbPoeAutoPowerResetEntry 10 }

sm24tat4xbPoeScheduling                         OBJECT IDENTIFIER ::= { sm24tat4xbPoe 4 }

sm24tat4xbPoeSchedulingProfileNumber OBJECT-TYPE
    SYNTAX      Integer32
    MAX-ACCESS  read-write
    STATUS      current
    DESCRIPTION
        "Specify the PoE Profile Number that want to configure. Range:1-16"
    ::= { sm24tat4xbPoeScheduling 1 }

sm24tat4xbPoeSchedulingPorofileName OBJECT-TYPE
    SYNTAX      DisplayString
    MAX-ACCESS  read-write
    STATUS      current
    DESCRIPTION
        "Profile Name. Maximum length:32."
    ::= { sm24tat4xbPoeScheduling 2 }

sm24tat4xbPoeSchedulingTimeTable OBJECT-TYPE
    SYNTAX      SEQUENCE OF SM24TAT4XBPoeSchedulingTimeEntry
    MAX-ACCESS  not-accessible
    STATUS      current
    DESCRIPTION
        " Show Poe Scheduling Time Config. "
    ::= { sm24tat4xbPoeScheduling 3 }

sm24tat4xbPoeSchedulingTimeEntry OBJECT-TYPE
    SYNTAX      SM24TAT4XBPoeSchedulingTimeEntry
    MAX-ACCESS  not-accessible
    STATUS      current
    DESCRIPTION
        " "
    INDEX    { sm24tat4xbPoeSchedulingTimeWeekIndex  }
    ::= { sm24tat4xbPoeSchedulingTimeTable 1 }

SM24TAT4XBPoeSchedulingTimeEntry ::= SEQUENCE {
    sm24tat4xbPoeSchedulingTimeWeekIndex    Integer32,
    sm24tat4xbPoeSchedulingTimeStartTimeHourMinute  DisplayString,
    sm24tat4xbPoeSchedulingTimeEndTimeHourMinute    DisplayString
}

sm24tat4xbPoeSchedulingTimeWeekIndex OBJECT-TYPE
    SYNTAX      Integer32 (1..7)
    MAX-ACCESS  not-accessible
    STATUS      current
    DESCRIPTION
        "Week Index.
	    1: Mon, 2:Tue, 3: Wed, 4: Thu, 5: Fri, 6: Sat, 7: Sun"
    ::= { sm24tat4xbPoeSchedulingTimeEntry 1 }

sm24tat4xbPoeSchedulingTimeStartTimeHourMinute OBJECT-TYPE
    SYNTAX      DisplayString
    MAX-ACCESS  read-write
    STATUS      current
    DESCRIPTION
        "PoE Scheduling Start Time. Format: HH:MM. Hour Range: 0-23. Minute Range:0,5,10,...,55."
    ::= { sm24tat4xbPoeSchedulingTimeEntry 2 }

sm24tat4xbPoeSchedulingTimeEndTimeHourMinute OBJECT-TYPE
    SYNTAX      DisplayString
    MAX-ACCESS  read-write
    STATUS      current
    DESCRIPTION
        "PoE Scheduling End Time. Format: HH:MM. Hour Range: 0-23. Minute Range:0,5,10,...,55."
    ::= { sm24tat4xbPoeSchedulingTimeEntry 3 }

sm24tat4xbPoeConfiguration                         OBJECT IDENTIFIER ::= { sm24tat4xbPoe 5 }

sm24tat4xbPoeConfigurationPowerManagementMode OBJECT-TYPE
    SYNTAX      Integer32(0..5)
    MAX-ACCESS  read-write
    STATUS      current
    DESCRIPTION
        "The power management mode for PoE port.
        0: CLASS_RESERVED,
        1: CLASS_CONSUMP,
        2: ALLOCATED_RESERVED,
        3: ALLOCATED_CONSUMP,
        4: LLDPMED_RESERVED,
        5: LLDPMED_CONSUMP,
        default: CLASS_RESERVED. "
    ::= { sm24tat4xbPoeConfiguration 1 }

sm24tat4xbPoeConfigurationCapacitorDetection OBJECT-TYPE
    SYNTAX      Integer32(0..1)
    MAX-ACCESS  read-write
    STATUS      current
    DESCRIPTION
        "The capacitor detection mode.
        0: Disable
        1: Enable
    "
    ::= { sm24tat4xbPoeConfiguration 2 }

sm24tat4xbPoeConfigurationTable OBJECT-TYPE
    SYNTAX      SEQUENCE OF SM24TAT4XBPoeConfigurationEntry
    MAX-ACCESS  not-accessible
    STATUS      current
    DESCRIPTION
        " Configure PoE Configuration mode. "
    ::= { sm24tat4xbPoeConfiguration 4 }

sm24tat4xbPoeConfigurationEntry OBJECT-TYPE
    SYNTAX      SM24TAT4XBPoeConfigurationEntry
    MAX-ACCESS  not-accessible
    STATUS      current
    DESCRIPTION
        " "
    INDEX    { sm24tat4xbPoeConfigurationSwitch  }
    ::= { sm24tat4xbPoeConfigurationTable 1 }

SM24TAT4XBPoeConfigurationEntry ::= SEQUENCE {
    sm24tat4xbPoeConfigurationSwitch	          Integer32,
    sm24tat4xbPoeConfigurationPrimaryPowerSupply    Integer32,
    sm24tat4xbPoeConfigurationAlwaysOnPoE    Integer32
}

sm24tat4xbPoeConfigurationSwitch OBJECT-TYPE
    SYNTAX      Integer32 (1..16)
    MAX-ACCESS  not-accessible
    STATUS      current
    DESCRIPTION
        " switch index, range : 1 - 16. "
    ::= { sm24tat4xbPoeConfigurationEntry 1 }

sm24tat4xbPoeConfigurationPrimaryPowerSupply  OBJECT-TYPE
    SYNTAX      Integer32(0..2000)
    MAX-ACCESS  read-only
    STATUS      current
    DESCRIPTION
        "It must be defined what amount of power the primary and backup power sources
    can deliver. "
    ::= { sm24tat4xbPoeConfigurationEntry 3 }

sm24tat4xbPoeConfigurationAlwaysOnPoE  OBJECT-TYPE
    SYNTAX      Integer32(0..1)
    MAX-ACCESS  read-write
    STATUS      current
    DESCRIPTION
        "Configure always-on-poe"
    ::= { sm24tat4xbPoeConfigurationEntry 4 }

sm24tat4xbPoeConfigurationPortTable OBJECT-TYPE
    SYNTAX      SEQUENCE OF SM24TAT4XBPoeConfigurationPortEntry
    MAX-ACCESS  not-accessible
    STATUS      current
    DESCRIPTION
        " Configure PoE Port Configuration mode. "
    ::= { sm24tat4xbPoeConfiguration 5 }

sm24tat4xbPoeConfigurationPortEntry OBJECT-TYPE
    SYNTAX      SM24TAT4XBPoeConfigurationPortEntry
    MAX-ACCESS  not-accessible
    STATUS      current
    DESCRIPTION
        " "
    INDEX    { sm24tat4xbPoeConfigurationPort  }
    ::= { sm24tat4xbPoeConfigurationPortTable 1 }

SM24TAT4XBPoeConfigurationPortEntry ::= SEQUENCE {
    sm24tat4xbPoeConfigurationPort	    Integer32,
    sm24tat4xbPoeConfigurationPortPoEMode    INTEGER,
    sm24tat4xbPoeConfigurationPortPriority      INTEGER,
    sm24tat4xbPoeConfigurationPortMaximumPower  DisplayString,
    sm24tat4xbPoeConfigurationPortDetection     Integer32,
-- sm24tat4xbPoeConfigurationPortPoEScheduleByProfileID     Integer32,
    sm24tat4xbPoeConfigurationPortPoEScheduleByProfileName    DisplayString,
    sm24tat4xbPoeConfigurationPortDelayMode     Integer32,
    sm24tat4xbPoeConfigurationPortDelayTime     Integer32
}

sm24tat4xbPoeConfigurationPort OBJECT-TYPE
    SYNTAX      Integer32(1..65535)
    MAX-ACCESS  not-accessible
    STATUS      current
    DESCRIPTION
        " port, range : 1 - port number. "
    ::= { sm24tat4xbPoeConfigurationPortEntry 1 }

sm24tat4xbPoeConfigurationPortPoEMode OBJECT-TYPE
    SYNTAX      INTEGER { disable(0), poe(1) , poeforce(3) }
    MAX-ACCESS  read-write
    STATUS      current
    DESCRIPTION
        "The PoE Mode represents the PoE operating mode for the port.
        0: Disable,
        1: Enable,
		3: Force,
        default: Enable. "
    ::= { sm24tat4xbPoeConfigurationPortEntry 2 }

sm24tat4xbPoeConfigurationPortPriority OBJECT-TYPE
    SYNTAX      INTEGER { low(0), high(1), critical(2) }
    MAX-ACCESS  read-write
    STATUS      current
    DESCRIPTION
        "The Priority represents the ports priority. There are three levels of power priority named Low, High and Critical.
        0: Low,
        1: High,
        2: Critical,
        default: Low.  "
    ::= { sm24tat4xbPoeConfigurationPortEntry 3 }

sm24tat4xbPoeConfigurationPortMaximumPower OBJECT-TYPE
    SYNTAX      DisplayString
    MAX-ACCESS  read-write
    STATUS      current
    DESCRIPTION
        "The Maximum Power value contains a numerical value that indicates the maximum
    power in watts that can be delivered to a remote device.
    max: 30[W]. "
    ::= { sm24tat4xbPoeConfigurationPortEntry 4 }

sm24tat4xbPoeConfigurationPortDetection OBJECT-TYPE
    SYNTAX      Integer32(1..5)
    MAX-ACCESS  read-write
    STATUS      current
    DESCRIPTION
        "The Detection represents the PoE capacitor detection for the port.
	      -1:Not support.
	    1:Legacy : Legacy capacitive detection only.
	    2:4-point : IEEE 802.3af 4-point detection only.
	    3:4-point-legacy : IEEE 802.3af 4-point detection followed by Legacy detection.
	    4:2-point : IEEE 802.3af 2-point detection only.
	    5:2-point-legacy : IEEE 802.3af 2-point detection followed by Legacy detection.
	    "
    ::= { sm24tat4xbPoeConfigurationPortEntry 5 }

-- sm24tat4xbPoeConfigurationPortPoEScheduleByProfileID OBJECT-TYPE
--    SYNTAX      Integer32(0..16)
--    MAX-ACCESS  read-write
--    STATUS      current
--    DESCRIPTION
--    "Specify a valid PoE schedule profile by profile id. 0:disable,1-16:1-16 profile."
--    ::= { sm24tat4xbPoeConfigurationPortEntry 6 }

sm24tat4xbPoeConfigurationPortPoEScheduleByProfileName OBJECT-TYPE
    SYNTAX      DisplayString
    MAX-ACCESS  read-write
    STATUS      current
    DESCRIPTION
        "Specify a valid PoE schedule profile by profile name. disabled: disable profile schedule."
    ::= { sm24tat4xbPoeConfigurationPortEntry 7 }

sm24tat4xbPoeConfigurationPortDelayMode OBJECT-TYPE
    SYNTAX      Integer32(0..1)
    MAX-ACCESS  read-write
    STATUS      current
    DESCRIPTION
        "Turn on off the power delay function.
	    0: Disable
        1: Enable"
    ::= { sm24tat4xbPoeConfigurationPortEntry 8 }

sm24tat4xbPoeConfigurationPortDelayTime OBJECT-TYPE
    SYNTAX      Integer32(0..300)
    MAX-ACCESS  read-write
    STATUS      current
    DESCRIPTION
        "When rebooting, the PoE port will start to provide power to the PD when it out of delay time.
	    Range:0-300"
    ::= { sm24tat4xbPoeConfigurationPortEntry 9 }

sm24tat4xbPoeChipsetRebootSchedule OBJECT IDENTIFIER ::= { sm24tat4xbPoe 6 }

sm24tat4xbPoeChipsetRebootMode OBJECT-TYPE
    SYNTAX      Integer32
    MAX-ACCESS  read-write
    STATUS      current
    DESCRIPTION
        "PoE Chipset Reboot Mode
	    0:disable
		1:enable"
    ::= { sm24tat4xbPoeChipsetRebootSchedule 1 }

sm24tat4xbPoeChipsetRebootTimeTable OBJECT-TYPE
    SYNTAX      SEQUENCE OF SM24TAT4XBPoeChipsetRebootTimeEntry
    MAX-ACCESS  not-accessible
    STATUS      current
    DESCRIPTION
        " Configure PoE Chipset Reboot Time."
    ::= { sm24tat4xbPoeChipsetRebootSchedule 2 }

sm24tat4xbPoeChipsetRebootTimeEntry OBJECT-TYPE
    SYNTAX      SM24TAT4XBPoeChipsetRebootTimeEntry
    MAX-ACCESS  not-accessible
    STATUS      current
    DESCRIPTION
        " "
    INDEX    { sm24tat4xbPoeChipsetRebootWeekIndex  }
    ::= { sm24tat4xbPoeChipsetRebootTimeTable 1 }

SM24TAT4XBPoeChipsetRebootTimeEntry ::= SEQUENCE {
    sm24tat4xbPoeChipsetRebootWeekIndex	    Integer32,
    sm24tat4xbPoeChipsetRebootTimeHour        Integer32,
    sm24tat4xbPoeChipsetRebootTimeMinute     Integer32
}

sm24tat4xbPoeChipsetRebootWeekIndex OBJECT-TYPE
    SYNTAX      Integer32 (1..7)
    MAX-ACCESS  not-accessible
    STATUS      current
    DESCRIPTION
        "PoE chipset reboot week index.
	    1: Mon, 2:Tue, 3: Wed, 4: Thu, 5: Fri, 6: Sat, 7: Sun"
    ::= { sm24tat4xbPoeChipsetRebootTimeEntry 1 }

sm24tat4xbPoeChipsetRebootTimeHour OBJECT-TYPE
    SYNTAX      Integer32 (-1..23)
    MAX-ACCESS  read-write
    STATUS      current
    DESCRIPTION
        "PoE Chipset Reboot Time (Hour). Range: 0-23.
	    -1:disable"
    ::= { sm24tat4xbPoeChipsetRebootTimeEntry 2 }

sm24tat4xbPoeChipsetRebootTimeMinute OBJECT-TYPE
    SYNTAX      Integer32 (-1..55)
    MAX-ACCESS  read-write
    STATUS      current
    DESCRIPTION
        "PoE Chipset Reboot Time (Minute). Range:0,5,10,...,55.
	    -1:disable"
    ::= { sm24tat4xbPoeChipsetRebootTimeEntry 3 }

-- =======================================================================================================================
-- RowStatus Info:  createAndWait, notReady, notInService not supported.
-- =======================================================================================================================
-- Textual Conventions for the sm24tat4xb AAA Mib
-- =======================================================================================================================
--
sm24tat4xbAAAMIB            OBJECT IDENTIFIER  ::= { sm24tat4xbConfiguration 15 }
    sm24tat4xbAAA          OBJECT IDENTIFIER  ::= { sm24tat4xbAAAMIB 1 }
    sm24tat4xbRADIUS        OBJECT IDENTIFIER  ::= { sm24tat4xbAAA 1 }
    sm24tat4xbRADIUSGlobalConfig    OBJECT IDENTIFIER  ::= { sm24tat4xbRADIUS 1 }

    sm24tat4xbTACACS        OBJECT IDENTIFIER  ::= { sm24tat4xbAAA 2 }

--
-- =======================================================================================================================
-- Start sm24tat4xbRADIUS group
-- =======================================================================================================================
--sm24tat4xbRADIUSGlobalConfig

    sm24tat4xbRADIUSGlobalConfigTimeout OBJECT-TYPE
        SYNTAX      Integer32(1..1000)
        MAX-ACCESS  read-write
        STATUS      current
        DESCRIPTION
            "Timeout is the number of seconds, to wait for a reply
            from a RADIUS server before retransmitting the request.
            range: 1-1000."
        ::= {     sm24tat4xbRADIUSGlobalConfig 1 }

    sm24tat4xbRADIUSGlobalConfigRetransmit OBJECT-TYPE
        SYNTAX      Integer32(1..1000)
        MAX-ACCESS  read-write
        STATUS      current
        DESCRIPTION
            "Retransmit is the number of times,a RADIUS request is
            retransmitted to a server that is not responding.If the
            server has not responded after the last retransmit it is
            considered to be dead.
            range: 1-1000."
        ::= {     sm24tat4xbRADIUSGlobalConfig 2 }

    sm24tat4xbRADIUSGlobalConfigDeadtime OBJECT-TYPE
        SYNTAX      Integer32(0..1440)
        MAX-ACCESS  read-write
        STATUS      current
        DESCRIPTION
            "This will stop the switch from continually trying to
            contact a server that it has already determined as dead.
            range: 0-1440."
        ::= {     sm24tat4xbRADIUSGlobalConfig 3 }

    sm24tat4xbRADIUSGlobalConfigKey OBJECT-TYPE
        SYNTAX      DisplayString
        MAX-ACCESS  read-write
        STATUS      current
        DESCRIPTION
            "The secret key shared between the RADIUS server and
            the switch."
        ::= {     sm24tat4xbRADIUSGlobalConfig 4 }

    sm24tat4xbRADIUSGlobalConfigNASIPv4 OBJECT-TYPE
        SYNTAX      IpAddress
        MAX-ACCESS  read-write
        STATUS      current
        DESCRIPTION
            "The IPv4 address to be used as attribute 4 in RADIUS
            Access-Request packets."
        ::= {     sm24tat4xbRADIUSGlobalConfig 5 }

    sm24tat4xbRADIUSGlobalConfigNASIPv6 OBJECT-TYPE
        SYNTAX      DisplayString
        MAX-ACCESS  read-write
        STATUS      current
        DESCRIPTION
            "The IPv6 address to be used as attribute 95 in RADIUS
            Access-Request packets. "
        ::= {     sm24tat4xbRADIUSGlobalConfig 6 }

    sm24tat4xbRADIUSGlobalConfigNASIdentifier OBJECT-TYPE
        SYNTAX      DisplayString
        MAX-ACCESS  read-write
        STATUS      current
        DESCRIPTION
            "The identifier to be used as attribute 32 in RADIUS
            Access-Request packets. "
        ::= {     sm24tat4xbRADIUSGlobalConfig 7 }

--sm24tat4xbRADIUSServerConfigTable

    sm24tat4xbRADIUSServerConfigTable OBJECT-TYPE
        SYNTAX      SEQUENCE OF     SM24TAT4XBRADIUSServerConfigEntry
        MAX-ACCESS  not-accessible
        STATUS      current
        DESCRIPTION
            "The RADIUS Server Configuration Table."
        ::= {     sm24tat4xbRADIUS 2 }

    sm24tat4xbRADIUSServerConfigEntry OBJECT-TYPE
        SYNTAX      SM24TAT4XBRADIUSServerConfigEntry
        MAX-ACCESS  not-accessible
        STATUS      current
        DESCRIPTION
            "The RADIUS Server Configuration Entry."
        INDEX    {    sm24tat4xbRADIUSServerConfServerNo  }
        ::= {     sm24tat4xbRADIUSServerConfigTable 1 }

    SM24TAT4XBRADIUSServerConfigEntry         ::= SEQUENCE {
         sm24tat4xbRADIUSServerConfServerNo      Integer32,
         sm24tat4xbRADIUSServerConfHostname      DisplayString,
         sm24tat4xbRADIUSServerConfAuthPort      Integer32,
         sm24tat4xbRADIUSServerConfAcctPort      Integer32,
         sm24tat4xbRADIUSServerConfTimeout    Integer32,
         sm24tat4xbRADIUSServerConfRetransmit    Integer32,
         sm24tat4xbRADIUSServerConfKey        DisplayString,
         sm24tat4xbRADIUSServerConfRowStatus     RowStatus
         }

    sm24tat4xbRADIUSServerConfServerNo OBJECT-TYPE
        SYNTAX      Integer32(1..5)
        MAX-ACCESS  not-accessible
        STATUS      current
        DESCRIPTION
            "The RADIUS server number.
            max: 5."
        ::= {     sm24tat4xbRADIUSServerConfigEntry 1 }

    sm24tat4xbRADIUSServerConfHostname OBJECT-TYPE
        SYNTAX      DisplayString
        MAX-ACCESS  read-create
        STATUS      current
        DESCRIPTION
            "The IP address or hostname of the RADIUS server. "
        ::= {     sm24tat4xbRADIUSServerConfigEntry 2 }

    sm24tat4xbRADIUSServerConfAuthPort OBJECT-TYPE
        SYNTAX      Integer32(0..65535)
        MAX-ACCESS  read-create
        STATUS      current
        DESCRIPTION
            "The UDP port to use on the RADIUS server for
            authentication.
            range: 0-65535. "
        ::= {     sm24tat4xbRADIUSServerConfigEntry 3 }

    sm24tat4xbRADIUSServerConfAcctPort OBJECT-TYPE
        SYNTAX      Integer32(0..65535)
        MAX-ACCESS  read-create
        STATUS      current
        DESCRIPTION
            "The UDP port to use on the RADIUS server for accounting.
            range: 0-65535. "
        ::= {     sm24tat4xbRADIUSServerConfigEntry 4 }

    sm24tat4xbRADIUSServerConfTimeout OBJECT-TYPE
        SYNTAX      Integer32(1..1000)
        MAX-ACCESS  read-create
        STATUS      current
        DESCRIPTION
            "This optional setting overrides the global timeout value.
            Leaving it blank will use the global timeout value.
            range: 1-1000. "
        ::= {     sm24tat4xbRADIUSServerConfigEntry 5 }

    sm24tat4xbRADIUSServerConfRetransmit OBJECT-TYPE
        SYNTAX      Integer32(1..1000)
        MAX-ACCESS  read-create
        STATUS      current
        DESCRIPTION
            "This optional setting overrides the global retransmit value.
            Leaving it blank will use the global retransmit value.
            range: 1-1000. "
        ::= {     sm24tat4xbRADIUSServerConfigEntry 6 }

    sm24tat4xbRADIUSServerConfKey OBJECT-TYPE
        SYNTAX      DisplayString
        MAX-ACCESS  read-create
        STATUS      current
        DESCRIPTION
            "This optional setting overrides the global key. Leaving
            it blank will use the global key."
        ::= {     sm24tat4xbRADIUSServerConfigEntry 7 }

    sm24tat4xbRADIUSServerConfRowStatus OBJECT-TYPE
        SYNTAX      RowStatus
        MAX-ACCESS  read-create
        STATUS      current
        DESCRIPTION
            "This object indicates the status of this entry, and is
            used to create/delete entries.  Any object in an entry of
            this table may be modified while the value of the
            corresponding instance of this object is active(1).
            createAndGo, notReady not supported."
        ::= {     sm24tat4xbRADIUSServerConfigEntry 8 }

--sm24tat4xbRADIUSDetailTable

    sm24tat4xbRADIUSDetailTable OBJECT-TYPE
        SYNTAX      SEQUENCE OF     SM24TAT4XBRADIUSDetailEntry
        MAX-ACCESS  not-accessible
        STATUS      current
        DESCRIPTION
            "The RADIUS Detail Table."
        ::= {     sm24tat4xbRADIUS 3 }

    sm24tat4xbRADIUSDetailEntry OBJECT-TYPE
        SYNTAX      SM24TAT4XBRADIUSDetailEntry
        MAX-ACCESS  not-accessible
        STATUS      current
        DESCRIPTION
            "The RADIUS Detail Entry."
        INDEX    {    sm24tat4xbRADIUSServerConfServerNo  }
        ::= {     sm24tat4xbRADIUSDetailTable 1 }

    SM24TAT4XBRADIUSDetailEntry         ::= SEQUENCE {
         sm24tat4xbRADIUSAuthIPAddress        DisplayString,
         sm24tat4xbRADIUSAuthStatus          DisplayString,
         sm24tat4xbRADIUSAuthRoundTripTime        Integer32,
         sm24tat4xbRADIUSAuthRxAccessAccept      Counter32,
         sm24tat4xbRADIUSAuthRxAccessReject      Counter32,
         sm24tat4xbRADIUSAuthRxAccessChallenge    Counter32,
         sm24tat4xbRADIUSAuthRxAccessResponse    Counter32,
         sm24tat4xbRADIUSAuthRxBadAuth        Counter32,
         sm24tat4xbRADIUSAuthRxUnknownType        Counter32,
         sm24tat4xbRADIUSAuthRxPacketsDropped    Counter32,
         sm24tat4xbRADIUSAuthTxAccessRequest     Counter32,
         sm24tat4xbRADIUSAuthTxAccessRetransmission  Counter32,
         sm24tat4xbRADIUSAuthTxPendingRequest    Counter32,
         sm24tat4xbRADIUSAuthTxTimeout        Counter32,
         sm24tat4xbRADIUSAccountIPAddress        IpAddress,
         sm24tat4xbRADIUSAccountStatus        DisplayString,
         sm24tat4xbRADIUSAccountRoundTripTime    Integer32,
         sm24tat4xbRADIUSAccountRxResponses      Counter32,
         sm24tat4xbRADIUSAccountRxMalformedResponse  Counter32,
         sm24tat4xbRADIUSAccountRxBadAuth        Counter32,
         sm24tat4xbRADIUSAccountRxUnknownType    Counter32,
         sm24tat4xbRADIUSAccountRxPacketsDrop    Counter32,
         sm24tat4xbRADIUSAccountTxRequest        Counter32,
         sm24tat4xbRADIUSAccountTxRetransmission     Counter32,
         sm24tat4xbRADIUSAccountTxPendingRequest     Counter32,
         sm24tat4xbRADIUSAccountTxTimeout        Counter32,
         sm24tat4xbRADIUSDetailClearCmd          ActivateCmd
         }

    sm24tat4xbRADIUSAuthIPAddress OBJECT-TYPE
        SYNTAX      DisplayString
        MAX-ACCESS  read-only
        STATUS      current
        DESCRIPTION
            "IP address and UDP port for the authentication
            server in question."
        ::= {     sm24tat4xbRADIUSDetailEntry 2 }

    sm24tat4xbRADIUSAuthStatus OBJECT-TYPE
        SYNTAX      DisplayString
        MAX-ACCESS  read-only
        STATUS      current
        DESCRIPTION
            "Shows the state of the server."
        ::= {     sm24tat4xbRADIUSDetailEntry 3 }

    sm24tat4xbRADIUSAuthRoundTripTime OBJECT-TYPE
        SYNTAX      Integer32(0..100000000)
        MAX-ACCESS  read-only
        STATUS      current
        DESCRIPTION
            "The time interval (measured in milliseconds) between
            the most recent Access-Reply/Access-Challenge and the
            Access-Request that matched it from the RADIUS
            authentication server."
        ::= {     sm24tat4xbRADIUSDetailEntry 4 }

    sm24tat4xbRADIUSAuthRxAccessAccept OBJECT-TYPE
        SYNTAX      Counter32
        MAX-ACCESS  read-only
        STATUS      current
        DESCRIPTION
            "The number of RADIUS Access-Accept packets
            (valid or invalid) received from the server."
        ::= {     sm24tat4xbRADIUSDetailEntry 5 }

    sm24tat4xbRADIUSAuthRxAccessReject OBJECT-TYPE
        SYNTAX      Counter32
        MAX-ACCESS  read-only
        STATUS      current
        DESCRIPTION
            "The number of RADIUS Access-Reject packets
            (valid or invalid) received from the server."
        ::= {     sm24tat4xbRADIUSDetailEntry 6 }

    sm24tat4xbRADIUSAuthRxAccessChallenge OBJECT-TYPE
        SYNTAX      Counter32
        MAX-ACCESS  read-only
        STATUS      current
        DESCRIPTION
            "The number of RADIUS Access-Challenge packets
            (valid or invalid) received from the server."
        ::= {     sm24tat4xbRADIUSDetailEntry 7 }

    sm24tat4xbRADIUSAuthRxAccessResponse OBJECT-TYPE
        SYNTAX      Counter32
        MAX-ACCESS  read-only
        STATUS      current
        DESCRIPTION
            "The number of malformed RADIUS Access-Response
            packets received from the server."
        ::= {     sm24tat4xbRADIUSDetailEntry 8 }

    sm24tat4xbRADIUSAuthRxBadAuth OBJECT-TYPE
        SYNTAX      Counter32
        MAX-ACCESS  read-only
        STATUS      current
        DESCRIPTION
            "The number of RADIUS Access-Response packets containing
            invalid authenticators or Message Authenticator
            attributes received from the server."
        ::= {     sm24tat4xbRADIUSDetailEntry 9 }

    sm24tat4xbRADIUSAuthRxUnknownType OBJECT-TYPE
        SYNTAX      Counter32
        MAX-ACCESS  read-only
        STATUS      current
        DESCRIPTION
            "The number of RADIUS packets that were received with
            unknown types from the server on the authentication
            port and dropped."
        ::= {     sm24tat4xbRADIUSDetailEntry 10 }

    sm24tat4xbRADIUSAuthRxPacketsDropped OBJECT-TYPE
        SYNTAX      Counter32
        MAX-ACCESS  read-only
        STATUS      current
        DESCRIPTION
            "The number of RADIUS packets that were received from
            the server on the authentication port and dropped for
            some other reason."
        ::= {     sm24tat4xbRADIUSDetailEntry 11 }

    sm24tat4xbRADIUSAuthTxAccessRequest OBJECT-TYPE
        SYNTAX      Counter32
        MAX-ACCESS  read-only
        STATUS      current
        DESCRIPTION
            "The number of RADIUS Access-Request packets sent to
            the server. This does not include retransmissions."
        ::= {     sm24tat4xbRADIUSDetailEntry 12 }

    sm24tat4xbRADIUSAuthTxAccessRetransmission OBJECT-TYPE
        SYNTAX      Counter32
        MAX-ACCESS  read-only
        STATUS      current
        DESCRIPTION
            "The number of RADIUS Access-Request packets
            retransmitted to the RADIUS authentication server."
        ::= {     sm24tat4xbRADIUSDetailEntry 13 }

    sm24tat4xbRADIUSAuthTxPendingRequest OBJECT-TYPE
        SYNTAX      Counter32
        MAX-ACCESS  read-only
        STATUS      current
        DESCRIPTION
            "The number of RADIUS Access-Request packets destined
            for the server that have not yet timed out or received
            a response. "
        ::= {     sm24tat4xbRADIUSDetailEntry 14 }

    sm24tat4xbRADIUSAuthTxTimeout OBJECT-TYPE
        SYNTAX      Counter32
        MAX-ACCESS  read-only
        STATUS      current
        DESCRIPTION
            "The number of authentication timeouts to the server.
            After a timeout, the client may retry to the same server,
            send to a different server, or give up."
        ::= {     sm24tat4xbRADIUSDetailEntry 15 }

    sm24tat4xbRADIUSAccountIPAddress OBJECT-TYPE
        SYNTAX      IpAddress
        MAX-ACCESS  read-only
        STATUS      current
        DESCRIPTION
            "IP address and UDP port for the authentication server
            in question."
        ::= {     sm24tat4xbRADIUSDetailEntry 16 }

    sm24tat4xbRADIUSAccountStatus OBJECT-TYPE
        SYNTAX      DisplayString
        MAX-ACCESS  read-only
        STATUS      current
        DESCRIPTION
            "Shows the state of the server. "
        ::= {     sm24tat4xbRADIUSDetailEntry 17 }

    sm24tat4xbRADIUSAccountRoundTripTime OBJECT-TYPE
        SYNTAX      Integer32(0..100000000)
        MAX-ACCESS  read-only
        STATUS      current
        DESCRIPTION
            "The time interval (measured in milliseconds) between
            the most recent Access-Reply/Access-Challenge and the
            Access-Request that matched it from the RADIUS
            authentication server."
        ::= {     sm24tat4xbRADIUSDetailEntry 18 }

    sm24tat4xbRADIUSAccountRxResponses OBJECT-TYPE
        SYNTAX      Counter32
        MAX-ACCESS  read-only
        STATUS      current
        DESCRIPTION
            "The number of RADIUS packets (valid or invalid)
            received from the server."
        ::= {     sm24tat4xbRADIUSDetailEntry 19 }

    sm24tat4xbRADIUSAccountRxMalformedResponse OBJECT-TYPE
        SYNTAX      Counter32
        MAX-ACCESS  read-only
        STATUS      current
        DESCRIPTION
            "The number of malformed RADIUS packets received from
            the server. "
        ::= {     sm24tat4xbRADIUSDetailEntry 20 }

    sm24tat4xbRADIUSAccountRxBadAuth OBJECT-TYPE
        SYNTAX      Counter32
        MAX-ACCESS  read-only
        STATUS      current
        DESCRIPTION
            "The number of RADIUS packets containing invalid
            authenticators received from the server."
        ::= {     sm24tat4xbRADIUSDetailEntry 21 }

    sm24tat4xbRADIUSAccountRxUnknownType OBJECT-TYPE
        SYNTAX      Counter32
        MAX-ACCESS  read-only
        STATUS      current
        DESCRIPTION
            "The number of RADIUS packets of unknown types that were
            received from the server on the accounting port. "
        ::= {     sm24tat4xbRADIUSDetailEntry 22 }

    sm24tat4xbRADIUSAccountRxPacketsDrop OBJECT-TYPE
        SYNTAX      Counter32
        MAX-ACCESS  read-only
        STATUS      current
        DESCRIPTION
            "The number of RADIUS packets that were received from
            the server on the accounting port and dropped for some
            other reason."
        ::= {     sm24tat4xbRADIUSDetailEntry 23 }

    sm24tat4xbRADIUSAccountTxRequest OBJECT-TYPE
        SYNTAX      Counter32
        MAX-ACCESS  read-only
        STATUS      current
        DESCRIPTION
            "The number of RADIUS packets sent to the server.
            This does not include retransmissions."
        ::= {     sm24tat4xbRADIUSDetailEntry 24 }

    sm24tat4xbRADIUSAccountTxRetransmission OBJECT-TYPE
        SYNTAX      Counter32
        MAX-ACCESS  read-only
        STATUS      current
        DESCRIPTION
            "The number of RADIUS packets retransmitted to the RADIUS
            accounting server."
        ::= {     sm24tat4xbRADIUSDetailEntry 25 }

    sm24tat4xbRADIUSAccountTxPendingRequest OBJECT-TYPE
        SYNTAX      Counter32
        MAX-ACCESS  read-only
        STATUS      current
        DESCRIPTION
            "The number of RADIUS packets destined for the server
            that have not yet timed out or received a response."
        ::= {     sm24tat4xbRADIUSDetailEntry 26 }

    sm24tat4xbRADIUSAccountTxTimeout OBJECT-TYPE
        SYNTAX      Counter32
        MAX-ACCESS  read-only
        STATUS      current
        DESCRIPTION
            "The number of accounting timeouts to the server.
            After a timeout, the client may retry to the same
            server, send to a different server, or give up."
        ::= {     sm24tat4xbRADIUSDetailEntry 27 }

    sm24tat4xbRADIUSDetailClearCmd OBJECT-TYPE
        SYNTAX      ActivateCmd
        MAX-ACCESS  read-only
        STATUS      current
        DESCRIPTION
            "Clears the counters for the selected server."
        ::= {     sm24tat4xbRADIUSDetailEntry 28 }

--
-- =======================================================================================================================
-- Start sm24tat4xbTACACS group
-- =======================================================================================================================
--sm24tat4xbTACACSGlobalConfig

    sm24tat4xbTACACSGlobalConfigTimeout OBJECT-TYPE
        SYNTAX      Integer32(1..1000)
        MAX-ACCESS  read-write
        STATUS      current
        DESCRIPTION
            "Timeout is the number of seconds,to wait for a reply
            from a TACACS+ server before it is considered to be dead.
            range: 1-1000 seconds,
            default: 5 seconds."
        ::= {     sm24tat4xbTACACS 1 }

    sm24tat4xbTACACSGlobalConfigDeadtime OBJECT-TYPE
        SYNTAX      Integer32(0..1440)
        MAX-ACCESS  read-write
        STATUS      current
        DESCRIPTION
            "The period during which the switch will not send new
            requests to a server that has failed to respond to a
            previous request. This will stop the switch from
            continually trying to contact a server that it has
            already determined as dead.
            range: 0-1440 minutes,
            default: 0 minutes."
        ::= {     sm24tat4xbTACACS 2 }

    sm24tat4xbTACACSGlobalConfigKey OBJECT-TYPE
        SYNTAX      DisplayString
        MAX-ACCESS  read-write
        STATUS      current
        DESCRIPTION
            "The secret key shared between the TACACS+ server and
            the switch."
        ::= {     sm24tat4xbTACACS 3 }

--sm24tat4xbTACACSServerConfigTable

    sm24tat4xbTACACSServerConfigTable OBJECT-TYPE
        SYNTAX      SEQUENCE OF     SM24TAT4XBTACACSServerConfigEntry
        MAX-ACCESS  not-accessible
        STATUS      current
        DESCRIPTION
            "The TACACS Server configuration Table."
        ::= {     sm24tat4xbTACACS 4 }

    sm24tat4xbTACACSServerConfigEntry OBJECT-TYPE
        SYNTAX      SM24TAT4XBTACACSServerConfigEntry
        MAX-ACCESS  not-accessible
        STATUS      current
        DESCRIPTION
            "The TACACS Server configuration Entry."
        INDEX    {    sm24tat4xbTACACSServerConfigServerNo  }
        ::= {     sm24tat4xbTACACSServerConfigTable 1 }

    SM24TAT4XBTACACSServerConfigEntry         ::= SEQUENCE {
         sm24tat4xbTACACSServerConfigServerNo    Integer32,
         sm24tat4xbTACACSServerConfigHostname    DisplayString,
         sm24tat4xbTACACSServerConfigPort        Integer32,
         sm24tat4xbTACACSServerConfigTimeout     Integer32,
         sm24tat4xbTACACSServerConfigKey         DisplayString,
         sm24tat4xbTACACSServerConfigRowStatus    RowStatus
         }

    sm24tat4xbTACACSServerConfigServerNo OBJECT-TYPE
        SYNTAX      Integer32(1..5)
        MAX-ACCESS  not-accessible
        STATUS      current
        DESCRIPTION
            "The TACACS server number.
            max: 5."
        ::= {     sm24tat4xbTACACSServerConfigEntry 1 }

    sm24tat4xbTACACSServerConfigHostname OBJECT-TYPE
        SYNTAX      DisplayString
        MAX-ACCESS  read-create
        STATUS      current
        DESCRIPTION
            "The IP address or hostname of the TACACS+ server."
        ::= {     sm24tat4xbTACACSServerConfigEntry 2 }

    sm24tat4xbTACACSServerConfigPort OBJECT-TYPE
        SYNTAX      Integer32(0..65535)
        MAX-ACCESS  read-create
        STATUS      current
        DESCRIPTION
            "The TCP port to use on the TACACS+ server for
            authentication."
        ::= {     sm24tat4xbTACACSServerConfigEntry 3 }

    sm24tat4xbTACACSServerConfigTimeout OBJECT-TYPE
        SYNTAX      Integer32(1..1000)
        MAX-ACCESS  read-create
        STATUS      current
        DESCRIPTION
            "This optional setting overrides the global timeout
            value. Leaving it blank will use the global timeout
            value.
            range: 1-1000."
        ::= {     sm24tat4xbTACACSServerConfigEntry 4 }

    sm24tat4xbTACACSServerConfigKey OBJECT-TYPE
        SYNTAX      DisplayString
        MAX-ACCESS  read-create
        STATUS      current
        DESCRIPTION
            "This optional setting overrides the global key.
            Leaving it blank will use the global key. "
        ::= {     sm24tat4xbTACACSServerConfigEntry 5 }

    sm24tat4xbTACACSServerConfigRowStatus OBJECT-TYPE
        SYNTAX      RowStatus
        MAX-ACCESS  read-create
        STATUS      current
        DESCRIPTION
            "This object indicates the status of this entry, and is
            used to create/delete entries.  Any object in an entry of
            this table may be modified while the value of the
            corresponding instance of this object is active(1).
            createAndGo, notReady not supported."
        ::= {     sm24tat4xbTACACSServerConfigEntry 6 }

-- =======================================================================================================================
--
-- =======================================================================================================================
-- Textual Conventions for the sm24tat4xb Nas Mib
-- =======================================================================================================================
--
sm24tat4xbNasMIB            OBJECT IDENTIFIER  ::= { sm24tat4xbConfiguration 16 }
    sm24tat4xbNAS          OBJECT IDENTIFIER  ::= { sm24tat4xbNasMIB 1 }
    sm24tat4xbNASConf          OBJECT IDENTIFIER  ::= { sm24tat4xbNAS 1 }
    sm24tat4xbNASStatus        OBJECT IDENTIFIER  ::= { sm24tat4xbNAS 2 }

--
-- =======================================================================================================================
-- Start sm24tat4xbNAS group
-- =======================================================================================================================
--sm24tat4xbNASConf

    sm24tat4xbNASConfMode OBJECT-TYPE
        SYNTAX      AdminMode
        MAX-ACCESS  read-write
        STATUS      current
        DESCRIPTION
            "Indicates if NAS is globally enabled or disabled on
            the switch."
        DEFVAL  { disable }
        ::= {     sm24tat4xbNASConf 1 }

    sm24tat4xbNASConfReauthenticationEnabled OBJECT-TYPE
        SYNTAX      AdminMode
        MAX-ACCESS  read-write
        STATUS      current
        DESCRIPTION
            "If enable, successfully authenticated supplicants/clients
            are reauthenticated after the interval specified by the
            Reauthentication Period."
        DEFVAL  { disable }
        ::= {     sm24tat4xbNASConf 2 }

    sm24tat4xbNASConfReauthenticationPeriod OBJECT-TYPE
        SYNTAX      Integer32(1..3600)
        MAX-ACCESS  read-write
        STATUS      current
        DESCRIPTION
            "Determines the period, in seconds, after which a
            connected client must be reauthenticated.
            default: 3600 sec,
            range: 1-3600 sec."
        ::= {     sm24tat4xbNASConf 3 }

    sm24tat4xbNASConfEAPOLTimeout OBJECT-TYPE
        SYNTAX      Integer32(1..65535)
        MAX-ACCESS  read-write
        STATUS      current
        DESCRIPTION
            "Determines the time for retransmission of Request
            Identity EAPOL frames.
            default: 30 sec,
            range: 1-65535 sec."
        ::= {     sm24tat4xbNASConf 4 }

    sm24tat4xbNASConfAgingPeriod OBJECT-TYPE
        SYNTAX      Integer32(0|10..1000000)
        MAX-ACCESS  read-write
        STATUS      current
        DESCRIPTION
            "When the NAS module uses the Port Security module to
            secure MAC addresses, the Port Security module needs to
            check for activity on the MAC address in question at regular
            intervals and free resources if no activity is seen within
            a given period of time.
            default: 300 sec,
            0: no support.
            range: 0,10-1000000 sec."
        ::= {     sm24tat4xbNASConf 5 }

    sm24tat4xbNASConfHoldTime OBJECT-TYPE
        SYNTAX      Integer32(0|10..1000000)
        MAX-ACCESS  read-write
        STATUS      current
        DESCRIPTION
            "If a client is denied access - either because the RADIUS
            server denies the client access or because the RADIUS server
            request times out - the client is put on hold in the
            Unauthorized state.
            default: 10 sec,
            0: no support.
            range: 0,10-1000000 sec."
        ::= {     sm24tat4xbNASConf 6 }

    sm24tat4xbNASConfRADIUSQoSEnabled OBJECT-TYPE
        SYNTAX      AdminMode
        MAX-ACCESS  read-write
        STATUS      current
        DESCRIPTION
            "RADIUS-assigned QoS provides a means to centrally control
            the traffic class to which traffic coming from a successfully
            authenticated supplicant is assigned on the switch."
        DEFVAL  { disable }
        ::= {     sm24tat4xbNASConf 7 }

    sm24tat4xbNASConfRADIUSVLANEnabled OBJECT-TYPE
        SYNTAX      AdminMode
        MAX-ACCESS  read-write
        STATUS      current
        DESCRIPTION
            "RADIUS-assigned VLAN provides a means to centrally control
            the VLAN on which a successfully authenticated supplicant
            is placed on the switch."
        DEFVAL  { disable }
        ::= {     sm24tat4xbNASConf 8 }

    sm24tat4xbNASConfGuestVLANEnabled OBJECT-TYPE
        SYNTAX      AdminMode
        MAX-ACCESS  read-write
        STATUS      current
        DESCRIPTION
            "A Guest VLAN is a special VLAN - typically with limited
            network access - on which 802.1X-unaware clients are placed
            after a network administrator-defined timeout."
        DEFVAL  { disable }
        ::= {     sm24tat4xbNASConf 9 }

    sm24tat4xbNASConfGuestVLANID OBJECT-TYPE
        SYNTAX      Integer32(1..4095)
        MAX-ACCESS  read-write
        STATUS      current
        DESCRIPTION
            "This is the value that a port's Port VLAN ID is set to if
            a port is moved into the Guest VLAN.
            default: 1,
            range: 1-4095."
        ::= {     sm24tat4xbNASConf 10 }

    sm24tat4xbNASConfMaxReauthCount OBJECT-TYPE
        SYNTAX      Integer32(1..255)
        MAX-ACCESS  read-write
        STATUS      current
        DESCRIPTION
            "The number of times the switch transmits an EAPOL Request
            Identity frame without response before considering entering
            the Guest VLAN is adjusted with this setting.
            default: 2,
            range: 1-255."
        ::= {     sm24tat4xbNASConf 11 }

    sm24tat4xbNASConfAllowGuestVLAN OBJECT-TYPE
        SYNTAX      AdminMode
        MAX-ACCESS  read-write
        STATUS      current
        DESCRIPTION
            "The switch remembers if an EAPOL frame has been received
            on the port for the life-time of the port."
        DEFVAL  { disable }
        ::= {     sm24tat4xbNASConf 12 }

--sm24tat4xbNASPortConfTable

    sm24tat4xbNASPortConfTable OBJECT-TYPE
        SYNTAX      SEQUENCE OF     SM24TAT4XBNASPortConfEntry
        MAX-ACCESS  not-accessible
        STATUS      current
        DESCRIPTION
            "The NAS Port Configuration Table.
            INDEX for this table is ifIndex which is
            equivalent to the panel port number."
        ::= {     sm24tat4xbNASConf 13 }

    sm24tat4xbNASPortConfEntry OBJECT-TYPE
        SYNTAX      SM24TAT4XBNASPortConfEntry
        MAX-ACCESS  not-accessible
        STATUS      current
        DESCRIPTION
            "The NAS Port Configuration Entry."
        INDEX    {    ifIndex  }
        ::= {     sm24tat4xbNASPortConfTable 1 }

    SM24TAT4XBNASPortConfEntry         ::= SEQUENCE {
         sm24tat4xbNASPortConfAdminState     Integer32,
         sm24tat4xbNASPortConfRADIUSQoSEnabled    AdminMode,
         sm24tat4xbNASPortConfRADIUSVLANEnabled  AdminMode,
         sm24tat4xbNASPortConfGuestVLANEnabled    AdminMode,
         sm24tat4xbNASPortConfPortState      DisplayString,
         sm24tat4xbNASPortConfReauthenticateCmd  INTEGER,
         sm24tat4xbNASPortConfReinitializeCmd    INTEGER
         }

    sm24tat4xbNASPortConfAdminState OBJECT-TYPE
        SYNTAX      Integer32(0..5)
        MAX-ACCESS  read-write
        STATUS      current
        DESCRIPTION
            "This selection controls the port's authentication mode.
            0: Force Authorized,
            1: Force Unauthorized,
            2: Port-based 802.1X,
            3: Single 802.1X,
            4: Multi 802.1X,
            5: MAC-based Auth,
            range: 0-5."
        ::= {     sm24tat4xbNASPortConfEntry 2 }

    sm24tat4xbNASPortConfRADIUSQoSEnabled OBJECT-TYPE
        SYNTAX      AdminMode
        MAX-ACCESS  read-write
        STATUS      current
        DESCRIPTION
            "When RADIUS-Assigned QoS is both globally enabled and
            enabled on a given port, the switch reacts to QoS Class
            information carried in the RADIUS Access-Accept packet
            transmitted by the RADIUS server when a supplicant is
            successfully authenticated."
        ::= {     sm24tat4xbNASPortConfEntry 3 }

    sm24tat4xbNASPortConfRADIUSVLANEnabled OBJECT-TYPE
        SYNTAX      AdminMode
        MAX-ACCESS  read-write
        STATUS      current
        DESCRIPTION
            "When RADIUS-Assigned VLAN is both globally enabled and
            enabled for a given port, the switch reacts to VLAN ID
            information carried in the RADIUS Access-Accept packet
            transmitted by the RADIUS server when a supplicant is
            successfully authenticated."
        ::= {     sm24tat4xbNASPortConfEntry 4 }

    sm24tat4xbNASPortConfGuestVLANEnabled OBJECT-TYPE
        SYNTAX      AdminMode
        MAX-ACCESS  read-write
        STATUS      current
        DESCRIPTION
            "When Guest VLAN is both globally enabled and enabled for
            a given port, the switch considers moving the port into
            the Guest VLAN according to the rules."
        ::= {     sm24tat4xbNASPortConfEntry 5 }

    sm24tat4xbNASPortConfPortState OBJECT-TYPE
        SYNTAX      DisplayString
        MAX-ACCESS  read-only
        STATUS      current
        DESCRIPTION
            "The current state of the port."
        ::= {     sm24tat4xbNASPortConfEntry 6 }

    sm24tat4xbNASPortConfReauthenticateCmd OBJECT-TYPE
        SYNTAX      ActivateCmd
        MAX-ACCESS  read-write
        STATUS      current
        DESCRIPTION
            "Schedules a reauthentication whenever the quiet-period of
            the port runs out (EAPOL-based authentication). For
            MAC-based authentication, reauthentication will be attempted
            immediately.The button only has effect for successfully
            authenticated clients on the port and will not cause the
            clients to get temporarily unauthorized."
        DEFVAL  { noAction }
        ::= {     sm24tat4xbNASPortConfEntry 7 }

    sm24tat4xbNASPortConfReinitializeCmd OBJECT-TYPE
        SYNTAX      ActivateCmd
        MAX-ACCESS  read-write
        STATUS      current
        DESCRIPTION
            "Forces a reinitialization of the clients on the port and
            thereby a reauthentication immediately. The clients will
            transfer to the unauthorized state while the
            reauthentication is in progress."
        DEFVAL  { noAction }
        ::= {     sm24tat4xbNASPortConfEntry 8 }

--sm24tat4xbNASSwitchStatusTable

    sm24tat4xbNASSwitchStatusTable OBJECT-TYPE
        SYNTAX      SEQUENCE OF     SM24TAT4XBNASSwitchStatusEntry
        MAX-ACCESS  not-accessible
        STATUS      current
        DESCRIPTION
            "The NAS Switch Status Table.
            INDEX for this table is ifIndex which is
            equivalent to the panel port number."
        ::= {     sm24tat4xbNASStatus 1 }

    sm24tat4xbNASSwitchStatusEntry OBJECT-TYPE
        SYNTAX      SM24TAT4XBNASSwitchStatusEntry
        MAX-ACCESS  not-accessible
        STATUS      current
        DESCRIPTION
            "The NAS Switch Status Entry."
        INDEX    {    ifIndex  }
        ::= {     sm24tat4xbNASSwitchStatusTable 1 }

    SM24TAT4XBNASSwitchStatusEntry         ::= SEQUENCE {
         sm24tat4xbNASSwitchStatusAdminState    DisplayString,
         sm24tat4xbNASSwitchStatusPortState    DisplayString,
         sm24tat4xbNASSwitchStatusLastSource    DisplayString,
         sm24tat4xbNASSwitchStatusLastID    DisplayString,
         sm24tat4xbNASSwitchStatusQoSClass     DisplayString,
         sm24tat4xbNASSwitchStatusPortVLANID    DisplayString
         }

    sm24tat4xbNASSwitchStatusAdminState OBJECT-TYPE
        SYNTAX      DisplayString
        MAX-ACCESS  read-only
        STATUS      current
        DESCRIPTION
            "The port's current administrative state."
        ::= {     sm24tat4xbNASSwitchStatusEntry 2 }

    sm24tat4xbNASSwitchStatusPortState OBJECT-TYPE
        SYNTAX      DisplayString
        MAX-ACCESS  read-only
        STATUS      current
        DESCRIPTION
            "The current state of the port."
        ::= {     sm24tat4xbNASSwitchStatusEntry 3 }

    sm24tat4xbNASSwitchStatusLastSource OBJECT-TYPE
        SYNTAX      DisplayString
        MAX-ACCESS  read-only
        STATUS      current
        DESCRIPTION
            "The source MAC address carried in the most recently
            received EAPOL frame for EAPOL-based authentication,
            and the most recently received frame from a new client
            for MAC-based authentication."
        ::= {     sm24tat4xbNASSwitchStatusEntry 4 }

    sm24tat4xbNASSwitchStatusLastID OBJECT-TYPE
        SYNTAX      DisplayString
        MAX-ACCESS  read-only
        STATUS      current
        DESCRIPTION
            "The user name (supplicant identity) carried in the most
            recently received Response Identity EAPOL frame for
            EAPOL-based authentication, and the source MAC address
            from the most recently received frame from a new client
            for MAC-based authentication."
        ::= {     sm24tat4xbNASSwitchStatusEntry 5 }

    sm24tat4xbNASSwitchStatusQoSClass OBJECT-TYPE
        SYNTAX      DisplayString
        MAX-ACCESS  read-only
        STATUS      current
        DESCRIPTION
            "QoS Class assigned to the port by the RADIUS server
            if enabled."
        ::= {     sm24tat4xbNASSwitchStatusEntry 6 }

    sm24tat4xbNASSwitchStatusPortVLANID OBJECT-TYPE
        SYNTAX      DisplayString
        MAX-ACCESS  read-only
        STATUS      current
        DESCRIPTION
            "The VLAN ID that NAS has put the port in."
        ::= {     sm24tat4xbNASSwitchStatusEntry 7 }

--sm24tat4xbNASPortCounterTable

    sm24tat4xbNASPortCounterTable OBJECT-TYPE
        SYNTAX      SEQUENCE OF     SM24TAT4XBNASPortCounterEntry
        MAX-ACCESS  not-accessible
        STATUS      current
        DESCRIPTION
            "The NAS Port Counter Table.
            INDEX for this table is ifIndex which is
            equivalent to the panel port number."
        ::= {     sm24tat4xbNASStatus 2 }

    sm24tat4xbNASPortCounterEntry OBJECT-TYPE
        SYNTAX      SM24TAT4XBNASPortCounterEntry
        MAX-ACCESS  not-accessible
        STATUS      current
        DESCRIPTION
            "The NAS Port Counter Entry."
        INDEX    {    ifIndex  }
        ::= {     sm24tat4xbNASPortCounterTable 1 }

    SM24TAT4XBNASPortCounterEntry         ::= SEQUENCE {
         sm24tat4xbNASReceiveEAPOLTotal      Integer32,
         sm24tat4xbNASReceiveEAPOLResponseID     Integer32,
         sm24tat4xbNASReceiveEAPOLResponses      Integer32,
         sm24tat4xbNASReceiveEAPOLStart      Integer32,
         sm24tat4xbNASReceiveEAPOLLogoff     Integer32,
         sm24tat4xbNASReceiveEAPOLInvalidType    Integer32,
         sm24tat4xbNASReceiveEAPOLInvalidLength  Integer32,
         sm24tat4xbNASTransmitEAPOLTotal     Integer32,
         sm24tat4xbNASTransmitEAPOLRequestID     Integer32,
         sm24tat4xbNASTransmitEAPOLRequests      Integer32,
         sm24tat4xbNASPortReceiveBackendServerAccessChallenges    Integer32,
         sm24tat4xbNASPortReceiveBackendServerOtherRequests    Integer32,
         sm24tat4xbNASPortReceiveBackendServerAuthSuccesses    Integer32,
         sm24tat4xbNASPortReceiveBackendServerAuthFailures    Integer32,
         sm24tat4xbNASPortTransmitBackendServerResponses      Integer32,
         sm24tat4xbNASSupplicantInfoMAC      DisplayString,
         sm24tat4xbNASSupplicantInfoVlanID    Integer32,
         sm24tat4xbNASSupplicantInfoVersion      Integer32,
         sm24tat4xbNASSupplicantInfoIdentity     DisplayString,
         sm24tat4xbNASPortCounterClearCmd    ActivateCmd
         }

    sm24tat4xbNASReceiveEAPOLTotal OBJECT-TYPE
        SYNTAX      Integer32(-1..1000000)
        MAX-ACCESS  read-only
        STATUS      current
        DESCRIPTION
            "The number of valid EAPOL frames of any type that have
            been received by the switch.
            -1: no support."
        ::= {     sm24tat4xbNASPortCounterEntry 2 }

    sm24tat4xbNASReceiveEAPOLResponseID OBJECT-TYPE
        SYNTAX      Integer32(-1..1000000)
        MAX-ACCESS  read-only
        STATUS      current
        DESCRIPTION
            "The number of valid EAPOL Response Identity frames that
            have been received by the switch.
            -1: no support."
        ::= {     sm24tat4xbNASPortCounterEntry 3 }

    sm24tat4xbNASReceiveEAPOLResponses OBJECT-TYPE
        SYNTAX      Integer32(-1..1000000)
        MAX-ACCESS  read-only
        STATUS      current
        DESCRIPTION
            "The number of valid EAPOL response frames (other than
            Response Identity frames) that have been received by
            the switch.
            -1: no support."
        ::= {     sm24tat4xbNASPortCounterEntry 4 }

    sm24tat4xbNASReceiveEAPOLStart OBJECT-TYPE
        SYNTAX      Integer32(-1..1000000)
        MAX-ACCESS  read-only
        STATUS      current
        DESCRIPTION
            "The number of EAPOL Start frames that have been received
            by the switch.
            -1: no support."
        ::= {     sm24tat4xbNASPortCounterEntry 5 }

    sm24tat4xbNASReceiveEAPOLLogoff OBJECT-TYPE
        SYNTAX      Integer32(-1..1000000)
        MAX-ACCESS  read-only
        STATUS      current
        DESCRIPTION
            "The number of valid EAPOL Logoff frames that have been
            received by the switch.
            -1: no support."
        ::= {     sm24tat4xbNASPortCounterEntry 6 }

    sm24tat4xbNASReceiveEAPOLInvalidType OBJECT-TYPE
        SYNTAX      Integer32(-1..1000000)
        MAX-ACCESS  read-only
        STATUS      current
        DESCRIPTION
            "The number of EAPOL frames that have been received by
            the switch in which the frame type is not recognized.
            -1: no support."
        ::= {     sm24tat4xbNASPortCounterEntry 7 }

    sm24tat4xbNASReceiveEAPOLInvalidLength OBJECT-TYPE
        SYNTAX      Integer32(-1..1000000)
        MAX-ACCESS  read-only
        STATUS      current
        DESCRIPTION
            "The number of EAPOL frames that have been received
            by the switch in which the Packet Body Length field
            is invalid.
            -1: no support."
        ::= {     sm24tat4xbNASPortCounterEntry 8 }

    sm24tat4xbNASTransmitEAPOLTotal OBJECT-TYPE
        SYNTAX      Integer32(-1..1000000)
        MAX-ACCESS  read-only
        STATUS      current
        DESCRIPTION
            "The number of EAPOL frames of any type that have been
            transmitted by the switch.
            -1: no support."
        ::= {     sm24tat4xbNASPortCounterEntry 9 }

    sm24tat4xbNASTransmitEAPOLRequestID OBJECT-TYPE
        SYNTAX      Integer32(-1..1000000)
        MAX-ACCESS  read-only
        STATUS      current
        DESCRIPTION
            "The number of EAPOL Request Identity frames that have
            been transmitted by the switch.
            -1: no support."
        ::= {     sm24tat4xbNASPortCounterEntry 10 }

    sm24tat4xbNASTransmitEAPOLRequests OBJECT-TYPE
        SYNTAX      Integer32(-1..1000000)
        MAX-ACCESS  read-only
        STATUS      current
        DESCRIPTION
            "The number of valid EAPOL Request frames (other than
            Request Identity frames) that have been transmitted
            by the switch.
            -1: no support."
        ::= {     sm24tat4xbNASPortCounterEntry 11 }

    sm24tat4xbNASPortReceiveBackendServerAccessChallenges OBJECT-TYPE
        SYNTAX      Integer32(-1..1000000)
        MAX-ACCESS  read-only
        STATUS      current
        DESCRIPTION
            "802.1X-based: Counts the number of times that the switch
            receives the first request from the backend server following
            the first response from the supplicant. Indicates that the
            backend server has communication with the switch.
            MAC-based:Counts all Access Challenges received from the
            backend server for this port (left-most table).
            -1: no support."
        ::= {     sm24tat4xbNASPortCounterEntry 12 }

    sm24tat4xbNASPortReceiveBackendServerOtherRequests OBJECT-TYPE
        SYNTAX      Integer32(-1..1000000)
        MAX-ACCESS  read-only
        STATUS      current
        DESCRIPTION
            "802.1X-based: Counts the number of times that the switch
            sends an EAP Request packet following the first to the
            supplicant. Indicates that the backend server chose an
            EAP-method.
            MAC-based: Not applicable.
            -1: no support."
        ::= {     sm24tat4xbNASPortCounterEntry 13 }

    sm24tat4xbNASPortReceiveBackendServerAuthSuccesses OBJECT-TYPE
        SYNTAX      Integer32(-1..1000000)
        MAX-ACCESS  read-only
        STATUS      current
        DESCRIPTION
            "802.1X- and MAC-based: Counts the number of times that
            the switch receives a success indication.Indicates that
            the supplicant has successfully authenticated to
            the backend server.
            -1: no support."
        ::= {     sm24tat4xbNASPortCounterEntry 14 }

    sm24tat4xbNASPortReceiveBackendServerAuthFailures OBJECT-TYPE
        SYNTAX      Integer32(-1..1000000)
        MAX-ACCESS  read-only
        STATUS      current
        DESCRIPTION
            "802.1X- and MAC-based:Counts the number of times that the
            switch receives a failure message.This indicates that the
            supplicant has not authenticated to the backend
            server.
            -1: no support."
        ::= {     sm24tat4xbNASPortCounterEntry 15 }

    sm24tat4xbNASPortTransmitBackendServerResponses OBJECT-TYPE
        SYNTAX      Integer32(-1..1000000)
        MAX-ACCESS  read-only
        STATUS      current
        DESCRIPTION
            "802.1X-based:Counts the number of times that the switch
            attempts to send a supplicant's first response packet to
            the backend server. Indicates the switch attempted
            communication with the backend server. Possible
            retransmissions are not counted.
            MAC-based: Counts all the backend server packets sent from
            the switch towards the backend server for a given port
            (left-most table). Possible retransmissions are not
            counted.
            -1: no support."
        ::= {     sm24tat4xbNASPortCounterEntry 16 }

    sm24tat4xbNASSupplicantInfoMAC OBJECT-TYPE
        SYNTAX      DisplayString
        MAX-ACCESS  read-only
        STATUS      current
        DESCRIPTION
            "The MAC address of the last supplicant. "
        ::= {     sm24tat4xbNASPortCounterEntry 17 }

    sm24tat4xbNASSupplicantInfoVlanID OBJECT-TYPE
        SYNTAX      Integer32(-1..1000000)
        MAX-ACCESS  read-only
        STATUS      current
        DESCRIPTION
            "The VLAN ID on which the last frame from the last
            supplicant was received.
            -1: no support."
        ::= {     sm24tat4xbNASPortCounterEntry 18 }

    sm24tat4xbNASSupplicantInfoVersion OBJECT-TYPE
        SYNTAX      Integer32(-1..1000000)
        MAX-ACCESS  read-only
        STATUS      current
        DESCRIPTION
            "802.1X-based:The protocol version number carried in
            the most recently received EAPOL frame.
            MAC-based: Not applicable.
            -1: no support."
        ::= {     sm24tat4xbNASPortCounterEntry 19 }

    sm24tat4xbNASSupplicantInfoIdentity OBJECT-TYPE
        SYNTAX      DisplayString
        MAX-ACCESS  read-only
        STATUS      current
        DESCRIPTION
            "802.1X-based:The user name (supplicant identity) carried
            in the most recently received Response Identity EAPOL frame.
            MAC-based: Not applicable. "
        ::= {     sm24tat4xbNASPortCounterEntry 20 }

    sm24tat4xbNASPortCounterClearCmd OBJECT-TYPE
        SYNTAX      ActivateCmd
        MAX-ACCESS  read-write
        STATUS      current
        DESCRIPTION
            "Clear the counters for the selected port."
        ::= {     sm24tat4xbNASPortCounterEntry 21 }


-- =======================================================================================================================
sm24tat4xbMACConf 						OBJECT IDENTIFIER ::= { sm24tat4xbConfiguration 17 }

    sm24tat4xbMAC                            OBJECT IDENTIFIER    ::= { sm24tat4xbMACConf 1 }

--
-- =======================================================================================================================
-- Start sm24tat4xbMAC group
-- =======================================================================================================================
    sm24tat4xbMACDisableAutomaticAging    OBJECT-TYPE
        SYNTAX    AdminMode
        MAX-ACCESS    read-write
        STATUS    current
        DESCRIPTION
            "Disable the automatic aging of dynamic entries."
        ::= {     sm24tat4xbMAC 1 }

    sm24tat4xbMACAgingTime  OBJECT-TYPE
        SYNTAX    Integer32 (-1 | 10..1000000)
        MAX-ACCESS    read-write
        STATUS    current
        DESCRIPTION
            "Configure aging time by entering a value here in seconds.
            range: 10-1000000 seconds.
            -1: Automatic Aging is disable."
        ::= {     sm24tat4xbMAC 2 }

--sm24tat4xbMACLearningTable
    sm24tat4xbMACLearningTable OBJECT-TYPE
        SYNTAX      SEQUENCE OF     SM24TAT4XBMACLearningEntry
        MAX-ACCESS  not-accessible
        STATUS      current
        DESCRIPTION
            "The mac learning table.
            INDEX for this table is ifIndex which is
            equivalent to the panel port number."
        ::= {     sm24tat4xbMAC 3 }

    sm24tat4xbMACLearningEntry OBJECT-TYPE
        SYNTAX      SM24TAT4XBMACLearningEntry
        MAX-ACCESS  not-accessible
        STATUS      current
        DESCRIPTION
            "The mac learning entry."
        INDEX    {     ifIndex  }
        ::= {     sm24tat4xbMACLearningTable 1 }

    SM24TAT4XBMACLearningEntry         ::= SEQUENCE {
        sm24tat4xbMACTableLearning     INTEGER
        }

    sm24tat4xbMACTableLearning OBJECT-TYPE
        SYNTAX      INTEGER{ auto(0), disable(1), secure(2)}
        MAX-ACCESS  read-write
        STATUS      current
        DESCRIPTION
            "auto(0)    : Learning is done automatically as soon as a
                frame with unknown SMAC is received.
            disable(1): Disable, No learning is done.
            secure(2) : Secure, Only static MAC entries are learned,
                all other frames are dropped."
        ::= {     sm24tat4xbMACLearningEntry 2 }

    sm24tat4xbLearningDisabledVLANs OBJECT-TYPE
        SYNTAX      DisplayString
        MAX-ACCESS  read-write
        STATUS      current
        DESCRIPTION
            "The Learning Disabled VLANs"
        ::= {     sm24tat4xbMAC 4 }

--sm24tat4xbMACStaticConfigTable
    sm24tat4xbMACStaticConfigTable OBJECT-TYPE
        SYNTAX      SEQUENCE OF     SM24TAT4XBMACStaticConfigEntry
        MAX-ACCESS  not-accessible
        STATUS      current
        DESCRIPTION
            "The static Mac config table."
        ::= {     sm24tat4xbMAC 5 }

    sm24tat4xbMACStaticConfigEntry OBJECT-TYPE
        SYNTAX      SM24TAT4XBMACStaticConfigEntry
        MAX-ACCESS  not-accessible
        STATUS      current
        DESCRIPTION
            "The static Mac config entry."
        INDEX    {     sm24tat4xbMACStaticConfigIndex  }
        ::= {     sm24tat4xbMACStaticConfigTable 1 }

    SM24TAT4XBMACStaticConfigEntry         ::= SEQUENCE {
        sm24tat4xbMACStaticConfigSwitchIndex Integer32,
        sm24tat4xbMACStaticConfigIndex    Integer32,
        sm24tat4xbMACStaticConfigVID     Integer32,
        sm24tat4xbMACStaticConfigMACaddress  DisplayString,
        sm24tat4xbMACStaticConfigPortList    DisplayString,
        sm24tat4xbMACStaticConfigRowStatus    RowStatus
        }

    sm24tat4xbMACStaticConfigSwitchIndex OBJECT-TYPE
        SYNTAX      Integer32(1..16)
        MAX-ACCESS  not-accessible
        STATUS      current
        DESCRIPTION
            "Switch Index."
        ::= {     sm24tat4xbMACStaticConfigEntry 1 }



    sm24tat4xbMACStaticConfigIndex OBJECT-TYPE
        SYNTAX      Integer32(1..64)
        MAX-ACCESS  not-accessible
        STATUS      current
        DESCRIPTION
            "The static entries in the MAC table are shown in this table.
            The static MAC table can contain 64 entries."
        ::= {     sm24tat4xbMACStaticConfigEntry 2 }

    sm24tat4xbMACStaticConfigVID OBJECT-TYPE
        SYNTAX      Integer32(1..4095)
        MAX-ACCESS  read-create
        STATUS      current
        DESCRIPTION
            "The VLAN ID of the entry.
            range: 1-4095."
        ::= {     sm24tat4xbMACStaticConfigEntry 3 }

    sm24tat4xbMACStaticConfigMACaddress OBJECT-TYPE
        SYNTAX      DisplayString
        MAX-ACCESS  read-create
        STATUS      current
        DESCRIPTION
            "The MAC address of the entry."
        ::= {     sm24tat4xbMACStaticConfigEntry 4 }

    sm24tat4xbMACStaticConfigPortList OBJECT-TYPE
        SYNTAX      DisplayString
        MAX-ACCESS  read-create
        STATUS      current
        DESCRIPTION
            "Checkmarks indicate which ports are members of the entry.
            Check or uncheck as needed to
            modify the entry."
        ::= {     sm24tat4xbMACStaticConfigEntry 5 }

    sm24tat4xbMACStaticConfigRowStatus OBJECT-TYPE
        SYNTAX      RowStatus
        MAX-ACCESS  read-create
        STATUS      current
        DESCRIPTION
            "This object indicates the status of this entry,
            and is used to create/delete entries. Any
            object in an entry of this table may be modified
            while the value of the corresponding instance
            of this object is active(1).
            createAndGo, notReady not supported."
        ::= {     sm24tat4xbMACStaticConfigEntry 6 }


-- =======================================================================================================================
sm24tat4xbSpanningTree 						OBJECT IDENTIFIER ::= { sm24tat4xbConfiguration 18 }

sm24tat4xbBridgeSettings             OBJECT IDENTIFIER ::= { sm24tat4xbSpanningTree 1 }

sm24tat4xbSTPProtocolVersion    OBJECT-TYPE
        SYNTAX      Integer32
        MAX-ACCESS  read-write
        STATUS      current
        DESCRIPTION
            "0:STP
				    2:RSTP
					3:MSTP"
        ::= {     sm24tat4xbBridgeSettings 1 }

sm24tat4xbBridgePriority    OBJECT-TYPE
        SYNTAX      Integer32
        MAX-ACCESS  read-write
        STATUS      current
        DESCRIPTION
            "Bridge Priority, range: 0-61440, multiple of 4096."
        ::= {     sm24tat4xbBridgeSettings 2 }

sm24tat4xbBridgeForwardDelay    OBJECT-TYPE
        SYNTAX      Integer32
        MAX-ACCESS  read-write
        STATUS      current
        DESCRIPTION
            "Bridge Forward Delay, range: 4-30 seconds."
        ::= {     sm24tat4xbBridgeSettings 3 }

sm24tat4xbBridgeMaxAge    OBJECT-TYPE
        SYNTAX      Integer32
        MAX-ACCESS  read-write
        STATUS      current
        DESCRIPTION
            "Bridge MaxAge, range:6-40 seconds."
        ::= {     sm24tat4xbBridgeSettings 4 }

sm24tat4xbBridgeMaxHops    OBJECT-TYPE
        SYNTAX      Integer32
        MAX-ACCESS  read-write
        STATUS      current
        DESCRIPTION
            "Bridge Max Hops, range:6-40 hops."
        ::= {     sm24tat4xbBridgeSettings 5 }

sm24tat4xbBridgetxHoldCount    OBJECT-TYPE
        SYNTAX      Integer32
        MAX-ACCESS  read-write
        STATUS      current
        DESCRIPTION
            "Bridge Transmit Hold Count,range: 1-10 bpdu's per second. "
        ::= {     sm24tat4xbBridgeSettings 6 }

sm24tat4xbBridgeBPDUFilter    OBJECT-TYPE
        SYNTAX      Integer32
        MAX-ACCESS  read-write
        STATUS      current
        DESCRIPTION
            "Bridge BPD UFilter
          		0:disable
            1:enable					"
        ::= {     sm24tat4xbBridgeSettings 7 }

sm24tat4xbBridgeBPDUGuard    OBJECT-TYPE
        SYNTAX      Integer32
        MAX-ACCESS  read-write
        STATUS      current
        DESCRIPTION
            "Bridge BPDU Guard
          		0:disable
            1:enable					    "
        ::= {     sm24tat4xbBridgeSettings 8 }

sm24tat4xbBridgeerrorRecoveryDelay    OBJECT-TYPE
        SYNTAX      Integer32
        MAX-ACCESS  read-write
        STATUS      current
        DESCRIPTION
            "Bridge error Recovery Delay
				    range:30-86400 seconds
				    0:disable
				    "
        ::= {     sm24tat4xbBridgeSettings 9 }

sm24tat4xbBridgeHelloTime    OBJECT-TYPE
        SYNTAX      Integer32
        MAX-ACCESS  read-write
        STATUS      current
        DESCRIPTION
            "The interval between sending STP BPDU's. Valid values are in the range 1 to 10 seconds,
				    default:2 seconds."
        ::= {     sm24tat4xbBridgeSettings 10 }

sm24tat4xbMSTIMapping            OBJECT IDENTIFIER ::= { sm24tat4xbSpanningTree 2 }
sm24tat4xbConfigName    OBJECT-TYPE
        SYNTAX      DisplayString
        MAX-ACCESS  read-write
        STATUS      current
        DESCRIPTION
            "Configuration Name, identify the VLAN to MSTI mapping"
        ::= {     sm24tat4xbMSTIMapping 1 }

sm24tat4xbConfigRevision    OBJECT-TYPE
        SYNTAX      Integer32
        MAX-ACCESS  read-write
        STATUS      current
        DESCRIPTION
            "Configuration Revision. range:0-65535 "
        ::= {     sm24tat4xbMSTIMapping 2 }

sm24tat4xbMSTIMappingVLAN            OBJECT IDENTIFIER ::= { sm24tat4xbSpanningTree 3 }
sm24tat4xbConfigMstiName1    OBJECT-TYPE
        SYNTAX      DisplayString
        MAX-ACCESS  read-write
        STATUS      current
        DESCRIPTION
            "The list of VLANs mapped to the MSTI1.
				    The VLANs can be given as a single (xx, xx being between 1 and 4094) VLAN, or a range (xx-yy), each of which must be separated with comma and/or space. "
        ::= {     sm24tat4xbMSTIMappingVLAN 1 }

sm24tat4xbConfigMstiName2    OBJECT-TYPE
        SYNTAX      DisplayString
        MAX-ACCESS  read-write
        STATUS      current
        DESCRIPTION
            "The list of VLANs mapped to the MSTI2.
				    The VLANs can be given as a single (xx, xx being between 1 and 4094) VLAN, or a range (xx-yy), each of which must be separated with comma and/or space.  "
        ::= {     sm24tat4xbMSTIMappingVLAN 2 }

sm24tat4xbConfigMstiName3    OBJECT-TYPE
        SYNTAX      DisplayString
        MAX-ACCESS  read-write
        STATUS      current
        DESCRIPTION
            "The list of VLANs mapped to the MSTI3.
				    The VLANs can be given as a single (xx, xx being between 1 and 4094) VLAN, or a range (xx-yy), each of which must be separated with comma and/or space. "
        ::= {     sm24tat4xbMSTIMappingVLAN 3 }

sm24tat4xbConfigMstiName4    OBJECT-TYPE
        SYNTAX      DisplayString
        MAX-ACCESS  read-write
        STATUS      current
        DESCRIPTION
            "The list of VLANs mapped to the MSTI4.
				    The VLANs can be given as a single (xx, xx being between 1 and 4094) VLAN, or a range (xx-yy), each of which must be separated with comma and/or space. "
        ::= {     sm24tat4xbMSTIMappingVLAN 4 }

sm24tat4xbConfigMstiName5    OBJECT-TYPE
        SYNTAX      DisplayString
        MAX-ACCESS  read-write
        STATUS      current
        DESCRIPTION
            "The list of VLANs mapped to the MSTI5.
				    The VLANs can be given as a single (xx, xx being between 1 and 4094) VLAN, or a range (xx-yy), each of which must be separated with comma and/or space. "
        ::= {     sm24tat4xbMSTIMappingVLAN 5 }

sm24tat4xbConfigMstiName6    OBJECT-TYPE
        SYNTAX      DisplayString
        MAX-ACCESS  read-write
        STATUS      current
        DESCRIPTION
            "The list of VLANs mapped to the MSTI6.
				    The VLANs can be given as a single (xx, xx being between 1 and 4094) VLAN, or a range (xx-yy), each of which must be separated with comma and/or space. "
        ::= {     sm24tat4xbMSTIMappingVLAN 6 }

sm24tat4xbConfigMstiName7    OBJECT-TYPE
        SYNTAX      DisplayString
        MAX-ACCESS  read-write
        STATUS      current
        DESCRIPTION
            "The list of VLANs mapped to the MSTI7.
				    The VLANs can be given as a single (xx, xx being between 1 and 4094) VLAN, or a range (xx-yy), each of which must be separated with comma and/or space. "
        ::= {     sm24tat4xbMSTIMappingVLAN 7 }

sm24tat4xbMSTIPriorities             OBJECT IDENTIFIER ::= { sm24tat4xbSpanningTree 4 }

sm24tat4xbCSTIPriority    OBJECT-TYPE
        SYNTAX      Integer32
        MAX-ACCESS  read-write
        STATUS      current
        DESCRIPTION
            "CSTI Priority. range: 0-61440, multiple of 4096. Lower numeric values have better priority."
        ::= {     sm24tat4xbMSTIPriorities 1 }

sm24tat4xbMSTI1Priority    OBJECT-TYPE
        SYNTAX      Integer32
        MAX-ACCESS  read-write
        STATUS      current
        DESCRIPTION
            "MSTI1 Priority. range: 0-61440, multiple of 4096. Lower numeric values have better priority."
        ::= {     sm24tat4xbMSTIPriorities 2 }

sm24tat4xbMSTI2Priority    OBJECT-TYPE
        SYNTAX      Integer32
        MAX-ACCESS  read-write
        STATUS      current
        DESCRIPTION
            "MSTI2 Priority. range: 0-61440, multiple of 4096. Lower numeric values have better priority."
        ::= {     sm24tat4xbMSTIPriorities 3 }

sm24tat4xbMSTI3Priority    OBJECT-TYPE
        SYNTAX      Integer32
        MAX-ACCESS  read-write
        STATUS      current
        DESCRIPTION
            "MSTI3 Priority. range: 0-61440, multiple of 4096. Lower numeric values have better priority."
        ::= {     sm24tat4xbMSTIPriorities 4 }
sm24tat4xbMSTI4Priority    OBJECT-TYPE
        SYNTAX      Integer32
        MAX-ACCESS  read-write
        STATUS      current
        DESCRIPTION
            "MSTI4 Priority. range: 0-61440, multiple of 4096. Lower numeric values have better priority."
        ::= {     sm24tat4xbMSTIPriorities 5 }
sm24tat4xbMSTI5Priority    OBJECT-TYPE
        SYNTAX      Integer32
        MAX-ACCESS  read-write
        STATUS      current
        DESCRIPTION
            "MSTI5 Priority. range: 0-61440, multiple of 4096. Lower numeric values have better priority."
        ::= {     sm24tat4xbMSTIPriorities 6 }

sm24tat4xbMSTI6Priority    OBJECT-TYPE
        SYNTAX      Integer32
        MAX-ACCESS  read-write
        STATUS      current
        DESCRIPTION
            "MSTI6 Priority. range: 0-61440, multiple of 4096. Lower numeric values have better priority."
        ::= {     sm24tat4xbMSTIPriorities 7 }
sm24tat4xbMSTI7Priority    OBJECT-TYPE
        SYNTAX      Integer32
        MAX-ACCESS  read-write
        STATUS      current
        DESCRIPTION
            "MSTI7 Priority. range: 0-61440, multiple of 4096. Lower numeric values have better priority."
        ::= {     sm24tat4xbMSTIPriorities 8 }


sm24tat4xbCISTPorts              OBJECT IDENTIFIER ::= { sm24tat4xbSpanningTree 5 }

sm24tat4xbCISTAggregatedEnable    OBJECT-TYPE
        SYNTAX      Integer32 (0|1)
        MAX-ACCESS  read-write
        STATUS      current
        DESCRIPTION
            "CIST Port Enable. range: 0-1.
				    0:disable
				    1:enable."
        ::= {     sm24tat4xbCISTPorts 1 }

sm24tat4xbCISTAggregatedPathCost    OBJECT-TYPE
        SYNTAX      Integer32 (0..200000000)
        MAX-ACCESS  read-write
        STATUS      current
        DESCRIPTION
            "CIST Port Path Cost. range: 0-200000000. 0 is Auto."
        ::= {     sm24tat4xbCISTPorts 2 }

sm24tat4xbCISTAggregatedPortPriority    OBJECT-TYPE
        SYNTAX      Integer32 (0|16|32|48|64|80|96|112|128|144|160|176|192|208|224|240)
        MAX-ACCESS  read-write
        STATUS      current
        DESCRIPTION
            "CIST Port Priority. range: 0-240, multiple of 16."
        ::= {     sm24tat4xbCISTPorts 3 }

sm24tat4xbCISTAggregatedAdminEdge    OBJECT-TYPE
        SYNTAX      Integer32 (0|1)
        MAX-ACCESS  read-write
        STATUS      current
        DESCRIPTION
            "CIST Port Admin Edge. range: 0-1.
				    0:Non-Edge
				    1:Edge."
        ::= {     sm24tat4xbCISTPorts 4 }

sm24tat4xbCISTAggregatedAutoEdge    OBJECT-TYPE
        SYNTAX      Integer32 (0|1)
        MAX-ACCESS  read-write
        STATUS      current
        DESCRIPTION
            "CIST Port Auto Edge. range: 0-1.
				    0:disable
				    1:enable."
        ::= {     sm24tat4xbCISTPorts 5 }

sm24tat4xbCISTAggregatedrestrictedRole    OBJECT-TYPE
        SYNTAX      Integer32 (0|1)
        MAX-ACCESS  read-write
        STATUS      current
        DESCRIPTION
            "CIST Port restricted Role. range: 0-1.
				    0:disable
				    1:enable."
        ::= {     sm24tat4xbCISTPorts 6 }

sm24tat4xbCISTAggregatedrestrictedTcn    OBJECT-TYPE
        SYNTAX      Integer32 (0|1)
        MAX-ACCESS  read-write
        STATUS      current
        DESCRIPTION
            "CIST Port restricted Tcn. range: 0-1.
				    0:disable
				    1:enable."
        ::= {     sm24tat4xbCISTPorts 7 }

sm24tat4xbCISTAggregatedbpduGuard    OBJECT-TYPE
        SYNTAX      Integer32 (0|1)
        MAX-ACCESS  read-write
        STATUS      current
        DESCRIPTION
            "CIST Port bpdu Guard. range: 0-1.
				    0:disable
				    1:enable."
        ::= {     sm24tat4xbCISTPorts 8 }

sm24tat4xbCISTAggregatedPointToPoint    OBJECT-TYPE
        SYNTAX      Integer32 (0..2)
        MAX-ACCESS  read-write
        STATUS      current
        DESCRIPTION
            "CIST Port Point To Point. range: 0-2.
				    0:Forced True
				    1:Forced False.
				    2:Auto"
        ::= {     sm24tat4xbCISTPorts 9 }


sm24tat4xbCISTPortsTable OBJECT-TYPE
    SYNTAX      SEQUENCE OF SM24TAT4XBCISTPortsEntry
    MAX-ACCESS  not-accessible
    STATUS      current
    DESCRIPTION
        "CIST port table."
    ::= { sm24tat4xbCISTPorts 10 }

sm24tat4xbCISTPortsEntry OBJECT-TYPE
    SYNTAX    SM24TAT4XBCISTPortsEntry
    MAX-ACCESS    not-accessible
    STATUS    current
    DESCRIPTION
        "An entry in the CIST Ports Table."
    INDEX    { sm24tat4xbCISTPortIndex }
    ::= { sm24tat4xbCISTPortsTable 1 }

SM24TAT4XBCISTPortsEntry ::=
    SEQUENCE {
    sm24tat4xbCISTPortIndex         Integer32,
    sm24tat4xbCISTPortEnable        Integer32,
    sm24tat4xbCISTPortPathCost          Integer32,
    sm24tat4xbCISTPortPortPriority      Integer32,
    sm24tat4xbCISTPortAdminEdge         Integer32,
    sm24tat4xbCISTPortAutoEdge          Integer32,
    sm24tat4xbCISTPortrestrictedRole    Integer32,
    sm24tat4xbCISTPortrestrictedTcn     Integer32,
    sm24tat4xbCISTPortbpduGuard         Integer32,
    sm24tat4xbCISTPortPointToPoint      Integer32,
    sm24tat4xbCISTPortRootGuard         Integer32
    }

sm24tat4xbCISTPortIndex    OBJECT-TYPE
        SYNTAX      Integer32 (1..53)
        MAX-ACCESS  not-accessible
        STATUS      current
        DESCRIPTION
            "CIST Port Index. range: 1-53. 53 is Aggregated Port Configuration."
        ::= {     sm24tat4xbCISTPortsEntry 1 }

sm24tat4xbCISTPortEnable    OBJECT-TYPE
        SYNTAX      Integer32 (0|1)
        MAX-ACCESS  read-write
        STATUS      current
        DESCRIPTION
            "CIST Port Enable. range: 0-1.
				    0:disable
				    1:enable."
        ::= {     sm24tat4xbCISTPortsEntry 2 }

sm24tat4xbCISTPortPathCost    OBJECT-TYPE
        SYNTAX      Integer32 (0..200000000)
        MAX-ACCESS  read-write
        STATUS      current
        DESCRIPTION
            "CIST Port Path Cost. range: 0-200000000. 0 is Auto."
        ::= {     sm24tat4xbCISTPortsEntry 3 }

sm24tat4xbCISTPortPortPriority    OBJECT-TYPE
        SYNTAX      Integer32 (0|16|32|48|64|80|96|112|128|144|160|176|192|208|224|240)
        MAX-ACCESS  read-write
        STATUS      current
        DESCRIPTION
            "CIST Port Priority. range: 0-240, multiple of 16."
        ::= {     sm24tat4xbCISTPortsEntry 4 }

sm24tat4xbCISTPortAdminEdge    OBJECT-TYPE
        SYNTAX      Integer32 (0|1)
        MAX-ACCESS  read-write
        STATUS      current
        DESCRIPTION
            "CIST Port Admin Edge. range: 0-1.
				    0:Non-Edge
				    1:Edge."
        ::= {     sm24tat4xbCISTPortsEntry 5 }

sm24tat4xbCISTPortAutoEdge    OBJECT-TYPE
        SYNTAX      Integer32 (0|1)
        MAX-ACCESS  read-write
        STATUS      current
        DESCRIPTION
            "CIST Port Auto Edge. range: 0-1.
				    0:disable
				    1:enable."
        ::= {     sm24tat4xbCISTPortsEntry 6 }

sm24tat4xbCISTPortrestrictedRole    OBJECT-TYPE
        SYNTAX      Integer32 (0|1)
        MAX-ACCESS  read-write
        STATUS      current
        DESCRIPTION
            "CIST Port restricted Role. range: 0-1.
				    0:disable
				    1:enable."
        ::= {     sm24tat4xbCISTPortsEntry 7 }

sm24tat4xbCISTPortrestrictedTcn    OBJECT-TYPE
        SYNTAX      Integer32 (0|1)
        MAX-ACCESS  read-write
        STATUS      current
        DESCRIPTION
            "CIST Port restricted Tcn. range: 0-1.
				    0:disable
				    1:enable."
        ::= {     sm24tat4xbCISTPortsEntry 8 }

sm24tat4xbCISTPortbpduGuard    OBJECT-TYPE
        SYNTAX      Integer32 (0|1)
        MAX-ACCESS  read-write
        STATUS      current
        DESCRIPTION
            "CIST Port bpdu Guard. range: 0-1.
				    0:disable
				    1:enable."
        ::= {     sm24tat4xbCISTPortsEntry 9 }

sm24tat4xbCISTPortPointToPoint    OBJECT-TYPE
        SYNTAX      Integer32 (0..2)
        MAX-ACCESS  read-write
        STATUS      current
        DESCRIPTION
            "CIST Port Point To Point. range: 0-2.
				    0:Forced True
				    1:Forced False.
				    2:Auto"
        ::= {     sm24tat4xbCISTPortsEntry 10 }

sm24tat4xbCISTPortRootGuard    OBJECT-TYPE
        SYNTAX      Integer32 (0|1)
        MAX-ACCESS  read-write
        STATUS      current
        DESCRIPTION
            "CIST Port root guard. range: 0-1.
				    0:disable
				    1:enable."
        ::= {     sm24tat4xbCISTPortsEntry 11 }

sm24tat4xbMSTIPorts              OBJECT IDENTIFIER ::= { sm24tat4xbSpanningTree 6 }


sm24tat4xbMSTIAggregatedPortsTable OBJECT-TYPE
    SYNTAX      SEQUENCE OF SM24TAT4XBMSTIAggregatedPortsEntry
    MAX-ACCESS  not-accessible
    STATUS      current
    DESCRIPTION
        "A table of MSTI ports."
    ::= { sm24tat4xbMSTIPorts 1 }

sm24tat4xbMSTIAggregatedPortsEntry OBJECT-TYPE
    SYNTAX    SM24TAT4XBMSTIAggregatedPortsEntry
    MAX-ACCESS    not-accessible
    STATUS    current
    DESCRIPTION
        "An entry in the MSTI ports Table."
    INDEX    { sm24tat4xbMSTIAggregatedPortsMSTIndex }
    ::= { sm24tat4xbMSTIAggregatedPortsTable 1 }

SM24TAT4XBMSTIAggregatedPortsEntry ::=
    SEQUENCE {
    sm24tat4xbMSTIAggregatedPortsMSTIndex            Integer32,
    sm24tat4xbMSTIAggregatedPortsPathCost            Integer32,
    sm24tat4xbMSTIAggregatedPortsPortPriority            Integer32
    }

sm24tat4xbMSTIAggregatedPortsMSTIndex OBJECT-TYPE
    SYNTAX      Integer32 (1..7)
    MAX-ACCESS  not-accessible
    STATUS      current
    DESCRIPTION
        "MST index, range:1-7"
    ::= {sm24tat4xbMSTIAggregatedPortsEntry 1 }

sm24tat4xbMSTIAggregatedPortsPathCost    OBJECT-TYPE
    SYNTAX      Integer32 (0..200000000)
    MAX-ACCESS  read-write
    STATUS      current
    DESCRIPTION
        "MST Path Cost. range: 0-200000000. 0 is Auto."
    ::= {sm24tat4xbMSTIAggregatedPortsEntry 3 }

sm24tat4xbMSTIAggregatedPortsPortPriority    OBJECT-TYPE
    SYNTAX      Integer32 (0|16|32|48|64|80|96|112|128|144|160|176|192|208|224|240)
    MAX-ACCESS  read-write
    STATUS      current
    DESCRIPTION
        "MST Port Priority. range: 0-240, multiple of 16."
    ::= {sm24tat4xbMSTIAggregatedPortsEntry 4 }


sm24tat4xbMSTIPortsTable OBJECT-TYPE
    SYNTAX      SEQUENCE OF SM24TAT4XBMSTIPortsEntry
    MAX-ACCESS  not-accessible
    STATUS      current
    DESCRIPTION
        "A table of MSTI ports."
    ::= { sm24tat4xbMSTIPorts 2 }

sm24tat4xbMSTIPortsEntry OBJECT-TYPE
    SYNTAX    SM24TAT4XBMSTIPortsEntry
    MAX-ACCESS    not-accessible
    STATUS    current
    DESCRIPTION
        "An entry in the MSTI ports Table."
    INDEX    { sm24tat4xbMSTIPortsMSTIndex, sm24tat4xbMSTIPortsPortIndex }
    ::= { sm24tat4xbMSTIPortsTable 1 }

SM24TAT4XBMSTIPortsEntry ::=
    SEQUENCE {
    sm24tat4xbMSTIPortsMSTIndex            Integer32,
    sm24tat4xbMSTIPortsPortIndex            Integer32,
    sm24tat4xbMSTIPortsPathCost            Integer32,
    sm24tat4xbMSTIPortsPortPriority            Integer32
    }

sm24tat4xbMSTIPortsMSTIndex OBJECT-TYPE
    SYNTAX      Integer32 (1..7)
    MAX-ACCESS  not-accessible
    STATUS      current
    DESCRIPTION
        "MST index, range:1-7"
    ::= {sm24tat4xbMSTIPortsEntry 1 }

sm24tat4xbMSTIPortsPortIndex OBJECT-TYPE
    SYNTAX      Integer32 (1..53)
    MAX-ACCESS  not-accessible
    STATUS      current
    DESCRIPTION
        "Port index, range 1-53, 53 is Aggregated Ports Configuration."
    ::= {sm24tat4xbMSTIPortsEntry 2 }

sm24tat4xbMSTIPortsPathCost    OBJECT-TYPE
    SYNTAX      Integer32 (0..200000000)
    MAX-ACCESS  read-write
    STATUS      current
    DESCRIPTION
        "MST Path Cost. range: 0-200000000. 0 is Auto."
    ::= {sm24tat4xbMSTIPortsEntry 3 }

sm24tat4xbMSTIPortsPortPriority    OBJECT-TYPE
    SYNTAX      Integer32 (0|16|32|48|64|80|96|112|128|144|160|176|192|208|224|240)
    MAX-ACCESS  read-write
    STATUS      current
    DESCRIPTION
        "MST Port Priority. range: 0-240, multiple of 16."
    ::= {sm24tat4xbMSTIPortsEntry 4 }

-- =======================================================================================================================
sm24tat4xbPrivateVLANs 						OBJECT IDENTIFIER ::= { sm24tat4xbConfiguration 19 }

sm24tat4xbPVLANMembershipTable  OBJECT-TYPE
    SYNTAX      SEQUENCE OF SM24TAT4XBPVLANMembershipEntry
    MAX-ACCESS  not-accessible
    STATUS      current
    DESCRIPTION
        "A table of Private VLAN Membership."
    ::= { sm24tat4xbPrivateVLANs 1 }

sm24tat4xbPVLANMembershipEntry OBJECT-TYPE
    SYNTAX    SM24TAT4XBPVLANMembershipEntry
    MAX-ACCESS    not-accessible
    STATUS    current
    DESCRIPTION
        "An entry in the private VLAN table."
    INDEX    { sm24tat4xbPVLANMembershipIndex }
    ::= { sm24tat4xbPVLANMembershipTable 1 }

SM24TAT4XBPVLANMembershipEntry ::=
    SEQUENCE {
    sm24tat4xbPVLANMembershipIndex            Integer32,
    sm24tat4xbPVLANID                 Integer32,
    sm24tat4xbPVLANMembers                DisplayString,
    sm24tat4xbPVLANRowStatus              RowStatus
    }

sm24tat4xbPVLANMembershipIndex OBJECT-TYPE
    SYNTAX      Integer32 (1..28)
    MAX-ACCESS  not-accessible
    STATUS      current
    DESCRIPTION
        "PVLAN membership index. Range:1-28."
    ::= {sm24tat4xbPVLANMembershipEntry 1 }

sm24tat4xbPVLANID OBJECT-TYPE
    SYNTAX      Integer32 (1..28)
    MAX-ACCESS  read-create
    STATUS      current
    DESCRIPTION
        "PVLAN ID. Range:1-28."
    ::= {sm24tat4xbPVLANMembershipEntry 2 }

sm24tat4xbPVLANMembers OBJECT-TYPE
    SYNTAX      DisplayString
    MAX-ACCESS  read-create
    STATUS      current
    DESCRIPTION
        "PVLAN Members. Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1',
        then that port is included in the set of ports; the port
        is not included if its bit has a value of '0'."
    ::= {sm24tat4xbPVLANMembershipEntry 3 }

sm24tat4xbPVLANRowStatus OBJECT-TYPE
    SYNTAX      RowStatus
    MAX-ACCESS  read-create
    STATUS      current
    DESCRIPTION
        "PVLAN Row Status."
    ::= {sm24tat4xbPVLANMembershipEntry 4 }

sm24tat4xbPVLANPortIsolationTable  OBJECT-TYPE
    SYNTAX      SEQUENCE OF SM24TAT4XBPVLANPortIsolationEntry
    MAX-ACCESS  not-accessible
    STATUS      current
    DESCRIPTION
        "A table of Private VLAN Port Isolation."
    ::= { sm24tat4xbPrivateVLANs 2 }

sm24tat4xbPVLANPortIsolationEntry OBJECT-TYPE
    SYNTAX    SM24TAT4XBPVLANPortIsolationEntry
    MAX-ACCESS    not-accessible
    STATUS    current
    DESCRIPTION
        "An entry in the private VLAN table."
    INDEX    { sm24tat4xbPVLANPortIsolationIndex }
    ::= { sm24tat4xbPVLANPortIsolationTable 1 }

SM24TAT4XBPVLANPortIsolationEntry ::=
    SEQUENCE {
    sm24tat4xbPVLANPortIsolationIndex         Integer32,
    sm24tat4xbPVLANPortIsolationPortMembers        Integer32
    }

sm24tat4xbPVLANPortIsolationIndex OBJECT-TYPE
    SYNTAX      Integer32 (1..28)
    MAX-ACCESS  not-accessible
    STATUS      current
    DESCRIPTION
        "PVLAN Port Isolation Index. Range:1-28."
    ::= {sm24tat4xbPVLANPortIsolationEntry 1 }

sm24tat4xbPVLANPortIsolationPortMembers OBJECT-TYPE
    SYNTAX      Integer32 (0|1)
    MAX-ACCESS  read-write
    STATUS      current
    DESCRIPTION
        "PVLAN Port Isolation Port Members enable/disable. Range:0-1.
	    1:Port Isolation enable  on that port.
	    0:Port Isolation disable on that port."
    ::= {sm24tat4xbPVLANPortIsolationEntry 2 }

-- =======================================================================================================================


sm24tat4xbsFlow 						OBJECT IDENTIFIER ::= { sm24tat4xbConfiguration 20 }

    sm24tat4xbsFlowVersion OBJECT-TYPE
        SYNTAX      SnmpAdminString
        MAX-ACCESS  read-only
        STATUS      current
        DESCRIPTION
            "Uniquely identifies the version and implementation of this MIB. The version string must have the following structure: <MIB Version>;<Organization>;<Software Revision> where: <MIB Version>  must be '1.3', the version of this MIB.
            <Organization> the name of the organization responsible for the agent implementation. <Revision>     the specific software build of this agent.
            As an example, the string '1.3;InMon Corp.;2.1.1' indicates that this agent implements version '1.2' of the SFLOW MIB, that
            it was developed by 'InMon Corp.' and that the software build is '2.1.1'.
            The MIB Version will change with each revision of the SFLOW MIB.
            Management entities must check the MIB Version and not attempt to manage agents with MIB Versions greater than that for which
            they were designed.
            Note: The sFlow Datagram Format has an independent version number which may change independently from <MIB Version>.
            <MIB Version> applies to the structure and semantics of the SFLOW MIB only." DEFVAL { "1.3;;" }
        ::= { sm24tat4xbsFlow 1 }

    sm24tat4xbsFlowAgentAddressType OBJECT-TYPE
        SYNTAX      InetAddressType
        MAX-ACCESS  read-only
        STATUS      current
        DESCRIPTION 
            "The address type of the address associated with this agent. Only ipv4 and ipv6 types are supported. ipv4:1, ipv6:2."
        ::= { sm24tat4xbsFlow 2 }

    sm24tat4xbsFlowAgentAddress OBJECT-TYPE
        SYNTAX      IpAddress
        MAX-ACCESS  read-write
        STATUS      current
        DESCRIPTION 
            "The IP address associated with this agent. In the case of a multi-homed agent, this should be the loopback address of the
            agent. The sFlowAgent address must provide SNMP connectivity to the agent. The address should be an invariant that does not
            change as interfaces are reconfigured, enabled, disabled, added or removed. A manager should be able to use the
            sFlowAgentAddress as a unique key that will identify this agent over extended periods of time so that a history can
            be maintained."
        ::= { sm24tat4xbsFlow 3 }
      --
      -- Receiver Table
      --
    sm24tat4xbsFlowRcvrTable OBJECT-TYPE
        SYNTAX      SEQUENCE OF SM24TAT4XBSFlowRcvrEntry
        MAX-ACCESS  not-accessible
        STATUS      current
        DESCRIPTION 
            "A table of the receivers of sFlow information."
        ::= { sm24tat4xbsFlow 4 }

    sm24tat4xbsFlowRcvrEntry OBJECT-TYPE
        SYNTAX SM24TAT4XBSFlowRcvrEntry
        MAX-ACCESS  not-accessible
        STATUS      current
        DESCRIPTION 
            "Attributes of an sFlow Receiver."
        INDEX { sm24tat4xbsFlowRcvrIndex }
        ::= { sm24tat4xbsFlowRcvrTable 1 }

    SM24TAT4XBSFlowRcvrEntry ::= SEQUENCE {
        sm24tat4xbsFlowRcvrIndex            Integer32,
        sm24tat4xbsFlowRcvrOwner            OwnerString,
        sm24tat4xbsFlowRcvrTimeout          Integer32,
        sm24tat4xbsFlowRcvrMaximumDatagramSize      Integer32,
        sm24tat4xbsFlowRcvrAddressType          InetAddressType,
        sm24tat4xbsFlowRcvrAddress          IpAddress,
        sm24tat4xbsFlowRcvrPort             Integer32,
        sm24tat4xbsFlowRcvrDatagramVersion      Integer32 }

    sm24tat4xbsFlowRcvrIndex OBJECT-TYPE
        SYNTAX      Integer32 (1..65535)
        MAX-ACCESS  not-accessible
        STATUS      current
        DESCRIPTION 
            "Index into sFlowReceiverTable."
        ::= { sm24tat4xbsFlowRcvrEntry 1 }

    sm24tat4xbsFlowRcvrOwner OBJECT-TYPE
        SYNTAX      OwnerString
        MAX-ACCESS  read-write
        STATUS      current
        DESCRIPTION 
            "The entity making use of this sFlowRcvrTable entry. The empty string indicates that the entry is currently unclaimed.
            An entity wishing to claim an sFlowRcvrTable entry must ensure that the entry is unclaimed before trying to claim it.
            The entry is claimed by setting the owner string. The entry must be claimed before any changes can be made to other sampler
            objects.
            In order to avoid a race condition, the entity taking control of the sampler must set both the owner and a value for
            sFlowRcvrTimeout in the same SNMP set request.
            When a management entity is finished using the sampler, it should set the value of sFlowRcvrOwner back to unclaimed.
            The agent must restore all other entities this row to their default values when the owner is set to unclaimed. It must
            also free all other resources associated with this sFlowRcvrTable entry.
            This mechanism provides no enforcement and relies on the cooperation of management entities in order to ensure that
            competition for a receiver entry is fairly resolved." DEFVAL { "" }
        ::= { sm24tat4xbsFlowRcvrEntry 2 }

    sm24tat4xbsFlowRcvrTimeout OBJECT-TYPE
        SYNTAX      Integer32
        MAX-ACCESS  read-write
        STATUS      current
        DESCRIPTION 
            "The time (in seconds) remaining before the sampler is released and stops sampling. When set, the owner establishes control
            for the specified period. When read, the remaining time in the interval is returned.
            A management entity wanting to maintain control of the sampler is responsible for setting a new value before the old one
            expires.
            When the interval expires, the agent is responsible for restoring all other entities in this row to their default
            values. It must also free all other resources associated with this sFlowRcvrTable entry." DEFVAL { 0 }
        ::= { sm24tat4xbsFlowRcvrEntry 3 }

    sm24tat4xbsFlowRcvrMaximumDatagramSize OBJECT-TYPE
        SYNTAX      Integer32
        MAX-ACCESS  read-write
        STATUS      current
        DESCRIPTION
             "The maximum number of data bytes that can be sent in a single sample datagram. The manager should set this value to avoid fragmentation of the sFlow datagrams." DEFVAL { 1400 }
        ::= { sm24tat4xbsFlowRcvrEntry 4 }

    sm24tat4xbsFlowRcvrAddressType OBJECT-TYPE
        SYNTAX      InetAddressType
        MAX-ACCESS  read-write
        STATUS      current
        DESCRIPTION 
            "The type of sFlowRcvrCollectorAddress." DEFVAL { ipv4 }
        ::= { sm24tat4xbsFlowRcvrEntry 5 }

    sm24tat4xbsFlowRcvrAddress OBJECT-TYPE
        SYNTAX      IpAddress
        MAX-ACCESS  read-write
        STATUS      current
        DESCRIPTION
            "The IP address of the sFlow collector. If set to 0.0.0.0 not sFlow datagrams will be sent." DEFVAL { '00000000'h }  -- 0.0.0.0
        ::= { sm24tat4xbsFlowRcvrEntry 6 }

    sm24tat4xbsFlowRcvrPort OBJECT-TYPE
        SYNTAX      Integer32
        MAX-ACCESS  read-write
        STATUS      current
        DESCRIPTION "The destination port for sFlow datagrams." DEFVAL { 6343 }
        ::= { sm24tat4xbsFlowRcvrEntry 7 }

    sm24tat4xbsFlowRcvrDatagramVersion OBJECT-TYPE
        SYNTAX      Integer32
        MAX-ACCESS  read-write
        STATUS      current
        DESCRIPTION
            "The version of sFlow datagrams that should be sent.
            When set to a value not support by the agent, the agent should adjust the value to the highest supported value less than the
            requested value, or return an SNMP bad value error if no such value exists." DEFVAL { 5 }
        ::= { sm24tat4xbsFlowRcvrEntry 8 }

      --
      -- Flow Sampling Table
      --
    sm24tat4xbsFlowFsTable OBJECT-TYPE
        SYNTAX      SEQUENCE OF SM24TAT4XBSFlowFsEntry
        MAX-ACCESS  not-accessible
        STATUS      current
        DESCRIPTION "A table of the flow samplers within a device."
        ::= { sm24tat4xbsFlow 5 }

    sm24tat4xbsFlowFsEntry OBJECT-TYPE
        SYNTAX      SM24TAT4XBSFlowFsEntry
        MAX-ACCESS  not-accessible
        STATUS      current
        DESCRIPTION "Attributes of a flow sampler."
        INDEX { sm24tat4xbsFlowFsDataSource, sm24tat4xbsFlowFsInstance }
        ::= { sm24tat4xbsFlowFsTable 1 }

    SM24TAT4XBSFlowFsEntry ::= SEQUENCE {
        sm24tat4xbsFlowFsDataSource        Integer32,
        sm24tat4xbsFlowFsInstance         Integer32,
        sm24tat4xbsFlowFsReceiver         Integer32,
        sm24tat4xbsFlowFsPacketSamplingRate    Integer32,
        sm24tat4xbsFlowFsMaximumHeaderSize    Integer32,
        sm24tat4xbsFlowFsType             Integer32
        }

    sm24tat4xbsFlowFsDataSource OBJECT-TYPE
        SYNTAX      Integer32(1..65535)
        MAX-ACCESS  not-accessible
        STATUS      current
        DESCRIPTION "sFlowDataSource for this flow sampler."
        ::= { sm24tat4xbsFlowFsEntry 1 }

    sm24tat4xbsFlowFsInstance OBJECT-TYPE
        SYNTAX      Integer32 (1..65535)
        MAX-ACCESS  not-accessible
        STATUS      current
        DESCRIPTION "The sFlow instance for this flow sampler."
        ::= { sm24tat4xbsFlowFsEntry 2 }

    sm24tat4xbsFlowFsReceiver OBJECT-TYPE
        SYNTAX      Integer32
        MAX-ACCESS  read-write
        STATUS      current
        DESCRIPTION "The SFlowReceiver for this flow sampler." DEFVAL { 0 }
        ::= { sm24tat4xbsFlowFsEntry 3 }

    sm24tat4xbsFlowFsPacketSamplingRate OBJECT-TYPE
        SYNTAX      Integer32
        MAX-ACCESS  read-write
        STATUS      current
        DESCRIPTION 
            "The statistical sampling rate for packet sampling from this source.
            Set to N to sample 1/Nth of the packets in the monitored flows. An agent should choose its own algorithm to introduce variance
            into the sampling so that exactly every Nth packet is not counted. A sampling rate of 1 counts all packets. A sampling
            rate of 0 disables sampling.
            The agent is permitted to have minimum and maximum allowable values for the sampling rate. A minimum rate lets the agent
            designer set an upper bound on the overhead associated with sampling, and a maximum rate may be the result of hardware
            restrictions (such as counter size). In addition not all values between the maximum and minimum may be realizable as the
            sampling rate (again because of implementation considerations).
            When the sampling rate is set the agent is free to adjust the value so that it lies between the maximum and minimum values
            and has the closest achievable value.
            When read, the agent must return the actual sampling rate it will be using (after the adjustments previously described). The
            sampling algorithm must converge so that over time the number of packets sampled approaches 1/Nth of the total number of
            packets in the monitored flows." DEFVAL { 0 }
        ::= { sm24tat4xbsFlowFsEntry 4 }

    sm24tat4xbsFlowFsMaximumHeaderSize OBJECT-TYPE
        SYNTAX      Integer32
        MAX-ACCESS  read-write
        STATUS      current
        DESCRIPTION 
            "The maximum number of bytes that should be copied from a sampled packet. The agent may have an internal maximum and
            minimum permissible sizes. If an attempt is made to set this value outside the permissible range then the agent should
            adjust the value to the closest permissible value." DEFVAL { 128 }
        ::= { sm24tat4xbsFlowFsEntry 5 }

    sm24tat4xbsFlowFsType OBJECT-TYPE
        SYNTAX      Integer32
        MAX-ACCESS  read-write
        STATUS      current
        DESCRIPTION
            "Flow Sample Type.
            1:Rx
            2:Tx
            3:All."
        DEFVAL { 2 }
        ::= { sm24tat4xbsFlowFsEntry 6 }
      --
      -- Counter Polling Table
      --
    sm24tat4xbsFlowCpTable OBJECT-TYPE
        SYNTAX      SEQUENCE OF SM24TAT4XBSFlowCpEntry
        MAX-ACCESS  not-accessible
        STATUS      current
        DESCRIPTION "A table of the counter pollers within a device."
        ::= { sm24tat4xbsFlow 6 }

    sm24tat4xbsFlowCpEntry OBJECT-TYPE
        SYNTAX      SM24TAT4XBSFlowCpEntry
        MAX-ACCESS  not-accessible
        STATUS      current
        DESCRIPTION "Attributes of a counter poller."
        INDEX { sm24tat4xbsFlowCpDataSource, sm24tat4xbsFlowCpInstance }
        ::= { sm24tat4xbsFlowCpTable 1 }

    SM24TAT4XBSFlowCpEntry ::= SEQUENCE {
        sm24tat4xbsFlowCpDataSource        Integer32,
        sm24tat4xbsFlowCpInstance         Integer32,
        sm24tat4xbsFlowCpReceiver         Integer32,
        sm24tat4xbsFlowCpInterval         Integer32
        }

    sm24tat4xbsFlowCpDataSource OBJECT-TYPE
        SYNTAX      Integer32(1..65535)
        MAX-ACCESS  not-accessible
        STATUS      current
        DESCRIPTION "Identifies the source of the data for the counter poller."
        ::= { sm24tat4xbsFlowCpEntry 1 }

    sm24tat4xbsFlowCpInstance OBJECT-TYPE
        SYNTAX      Integer32 (1..65535)
        MAX-ACCESS  not-accessible
        STATUS      current
        DESCRIPTION "The sFlowInstance for this counter poller."
        ::= { sm24tat4xbsFlowCpEntry 2 }

    sm24tat4xbsFlowCpReceiver OBJECT-TYPE
        SYNTAX      Integer32
        MAX-ACCESS  read-write
        STATUS      current
        DESCRIPTION "The SFlowReciever associated with this counter poller." DEFVAL { 0 }
        ::= { sm24tat4xbsFlowCpEntry 3 }

    sm24tat4xbsFlowCpInterval OBJECT-TYPE
        SYNTAX      Integer32
        MAX-ACCESS  read-write
        STATUS      current
        DESCRIPTION 
            "The maximum number of seconds between successive samples of the counters associated with this data source. A sampling interval
            of 0 disables counter sampling.
            The agent is permitted to have minimum and maximum allowable values for the counter polling interval. A minimum interval
            lets the agent designer set an upper bound on the overhead associated with polling, and a maximum interval may be the
            result of implementation restrictions (such as counter size). In addition not all values between the maximum and minimum may
            be realizable as the sampling interval (again because of implementation considerations).
            When the sampling rate is set the agent is free to adjust the value so that it lies between the maximum and minimum values
            and has the closest achievable value.
            When read, the agent must return the actual sampling interval it will be using (after the adjustments previously described).
            The sampling algorithm must converge so that over time the number of packets sampled approaches 1/Nth of the total number
            of packets in the monitored flows." DEFVAL { 0 }
        ::= { sm24tat4xbsFlowCpEntry 4 }

sm24tat4xbLLDP          OBJECT IDENTIFIER ::= { sm24tat4xbConfiguration 21 }

    sm24tat4xbLLDPConfTable OBJECT-TYPE
        SYNTAX      SEQUENCE OF     SM24TAT4XBLLDPConfEntry
        MAX-ACCESS  not-accessible
        STATUS      current
        DESCRIPTION
            " "
        ::= {     sm24tat4xbLLDP 1 }

    sm24tat4xbLLDPConfEntry OBJECT-TYPE
        SYNTAX      SM24TAT4XBLLDPConfEntry
        MAX-ACCESS  not-accessible
        STATUS      current
        DESCRIPTION
            " "
        INDEX    {    sm24tat4xbLLDPIndex  }
        ::= {     sm24tat4xbLLDPConfTable 1 }

    SM24TAT4XBLLDPConfEntry         ::= SEQUENCE {
     sm24tat4xbLLDPIndex    Integer32,
     sm24tat4xbLLDPMode     Integer32,
     sm24tat4xbLLDPCDPAware     Integer32,
     sm24tat4xbLLDPTrap     Integer32,
     sm24tat4xbLLDPPortDescr    Integer32,
		 sm24tat4xbLLDPSysName      Integer32,
		 sm24tat4xbLLDPSysDescr     Integer32,
		 sm24tat4xbLLDPSysCapa      Integer32,
		 sm24tat4xbLLDPMgmtAddr     Integer32
    }

    sm24tat4xbLLDPIndex OBJECT-TYPE
        SYNTAX      Integer32(1..65535)
        MAX-ACCESS  read-write
        STATUS      current
        DESCRIPTION
            "LLDP configuration index."
        ::= {     sm24tat4xbLLDPConfEntry 1 }

    sm24tat4xbLLDPMode OBJECT-TYPE
        SYNTAX      Integer32
        MAX-ACCESS  read-write
        STATUS      current
        DESCRIPTION
            "0:Disable
		    1:Tx only
		    2:Rx only
		    3:Enabled"
        ::= {     sm24tat4xbLLDPConfEntry 2 }

    sm24tat4xbLLDPCDPAware OBJECT-TYPE
        SYNTAX      Integer32
        MAX-ACCESS  read-write
        STATUS      current
        DESCRIPTION
            "0:Disable
		    1:Enable"
        ::= {     sm24tat4xbLLDPConfEntry 3 }

    sm24tat4xbLLDPTrap OBJECT-TYPE
        SYNTAX      Integer32
        MAX-ACCESS  read-write
        STATUS      current
        DESCRIPTION
            "0:Disable
		    1:Enable"
        ::= {     sm24tat4xbLLDPConfEntry 4 }

    sm24tat4xbLLDPPortDescr OBJECT-TYPE
        SYNTAX      Integer32
        MAX-ACCESS  read-write
        STATUS      current
        DESCRIPTION
            "0:Disable
		    1:Enable"
        ::= {     sm24tat4xbLLDPConfEntry 5 }

    sm24tat4xbLLDPSysName OBJECT-TYPE
        SYNTAX      Integer32
        MAX-ACCESS  read-write
        STATUS      current
        DESCRIPTION
            "0:Disable
		    1:Enable"
        ::= {     sm24tat4xbLLDPConfEntry 6 }

    sm24tat4xbLLDPSysDescr OBJECT-TYPE
        SYNTAX      Integer32
        MAX-ACCESS  read-write
        STATUS      current
        DESCRIPTION
            "0:Disable
		    1:Enable"
        ::= {     sm24tat4xbLLDPConfEntry 7 }

    sm24tat4xbLLDPSysCapa OBJECT-TYPE
        SYNTAX      Integer32
        MAX-ACCESS  read-write
        STATUS      current
        DESCRIPTION
            "0:Disable
		    1:Enable"
        ::= {     sm24tat4xbLLDPConfEntry 8 }

    sm24tat4xbLLDPMgmtAddr OBJECT-TYPE
        SYNTAX      Integer32
        MAX-ACCESS  read-write
        STATUS      current
        DESCRIPTION
            "0:Disable
		    1:Enable"
        ::= {     sm24tat4xbLLDPConfEntry 9 }

sm24tat4xbLLDPMEDCoordinatesLocation              OBJECT IDENTIFIER ::= { sm24tat4xbLLDP 2 }

sm24tat4xbLLDPMEDLatitude    OBJECT-TYPE
    SYNTAX      DisplayString
    MAX-ACCESS  read-write
    STATUS      current
    DESCRIPTION
	    "Latitude SHOULD be normalized to within 0-90 degrees with a maximum of 4 digits."
    ::= { sm24tat4xbLLDPMEDCoordinatesLocation 2 }

sm24tat4xbLLDPMEDLatitudeDirection OBJECT-TYPE
    SYNTAX      Integer32(0|1)
    MAX-ACCESS  read-write
    STATUS      current
    DESCRIPTION
        "0:North
	    1:South"
    ::= { sm24tat4xbLLDPMEDCoordinatesLocation 3 }

sm24tat4xbLLDPMEDLongitude    OBJECT-TYPE
    SYNTAX      DisplayString
    MAX-ACCESS  read-write
    STATUS      current
    DESCRIPTION
	    "Longitude SHOULD be normalized to within 0-180 degrees with a maximum of 4 digits."
    ::= { sm24tat4xbLLDPMEDCoordinatesLocation 4 }

sm24tat4xbLLDPMEDLongitudeDirection OBJECT-TYPE
    SYNTAX      Integer32(0|1)
    MAX-ACCESS  read-write
    STATUS      current
    DESCRIPTION
        "0:East
	    1:West"
    ::= { sm24tat4xbLLDPMEDCoordinatesLocation 5 }

sm24tat4xbLLDPMEDAltitude    OBJECT-TYPE
    SYNTAX      DisplayString
    MAX-ACCESS  read-write
    STATUS      current
    DESCRIPTION
	    "Altitude SHOULD be normalized to within -2097151.9 to 2097151.9 with a maximum of 1 digits."
    ::= { sm24tat4xbLLDPMEDCoordinatesLocation 6 }

sm24tat4xbLLDPMEDAltitudeType OBJECT-TYPE
    SYNTAX      Integer32(1|2)
    MAX-ACCESS  read-write
    STATUS      current
    DESCRIPTION
        "1:Meters
	    2:Floors"
    ::= { sm24tat4xbLLDPMEDCoordinatesLocation 7 }

sm24tat4xbLLDPMEDMapDatum OBJECT-TYPE
    SYNTAX      Integer32(0..2)
    MAX-ACCESS  read-write
    STATUS      current
    DESCRIPTION
        "The Map Datum is used for the coordinates given in these options:
	    1:WGS84
	    2:NAD83/NAVD88
	    3:NAD83/MLLW
		"
    ::= { sm24tat4xbLLDPMEDCoordinatesLocation 8 }

sm24tat4xbLLDPMEDCivicAddressLocation              OBJECT IDENTIFIER ::= { sm24tat4xbLLDP 4 }

sm24tat4xbLLDPMEDCivicAddressLocationCountryCode    OBJECT-TYPE
    SYNTAX      DisplayString
    MAX-ACCESS  read-write
    STATUS      current
    DESCRIPTION
        " "
    ::= { sm24tat4xbLLDPMEDCivicAddressLocation 2 }

sm24tat4xbLLDPMEDCivicAddressLocationStateProvince    OBJECT-TYPE
    SYNTAX      DisplayString
    MAX-ACCESS  read-write
    STATUS      current
    DESCRIPTION
        " "
    ::= { sm24tat4xbLLDPMEDCivicAddressLocation 3 }

sm24tat4xbLLDPMEDCivicAddressLocationCounty    OBJECT-TYPE
    SYNTAX      DisplayString
    MAX-ACCESS  read-write
    STATUS      current
    DESCRIPTION
        " "
    ::= { sm24tat4xbLLDPMEDCivicAddressLocation 4 }

sm24tat4xbLLDPMEDCivicAddressLocationCity    OBJECT-TYPE
    SYNTAX      DisplayString
    MAX-ACCESS  read-write
    STATUS      current
    DESCRIPTION
        " "
    ::= { sm24tat4xbLLDPMEDCivicAddressLocation 5 }

sm24tat4xbLLDPMEDCivicAddressLocationCityDistrict    OBJECT-TYPE
    SYNTAX      DisplayString
    MAX-ACCESS  read-write
    STATUS      current
    DESCRIPTION
        " "
    ::= { sm24tat4xbLLDPMEDCivicAddressLocation 6 }

sm24tat4xbLLDPMEDCivicAddressLocationBlockNeighborhood    OBJECT-TYPE
    SYNTAX      DisplayString
    MAX-ACCESS  read-write
    STATUS      current
    DESCRIPTION
        " "
    ::= { sm24tat4xbLLDPMEDCivicAddressLocation 7 }

sm24tat4xbLLDPMEDCivicAddressLocationStreet    OBJECT-TYPE
    SYNTAX      DisplayString
    MAX-ACCESS  read-write
    STATUS      current
    DESCRIPTION
        " "
    ::= { sm24tat4xbLLDPMEDCivicAddressLocation 8 }

sm24tat4xbLLDPMEDCivicAddressLocationLeadingStreetDirection    OBJECT-TYPE
    SYNTAX      DisplayString
    MAX-ACCESS  read-write
    STATUS      current
    DESCRIPTION
        " "
    ::= { sm24tat4xbLLDPMEDCivicAddressLocation 9 }

sm24tat4xbLLDPMEDCivicAddressLocationTrailingStreetSuffix    OBJECT-TYPE
    SYNTAX      DisplayString
    MAX-ACCESS  read-write
    STATUS      current
    DESCRIPTION
        " "
    ::= { sm24tat4xbLLDPMEDCivicAddressLocation 10 }

sm24tat4xbLLDPMEDCivicAddressLocationStreetSuffix    OBJECT-TYPE
    SYNTAX      DisplayString
    MAX-ACCESS  read-write
    STATUS      current
    DESCRIPTION
        " "
    ::= { sm24tat4xbLLDPMEDCivicAddressLocation 11 }

sm24tat4xbLLDPMEDCivicAddressLocationHouseNo    OBJECT-TYPE
    SYNTAX      DisplayString
    MAX-ACCESS  read-write
    STATUS      current
    DESCRIPTION
        " "
    ::= { sm24tat4xbLLDPMEDCivicAddressLocation 12 }

sm24tat4xbLLDPMEDCivicAddressLocationHouseNoSuffix    OBJECT-TYPE
    SYNTAX      DisplayString
    MAX-ACCESS  read-write
    STATUS      current
    DESCRIPTION
        " "
    ::= { sm24tat4xbLLDPMEDCivicAddressLocation 13 }

sm24tat4xbLLDPMEDCivicAddressLocationLandmark    OBJECT-TYPE
    SYNTAX      DisplayString
    MAX-ACCESS  read-write
    STATUS      current
    DESCRIPTION
        " "
    ::= { sm24tat4xbLLDPMEDCivicAddressLocation 14 }

sm24tat4xbLLDPMEDCivicAddressLocationAdditionalLocationInfo    OBJECT-TYPE
    SYNTAX      DisplayString
    MAX-ACCESS  read-write
    STATUS      current
    DESCRIPTION
        " "
    ::= { sm24tat4xbLLDPMEDCivicAddressLocation 15 }

sm24tat4xbLLDPMEDCivicAddressLocationName    OBJECT-TYPE
    SYNTAX      DisplayString
    MAX-ACCESS  read-write
    STATUS      current
    DESCRIPTION
        " "
    ::= { sm24tat4xbLLDPMEDCivicAddressLocation 16 }

sm24tat4xbLLDPMEDCivicAddressLocationZipCode    OBJECT-TYPE
    SYNTAX      DisplayString
    MAX-ACCESS  read-write
    STATUS      current
    DESCRIPTION
        " "
    ::= { sm24tat4xbLLDPMEDCivicAddressLocation 17 }

sm24tat4xbLLDPMEDCivicAddressLocationBuilding    OBJECT-TYPE
    SYNTAX      DisplayString
    MAX-ACCESS  read-write
    STATUS      current
    DESCRIPTION
        " "
    ::= { sm24tat4xbLLDPMEDCivicAddressLocation 18 }

sm24tat4xbLLDPMEDCivicAddressLocationApartment    OBJECT-TYPE
    SYNTAX      DisplayString
    MAX-ACCESS  read-write
    STATUS      current
    DESCRIPTION
        " "
    ::= { sm24tat4xbLLDPMEDCivicAddressLocation 19 }

sm24tat4xbLLDPMEDCivicAddressLocationFloor    OBJECT-TYPE
    SYNTAX      DisplayString
    MAX-ACCESS  read-write
    STATUS      current
    DESCRIPTION
        " "
    ::= { sm24tat4xbLLDPMEDCivicAddressLocation 20 }

sm24tat4xbLLDPMEDCivicAddressLocationRoomNo    OBJECT-TYPE
    SYNTAX      DisplayString
    MAX-ACCESS  read-write
    STATUS      current
    DESCRIPTION
        " "
    ::= { sm24tat4xbLLDPMEDCivicAddressLocation 21 }

sm24tat4xbLLDPMEDCivicAddressLocationPlaceType    OBJECT-TYPE
    SYNTAX      DisplayString
    MAX-ACCESS  read-write
    STATUS      current
    DESCRIPTION
        " "
    ::= { sm24tat4xbLLDPMEDCivicAddressLocation 22 }

sm24tat4xbLLDPMEDCivicAddressLocationPostalCommunityName    OBJECT-TYPE
    SYNTAX      DisplayString
    MAX-ACCESS  read-write
    STATUS      current
    DESCRIPTION
        " "
    ::= { sm24tat4xbLLDPMEDCivicAddressLocation 23 }

sm24tat4xbLLDPMEDCivicAddressLocationPOBox    OBJECT-TYPE
    SYNTAX      DisplayString
    MAX-ACCESS  read-write
    STATUS      current
    DESCRIPTION
        " "
    ::= { sm24tat4xbLLDPMEDCivicAddressLocation 24 }

sm24tat4xbLLDPMEDCivicAddressLocationAdditionalCode    OBJECT-TYPE
    SYNTAX      DisplayString
    MAX-ACCESS  read-write
    STATUS      current
    DESCRIPTION
        " "
    ::= { sm24tat4xbLLDPMEDCivicAddressLocation 25 }


sm24tat4xbLLDPMEDPoliciesTable OBJECT-TYPE
    SYNTAX      SEQUENCE OF SM24TAT4XBLLDPMEDPoliciesEntry
    MAX-ACCESS  not-accessible
    STATUS      current
    DESCRIPTION
        " "
    ::= { sm24tat4xbLLDP 5 }

sm24tat4xbLLDPMEDPoliciesEntry OBJECT-TYPE
    SYNTAX      SM24TAT4XBLLDPMEDPoliciesEntry
    MAX-ACCESS  not-accessible
    STATUS      current
    DESCRIPTION
        " "
    INDEX    { sm24tat4xbLLDPMEDPoliciesIndex  }
    ::= { sm24tat4xbLLDPMEDPoliciesTable 1 }

SM24TAT4XBLLDPMEDPoliciesEntry ::= SEQUENCE {
    sm24tat4xbLLDPMEDPoliciesIndex        Integer32,
    sm24tat4xbLLDPMEDPoliciesPolicyID     Integer32,
    sm24tat4xbLLDPMEDPoliciesApplicationType  Integer32,
    sm24tat4xbLLDPMEDPoliciesTag          Integer32,
    sm24tat4xbLLDPMEDPoliciesVLANID        Integer32,
    sm24tat4xbLLDPMEDPoliciesL2Priority    Integer32,
    sm24tat4xbLLDPMEDPoliciesDSCP         Integer32,
    sm24tat4xbLLDPMEDPoliciesRowStatus    RowStatus
}

sm24tat4xbLLDPMEDPoliciesIndex OBJECT-TYPE
    SYNTAX      Integer32(1..65535)
    MAX-ACCESS  not-accessible
    STATUS      current
    DESCRIPTION
        "Index"
    ::= { sm24tat4xbLLDPMEDPoliciesEntry 1 }

sm24tat4xbLLDPMEDPoliciesPolicyID OBJECT-TYPE
    SYNTAX      Integer32
    MAX-ACCESS  read-only
    STATUS      current
    DESCRIPTION
        " "
    ::= { sm24tat4xbLLDPMEDPoliciesEntry 2 }

sm24tat4xbLLDPMEDPoliciesApplicationType OBJECT-TYPE
    SYNTAX      Integer32 (1..8)
    MAX-ACCESS  read-write
    STATUS      current
    DESCRIPTION
        "1:Voice
		2:Voice Signalling
		3:Guest Voice
		4:Guest Voice Signalling
		5:Softphone Voice
		6:Video Conferencing
		7:Streaming Video
		8:Video Signalling"
    ::= { sm24tat4xbLLDPMEDPoliciesEntry 3 }

sm24tat4xbLLDPMEDPoliciesTag OBJECT-TYPE
    SYNTAX      Integer32 (0|1)
    MAX-ACCESS  read-write
    STATUS      current
    DESCRIPTION
        "0:Untagged
	    1:Tagged"
    ::= { sm24tat4xbLLDPMEDPoliciesEntry 4 }

sm24tat4xbLLDPMEDPoliciesVLANID OBJECT-TYPE
    SYNTAX      Integer32 (1..4095)
    MAX-ACCESS  read-write
    STATUS      current
    DESCRIPTION
        "Range:1-4095"
    ::= { sm24tat4xbLLDPMEDPoliciesEntry 5 }

sm24tat4xbLLDPMEDPoliciesL2Priority OBJECT-TYPE
    SYNTAX      Integer32 (0..7)
    MAX-ACCESS  read-write
    STATUS      current
    DESCRIPTION
        "Range:0-7"
    ::= { sm24tat4xbLLDPMEDPoliciesEntry 6 }

sm24tat4xbLLDPMEDPoliciesDSCP OBJECT-TYPE
    SYNTAX      Integer32 (0..63)
    MAX-ACCESS  read-write
    STATUS      current
    DESCRIPTION
        "Range:0-63"
    ::= { sm24tat4xbLLDPMEDPoliciesEntry 7 }

sm24tat4xbLLDPMEDPoliciesRowStatus OBJECT-TYPE
    SYNTAX      RowStatus
    MAX-ACCESS  read-create
    STATUS      current
    DESCRIPTION
        "Row Status."
    ::= { sm24tat4xbLLDPMEDPoliciesEntry 8 }

sm24tat4xbLLDPMEDPolicyPortConfTable OBJECT-TYPE
    SYNTAX      SEQUENCE OF SM24TAT4XBLLDPMEDPolicyPortConfEntry
    MAX-ACCESS  not-accessible
    STATUS      current
    DESCRIPTION
        " "
    ::= { sm24tat4xbLLDP 6 }

sm24tat4xbLLDPMEDPolicyPortConfEntry OBJECT-TYPE
    SYNTAX      SM24TAT4XBLLDPMEDPolicyPortConfEntry
    MAX-ACCESS  not-accessible
    STATUS      current
    DESCRIPTION
        " "
    INDEX    { sm24tat4xbLLDPMEDPolicyPortConfPort  }
    ::= { sm24tat4xbLLDPMEDPolicyPortConfTable 1 }

SM24TAT4XBLLDPMEDPolicyPortConfEntry ::= SEQUENCE {
    sm24tat4xbLLDPMEDPolicyPortConfPort    Integer32,
    sm24tat4xbLLDPMEDPolicyPortConf        Integer32
}

sm24tat4xbLLDPMEDPolicyPortConfPort OBJECT-TYPE
    SYNTAX      Integer32(1..65535)
    MAX-ACCESS  not-accessible
    STATUS      current
    DESCRIPTION
        "Index"
    ::= { sm24tat4xbLLDPMEDPolicyPortConfEntry 1 }

sm24tat4xbLLDPMEDPolicyPortConf OBJECT-TYPE
    SYNTAX      Integer32 (0|1)
    MAX-ACCESS  read-write
    STATUS      current
    DESCRIPTION
        "0:Disable
	    1:Enable"
    ::= { sm24tat4xbLLDPMEDPolicyPortConfEntry 2 }

sm24tat4xbLLDPMEDFastStartRepeatCount OBJECT-TYPE
    SYNTAX      Integer32 (1..10)
    MAX-ACCESS  read-write
    STATUS      current
    DESCRIPTION
        "Range:1-10"
    ::= { sm24tat4xbLLDP 7 }

sm24tat4xbLLDPMEDEmergencyCallService OBJECT-TYPE
    SYNTAX      DisplayString
    MAX-ACCESS  read-write
    STATUS      current
    DESCRIPTION
        " "
    ::= { sm24tat4xbLLDP 8 }

sm24tat4xbUDLD    OBJECT IDENTIFIER ::= { sm24tat4xbConfiguration 22 }

sm24tat4xbUDLDPortConfigTable OBJECT-TYPE
    SYNTAX      SEQUENCE OF SM24TAT4XBUDLDPortConfigEntry
    MAX-ACCESS  not-accessible
    STATUS      current
    DESCRIPTION
        " "
    ::= { sm24tat4xbUDLD 1 }

sm24tat4xbUDLDPortConfigEntry OBJECT-TYPE
    SYNTAX      SM24TAT4XBUDLDPortConfigEntry
    MAX-ACCESS  not-accessible
    STATUS      current
    DESCRIPTION
        " "
    INDEX    { sm24tat4xbUDLDPort  }
    ::= { sm24tat4xbUDLDPortConfigTable 1 }

SM24TAT4XBUDLDPortConfigEntry ::= SEQUENCE {
    sm24tat4xbUDLDPort            Integer32,
    sm24tat4xbUDLDPortMode            Integer32,
    sm24tat4xbUDLDPortMessageInterval    Integer32
}

sm24tat4xbUDLDPort OBJECT-TYPE
    SYNTAX      Integer32(1..65535)
    MAX-ACCESS  not-accessible
    STATUS      current
    DESCRIPTION
        " "
    ::= { sm24tat4xbUDLDPortConfigEntry 1 }

sm24tat4xbUDLDPortMode OBJECT-TYPE
    SYNTAX      Integer32 (0|1|2)
    MAX-ACCESS  read-write
    STATUS      current
    DESCRIPTION
        "default: 0
        0: disable
        1: Normal
	    2: Aggressive"
    ::= { sm24tat4xbUDLDPortConfigEntry 2 }

sm24tat4xbUDLDPortMessageInterval OBJECT-TYPE
    SYNTAX      Integer32(7..90)
    MAX-ACCESS  read-write
    STATUS      current
    DESCRIPTION
        "default: 7, range: 7-90"
    ::= { sm24tat4xbUDLDPortConfigEntry 3 }


sm24tat4xbUDLDPortStatusTable OBJECT-TYPE
    SYNTAX      SEQUENCE OF SM24TAT4XBUDLDPortStatusEntry
    MAX-ACCESS  not-accessible
    STATUS      current
    DESCRIPTION
        " "
    ::= { sm24tat4xbUDLD 2 }

sm24tat4xbUDLDPortStatusEntry OBJECT-TYPE
    SYNTAX      SM24TAT4XBUDLDPortStatusEntry
    MAX-ACCESS  not-accessible
    STATUS      current
    DESCRIPTION
        " "
    INDEX    { sm24tat4xbUDLDPortStatusPort  }
    ::= { sm24tat4xbUDLDPortStatusTable 1 }

SM24TAT4XBUDLDPortStatusEntry ::= SEQUENCE {
    sm24tat4xbUDLDPortStatusPort            Integer32,
    sm24tat4xbUDLDStatusAdminState         Integer32,
    sm24tat4xbUDLDStatusDeviceIDLocal      DisplayString,
    sm24tat4xbUDLDStatusDeviceNameLocal    DisplayString,
    sm24tat4xbUDLDStatusBidirectionalState     DisplayString
}

sm24tat4xbUDLDPortStatusPort OBJECT-TYPE
    SYNTAX      Integer32(1..65535)
    MAX-ACCESS  not-accessible
    STATUS      current
    DESCRIPTION
        "Port index"
    ::= { sm24tat4xbUDLDPortStatusEntry 1 }

sm24tat4xbUDLDStatusAdminState OBJECT-TYPE
    SYNTAX      Integer32
    MAX-ACCESS  read-only
    STATUS      current
    DESCRIPTION
        "0:disable
	    1:enable"
    ::= { sm24tat4xbUDLDPortStatusEntry 2 }

sm24tat4xbUDLDStatusDeviceIDLocal OBJECT-TYPE
    SYNTAX      DisplayString
    MAX-ACCESS  read-only
    STATUS      current
    DESCRIPTION
        " "
    ::= { sm24tat4xbUDLDPortStatusEntry 3 }

sm24tat4xbUDLDStatusDeviceNameLocal OBJECT-TYPE
    SYNTAX      DisplayString
    MAX-ACCESS  read-only
    STATUS      current
    DESCRIPTION
        " "
    ::= { sm24tat4xbUDLDPortStatusEntry 4 }

sm24tat4xbUDLDStatusBidirectionalState OBJECT-TYPE
    SYNTAX      DisplayString
    MAX-ACCESS  read-only
    STATUS      current
    DESCRIPTION
        " "
    ::= { sm24tat4xbUDLDPortStatusEntry 5 }


sm24tat4xbUDLDStatusPort OBJECT-TYPE
    SYNTAX      Integer32
    MAX-ACCESS  read-write
    STATUS      current
    DESCRIPTION
        "Specify port number for check neighbour status"
    ::= { sm24tat4xbUDLD 3 }

sm24tat4xbUDLDPortNeighbourStatusTable OBJECT-TYPE
    SYNTAX      SEQUENCE OF SM24TAT4XBUDLDPortNeighbourStatusEntry
    MAX-ACCESS  not-accessible
    STATUS      current
    DESCRIPTION
        " "
    ::= { sm24tat4xbUDLD 4 }

sm24tat4xbUDLDPortNeighbourStatusEntry OBJECT-TYPE
    SYNTAX      SM24TAT4XBUDLDPortNeighbourStatusEntry
    MAX-ACCESS  not-accessible
    STATUS      current
    DESCRIPTION
        " "
    INDEX    { sm24tat4xbUDLDNeighbourPort  }
    ::= { sm24tat4xbUDLDPortNeighbourStatusTable 1 }

SM24TAT4XBUDLDPortNeighbourStatusEntry ::= SEQUENCE {
    sm24tat4xbUDLDNeighbourPort         Integer32,
    sm24tat4xbUDLDNeighbourStatusPort        DisplayString,
    sm24tat4xbUDLDNeighbourStatusDeviceId    DisplayString,
    sm24tat4xbUDLDNeighbourStatusLinkStatus     DisplayString,
    sm24tat4xbUDLDNeighbourStatusDeviceName     DisplayString
}

sm24tat4xbUDLDNeighbourPort OBJECT-TYPE
    SYNTAX      Integer32(1..65535)
    MAX-ACCESS  not-accessible
    STATUS      current
    DESCRIPTION
        "Index"
    ::= { sm24tat4xbUDLDPortNeighbourStatusEntry 1 }

sm24tat4xbUDLDNeighbourStatusPort OBJECT-TYPE
    SYNTAX      DisplayString
    MAX-ACCESS  read-only
    STATUS      current
    DESCRIPTION
        " "
    ::= { sm24tat4xbUDLDPortNeighbourStatusEntry 2 }

sm24tat4xbUDLDNeighbourStatusDeviceId OBJECT-TYPE
    SYNTAX      DisplayString
    MAX-ACCESS  read-only
    STATUS      current
    DESCRIPTION
        " "
    ::= { sm24tat4xbUDLDPortNeighbourStatusEntry 3 }

sm24tat4xbUDLDNeighbourStatusLinkStatus OBJECT-TYPE
    SYNTAX      DisplayString
    MAX-ACCESS  read-only
    STATUS      current
    DESCRIPTION
        " "
    ::= { sm24tat4xbUDLDPortNeighbourStatusEntry 4 }

sm24tat4xbUDLDNeighbourStatusDeviceName OBJECT-TYPE
    SYNTAX      DisplayString
    MAX-ACCESS  read-only
    STATUS      current
    DESCRIPTION
        " "
    ::= { sm24tat4xbUDLDPortNeighbourStatusEntry 5 }
-- =======================================================================================================================
sm24tat4xbEPS    OBJECT IDENTIFIER ::= { sm24tat4xbConfiguration 23 }

sm24tat4xbEPSTable  OBJECT-TYPE
    SYNTAX      SEQUENCE OF SM24TAT4XBEPSEntry
    MAX-ACCESS  not-accessible
    STATUS      current
    DESCRIPTION
        "A table of EPS."
    ::= { sm24tat4xbEPS 1 }

sm24tat4xbEPSEntry OBJECT-TYPE
    SYNTAX    SM24TAT4XBEPSEntry
    MAX-ACCESS    not-accessible
    STATUS    current
    DESCRIPTION
        ""
    INDEX    { sm24tat4xbEPSIndex }
    ::= { sm24tat4xbEPSTable 1 }

SM24TAT4XBEPSEntry ::=
    SEQUENCE {
    sm24tat4xbEPSIndex                Integer32,
    sm24tat4xbEpsID                    Integer32,
		sm24tat4xbEpsDomain                Integer32,
    sm24tat4xbEpsArchitecture             Integer32,
    sm24tat4xbEpsWFlow                Integer32,
    sm24tat4xbEpsPFlow                Integer32,
    sm24tat4xbEpsWSFMEP                Integer32,
    sm24tat4xbEpsPSFMEP                Integer32,
    sm24tat4xbEpsAPSMEP                Integer32,
    sm24tat4xbEpsAlarm                Integer32,
    sm24tat4xbEpsRowStatus                RowStatus
    }

sm24tat4xbEPSIndex OBJECT-TYPE
    SYNTAX      Integer32(1..65535)
    MAX-ACCESS  not-accessible
    STATUS      current
    DESCRIPTION
        "Index"
    ::= { sm24tat4xbEPSEntry 1 }

sm24tat4xbEpsID OBJECT-TYPE
    SYNTAX      Integer32 (1..100)
    MAX-ACCESS  read-create
    STATUS      current
    DESCRIPTION
        "EPS ID. Range:1-100."
    ::= {sm24tat4xbEPSEntry 2 }

sm24tat4xbEpsDomain OBJECT-TYPE
    SYNTAX      Integer32
    MAX-ACCESS  read-create
    STATUS      current
    DESCRIPTION
        "EPS Domain. Range:0.
	    0:Domain is Port"
    ::= {sm24tat4xbEPSEntry 3 }

sm24tat4xbEpsArchitecture OBJECT-TYPE
    SYNTAX      Integer32
    MAX-ACCESS  read-create
    STATUS      current
    DESCRIPTION
        "EPS Architecture. Range:0-1.
	    0:Architecture is 1+1
	    1:Architecture is 1:1"
    ::= {sm24tat4xbEPSEntry 4 }

sm24tat4xbEpsWFlow OBJECT-TYPE
    SYNTAX      Integer32
    MAX-ACCESS  read-create
    STATUS      current
    DESCRIPTION
        "The working flow for the EPS."
    ::= {sm24tat4xbEPSEntry 5 }

sm24tat4xbEpsPFlow OBJECT-TYPE
    SYNTAX      Integer32
    MAX-ACCESS  read-create
    STATUS      current
    DESCRIPTION
        "The protecting flow for the EPS"
    ::= {sm24tat4xbEPSEntry 6 }

sm24tat4xbEpsWSFMEP OBJECT-TYPE
    SYNTAX      Integer32
    MAX-ACCESS  read-create
    STATUS      current
    DESCRIPTION
        "The working Signal Fail reporting MEP."
    ::= {sm24tat4xbEPSEntry 7 }

sm24tat4xbEpsPSFMEP OBJECT-TYPE
    SYNTAX      Integer32
    MAX-ACCESS  read-create
    STATUS      current
    DESCRIPTION
        "The protecting Signal Fail reporting MEP."
    ::= {sm24tat4xbEPSEntry 8 }

sm24tat4xbEpsAPSMEP OBJECT-TYPE
    SYNTAX      Integer32
    MAX-ACCESS  read-create
    STATUS      current
    DESCRIPTION
        "The APS PDU handling MEP."
    ::= {sm24tat4xbEPSEntry 9 }

sm24tat4xbEpsAlarm OBJECT-TYPE
    SYNTAX      Integer32
    MAX-ACCESS  read-only
    STATUS      current
    DESCRIPTION
        "There is an active alarm on the EPS."
    ::= {sm24tat4xbEPSEntry 10 }

sm24tat4xbEpsRowStatus OBJECT-TYPE
    SYNTAX      RowStatus
    MAX-ACCESS  read-create
    STATUS      current
    DESCRIPTION
        "EPS Row Status."
    ::= {sm24tat4xbEPSEntry 11 }

sm24tat4xbEpsConfigInstanceEpsID    OBJECT-TYPE
    SYNTAX      Integer32
    MAX-ACCESS  read-write
    STATUS      current
    DESCRIPTION
	    "Specify EPS ID for table uesd."
    ::= {sm24tat4xbEPS 2 }


sm24tat4xbEPSConfigInstanceEntry    OBJECT IDENTIFIER ::= { sm24tat4xbEPS 3 }

sm24tat4xbEpsConfigInstanceProtectionType OBJECT-TYPE
    SYNTAX      Integer32
    MAX-ACCESS  read-write
    STATUS      current
    DESCRIPTION
        "Range:0-1.
	    0:Unidirectional: EPS in the two ends can select traffic from different working/protecting flow. This is only possible in case of 1+1.
        1:Bidirectional: EPS in the two ends is selecting traffic from the same working/protecting flow. This requires APS enabled. This is mandatory for 1:1"
    ::= { sm24tat4xbEPSConfigInstanceEntry 2 }

sm24tat4xbEpsConfigInstanceAPS OBJECT-TYPE
    SYNTAX      Integer32
    MAX-ACCESS  read-write
    STATUS      current
    DESCRIPTION
        "Range:0-1.
	    0:disable
	    1:enable
	    The Automatic Protection Switching protocol can be enabled/disabled. This is mandatory for 1:1."
    ::= { sm24tat4xbEPSConfigInstanceEntry 3 }

sm24tat4xbEpsConfigInstanceRevertive OBJECT-TYPE
    SYNTAX      Integer32
    MAX-ACCESS  read-write
    STATUS      current
    DESCRIPTION
        "Range:0-1.
	    0:disable
	    1:enable
		The revertive switching to working flow can be enabled/disabled.
		"
    ::= { sm24tat4xbEPSConfigInstanceEntry 4 }

sm24tat4xbEpsConfigInstanceWTRTime OBJECT-TYPE
    SYNTAX      Integer32
    MAX-ACCESS  read-write
    STATUS      current
    DESCRIPTION
        "The Wait To Restore timing value to be used in revertive switching. Range is 1 to 720 seconds.
		"
    ::= { sm24tat4xbEPSConfigInstanceEntry 5 }

sm24tat4xbEpsConfigInstanceHoldOffTime OBJECT-TYPE
    SYNTAX      Integer32
    MAX-ACCESS  read-write
    STATUS      current
    DESCRIPTION
        "The timing value to be used to make persistent check on Signal Fail before switching. This is in 100 ms. and the max value is 100 (10 sec)."
    ::= { sm24tat4xbEPSConfigInstanceEntry 6 }

sm24tat4xbEpsConfigInstanceCommand OBJECT-TYPE
    SYNTAX      Integer32
    MAX-ACCESS  read-write
    STATUS      current
    DESCRIPTION
        "0:None
	    1:Clear
		2:Lock Out
		3:Forced switch
		4:Manual switch P
		5:Manual switch W
		6:Exercise
		7:Freeze
		8:Lock Out Local
	    "
    ::= { sm24tat4xbEPSConfigInstanceEntry 7 }

sm24tat4xbEpsStatusProtectionState OBJECT-TYPE
    SYNTAX      DisplayString
    MAX-ACCESS  read-only
    STATUS      current
    DESCRIPTION
        "EPS state according to State Transition Tables in G.8031.
	    "
    ::= { sm24tat4xbEPSConfigInstanceEntry 8 }

sm24tat4xbEpsStatusWorkingFlowState OBJECT-TYPE
    SYNTAX      DisplayString
    MAX-ACCESS  read-only
    STATUS      current
    DESCRIPTION
        "OK: State of working flow is ok
        SF: State of working flow is Signal Fail
		SD: State of working flow is Signal Degrade (for future use)
	    "
    ::= { sm24tat4xbEPSConfigInstanceEntry 9 }

sm24tat4xbEpsStatusProtectingFlowState OBJECT-TYPE
    SYNTAX      DisplayString
    MAX-ACCESS  read-only
    STATUS      current
    DESCRIPTION
        "OK: State of protecting flow is ok
        SF: State of protecting flow is Signal Fail
        SD: State of protecting flow is Signal Degrade (for future use)"
    ::= { sm24tat4xbEPSConfigInstanceEntry 10 }

sm24tat4xbEpsStatusTransmittedApsRequest OBJECT-TYPE
    SYNTAX      DisplayString
    MAX-ACCESS  read-only
    STATUS      current
    DESCRIPTION
        "The transmitted APS according to State Transition Tables in G.8031."
    ::= { sm24tat4xbEPSConfigInstanceEntry 11 }

sm24tat4xbEpsStatusTransmittedApsReSignal OBJECT-TYPE
    SYNTAX      Integer32
    MAX-ACCESS  read-only
    STATUS      current
    DESCRIPTION
        "The transmitted APS according to State Transition Tables in G.8031."
    ::= { sm24tat4xbEPSConfigInstanceEntry 12 }

sm24tat4xbEpsStatusTransmittedApsBrSignal OBJECT-TYPE
    SYNTAX      Integer32
    MAX-ACCESS  read-only
    STATUS      current
    DESCRIPTION
        "The transmitted APS according to State Transition Tables in G.8031."
    ::= { sm24tat4xbEPSConfigInstanceEntry 13 }

sm24tat4xbEpsStatusReceivedApsRequest OBJECT-TYPE
    SYNTAX      DisplayString
    MAX-ACCESS  read-only
    STATUS      current
    DESCRIPTION
        "The received APS according to State Transition Tables in G.8031."
    ::= { sm24tat4xbEPSConfigInstanceEntry 14 }

sm24tat4xbEpsStatusReceivedApsReSignal OBJECT-TYPE
    SYNTAX      Integer32
    MAX-ACCESS  read-only
    STATUS      current
    DESCRIPTION
        "The received APS according to State Transition Tables in G.8031."
    ::= { sm24tat4xbEPSConfigInstanceEntry 15 }

sm24tat4xbEpsStatusReceivedApsBrSignal OBJECT-TYPE
    SYNTAX      Integer32
    MAX-ACCESS  read-only
    STATUS      current
    DESCRIPTION
        "The received APS according to State Transition Tables in G.8031."
    ::= { sm24tat4xbEPSConfigInstanceEntry 16 }

sm24tat4xbEpsStatusArchitectureMismatch OBJECT-TYPE
    SYNTAX      DisplayString
    MAX-ACCESS  read-only
    STATUS      current
    DESCRIPTION
        "The architecture indicated in the received APS does not match the locally configured."
    ::= { sm24tat4xbEPSConfigInstanceEntry 17 }

sm24tat4xbEpsStatusAPSOnWorking OBJECT-TYPE
    SYNTAX      DisplayString
    MAX-ACCESS  read-only
    STATUS      current
    DESCRIPTION
        "APS is received on the working flow."
    ::= { sm24tat4xbEPSConfigInstanceEntry 18 }

sm24tat4xbEpsStatusSwitchingIncomplete OBJECT-TYPE
    SYNTAX      DisplayString
    MAX-ACCESS  read-only
    STATUS      current
    DESCRIPTION
        "Traffic is not selected from the same flow instance in the two ends."
    ::= { sm24tat4xbEPSConfigInstanceEntry 19 }

sm24tat4xbEpsStatusNoApsReceived OBJECT-TYPE
    SYNTAX      DisplayString
    MAX-ACCESS  read-only
    STATUS      current
    DESCRIPTION
        "APS PDU is not received from the other end."
    ::= { sm24tat4xbEPSConfigInstanceEntry 20 }

-- =======================================================================================================================

sm24tat4xbERPS    OBJECT IDENTIFIER ::= { sm24tat4xbConfiguration 24 }

sm24tat4xbERPSTable  OBJECT-TYPE
    SYNTAX      SEQUENCE OF SM24TAT4XBERPSEntry
    MAX-ACCESS  not-accessible
    STATUS      current
    DESCRIPTION
        "A table of ERPS."
    ::= { sm24tat4xbERPS 1 }

sm24tat4xbERPSEntry OBJECT-TYPE
    SYNTAX    SM24TAT4XBERPSEntry
    MAX-ACCESS    not-accessible
    STATUS    current
    DESCRIPTION
        ""
    INDEX    { sm24tat4xbErpsIndex }
    ::= { sm24tat4xbERPSTable 1 }

SM24TAT4XBERPSEntry ::=
    SEQUENCE {
        sm24tat4xbErpsIndex                Integer32,
        sm24tat4xbErpsID                    Integer32,
		    sm24tat4xbErpsPort0                Integer32,
		    sm24tat4xbErpsPort1                Integer32,
		    sm24tat4xbErpsPort0APSMEP              Integer32,
        sm24tat4xbErpsPort1APSMEP              Integer32,
        sm24tat4xbErpsPort0SFMEP                Integer32,
        sm24tat4xbErpsPort1SFMEP                Integer32,
        sm24tat4xbErpsRingType                 Integer32,
        sm24tat4xbErpsInterconnectedNode            Integer32,
        sm24tat4xbErpsVirtualChannel            Integer32,
        sm24tat4xbErpsMajorRingID              Integer32,
        sm24tat4xbErpsAlarm		              Integer32,
        sm24tat4xbErpsRowStatus                RowStatus
        }

sm24tat4xbErpsIndex OBJECT-TYPE
    SYNTAX      Integer32(1..65535)
    MAX-ACCESS  not-accessible
    STATUS      current
    DESCRIPTION
        "Index"
    ::= { sm24tat4xbERPSEntry 1 }

sm24tat4xbErpsID OBJECT-TYPE
    SYNTAX      Integer32 (1..64)
    MAX-ACCESS  read-create
    STATUS      current
    DESCRIPTION
        "ERPS ID. Range:1-64."
    ::= {sm24tat4xbERPSEntry 2 }

sm24tat4xbErpsPort0 OBJECT-TYPE
    SYNTAX      Integer32
    MAX-ACCESS  read-create
    STATUS      current
    DESCRIPTION
        "This will create a Port 0 of the switch in the ring."
    ::= {sm24tat4xbERPSEntry 3 }

sm24tat4xbErpsPort1 OBJECT-TYPE
    SYNTAX      Integer32
    MAX-ACCESS  read-create
    STATUS      current
    DESCRIPTION
        "This will create Port 1 of the switch in the Ring.
	    As interconnected sub-ring will have only one ring port, Port 1 is configured as 0 for interconnected sub-ring.
	    0 in this field indicates that no Port 1 is associated with this instance"
    ::= {sm24tat4xbERPSEntry 4 }

sm24tat4xbErpsPort0APSMEP OBJECT-TYPE
    SYNTAX      Integer32
    MAX-ACCESS  read-create
    STATUS      current
    DESCRIPTION
        "The Port 0 APS PDU handling MEP.
	    Range: 1-100."
    ::= {sm24tat4xbERPSEntry 5 }

sm24tat4xbErpsPort1APSMEP OBJECT-TYPE
    SYNTAX      Integer32
    MAX-ACCESS  read-create
    STATUS      current
    DESCRIPTION
        "The Port 1 APS PDU handling MEP.
	    Range: 1-100."
    ::= {sm24tat4xbERPSEntry 6 }

sm24tat4xbErpsPort0SFMEP OBJECT-TYPE
    SYNTAX      Integer32
    MAX-ACCESS  read-create
    STATUS      current
    DESCRIPTION
        "The Port 0 Signal Fail reporting MEP.
	    Range: 1-100."
    ::= {sm24tat4xbERPSEntry 7 }

 sm24tat4xbErpsPort1SFMEP OBJECT-TYPE
    SYNTAX      Integer32
    MAX-ACCESS  read-create
    STATUS      current
    DESCRIPTION
        "The Port 1 Signal Fail reporting MEP.
	    Range: 1-100."
    ::= {sm24tat4xbERPSEntry 8 }

sm24tat4xbErpsRingType OBJECT-TYPE
    SYNTAX      Integer32
    MAX-ACCESS  read-create
    STATUS      current
    DESCRIPTION
        "Type of Protecting ring. It can be either major ring or sub-ring.
	    0:Major
	    1:Sub"
    ::= {sm24tat4xbERPSEntry 9 }

sm24tat4xbErpsInterconnectedNode OBJECT-TYPE
    SYNTAX      Integer32
    MAX-ACCESS  read-create
    STATUS      current
    DESCRIPTION
        "Interconnected Node indicates that the ring instance is interconnected.
	    0: not interconnected
	    1: interconnected"
    ::= {sm24tat4xbERPSEntry 10 }

sm24tat4xbErpsVirtualChannel OBJECT-TYPE
    SYNTAX      Integer32
    MAX-ACCESS  read-create
    STATUS      current
    DESCRIPTION
        "1: indicates it is a sub-ring with virtual channel.
	    0: indicates, sub-ring doesn't have virtual channel."
    ::= {sm24tat4xbERPSEntry 11 }

sm24tat4xbErpsMajorRingID OBJECT-TYPE
    SYNTAX      Integer32
    MAX-ACCESS  read-create
    STATUS      current
    DESCRIPTION
        "Major ring group ID for the interconnected sub-ring.
	    Range:1-64"
    ::= {sm24tat4xbERPSEntry 12 }

sm24tat4xbErpsAlarm OBJECT-TYPE
    SYNTAX      Integer32
    MAX-ACCESS  read-create
    STATUS      current
    DESCRIPTION
        "There is an active alarm on the ERPS."
    ::= {sm24tat4xbERPSEntry 13 }

sm24tat4xbErpsRowStatus OBJECT-TYPE
    SYNTAX      RowStatus
    MAX-ACCESS  read-create
    STATUS      current
    DESCRIPTION
        "ERPS Row Status."
    ::= {sm24tat4xbERPSEntry 14 }


sm24tat4xbErpsConfigInstanceErpsID    OBJECT-TYPE
    SYNTAX      Integer32
    MAX-ACCESS  read-write
    STATUS      current
    DESCRIPTION
	    "Specify ERPS ID for ERPSConfigInstanceEntry and ErpsConfigInstanceVLANConfigTable uesd."
    ::= {sm24tat4xbERPS 2 }


sm24tat4xbERPSConfigInstanceEntry    OBJECT IDENTIFIER ::= { sm24tat4xbERPS 3 }

sm24tat4xbErpsConfigInstanceConfigured OBJECT-TYPE
    SYNTAX      DisplayString
    MAX-ACCESS  read-only
    STATUS      current
    DESCRIPTION
        "Down: This ERPS is only created and has not yet been configured - is not active.
        Up: This ERPS is configured - is active."
    ::= { sm24tat4xbERPSConfigInstanceEntry 2 }

sm24tat4xbErpsConfigInstanceGuardTime OBJECT-TYPE
    SYNTAX      Integer32
    MAX-ACCESS  read-write
    STATUS      current
    DESCRIPTION
        "The period of the guard timer can be configured in 10 ms steps between 10 ms and 2 seconds, with a default value of 500 ms.
	    Guard timeout value to be used to prevent ring nodes from receiving outdated R-APS messages."
    ::= { sm24tat4xbERPSConfigInstanceEntry 3 }

sm24tat4xbErpsConfigInstanceWTRTime OBJECT-TYPE
    SYNTAX      Integer32
    MAX-ACCESS  read-write
    STATUS      current
    DESCRIPTION
        "The Wait To Restore timing value to be used in revertive switching.
        The period of the WTR time can be configured by the operator in 1 minute steps between 5 and 12 minutes with a default value of 5 minutes."
    ::= { sm24tat4xbERPSConfigInstanceEntry 4 }

sm24tat4xbErpsConfigInstanceHoldOffTime OBJECT-TYPE
    SYNTAX      Integer32
    MAX-ACCESS  read-write
    STATUS      current
    DESCRIPTION
        "The timing value to be used to make persistent check on Signal Fail before switching.
        The range of the hold off timer is 0 to 10 seconds in steps of 100 ms"
    ::= { sm24tat4xbERPSConfigInstanceEntry 5 }

sm24tat4xbErpsConfigInstanceVersion OBJECT-TYPE
    SYNTAX      Integer32
    MAX-ACCESS  read-write
    STATUS      current
    DESCRIPTION
        "ERPS Protocol Version - v1 or v2
	    1:v1
	    2:v2"
    ::= { sm24tat4xbERPSConfigInstanceEntry 6 }

sm24tat4xbErpsConfigInstanceRevertive OBJECT-TYPE
    SYNTAX      Integer32
    MAX-ACCESS  read-write
    STATUS      current
    DESCRIPTION
        "1:Revertive mode
	    0:Non-Revertive mode"
    ::= { sm24tat4xbERPSConfigInstanceEntry 7 }

sm24tat4xbErpsConfigInstanceRPLRole OBJECT-TYPE
    SYNTAX      Integer32
    MAX-ACCESS  read-write
    STATUS      current
    DESCRIPTION
        "It can be either RPL owner or RPL Neighbor.
	    0:None
	    1:RPL owner
	    2:RPL Neighbor
	    Please set RPLPort first."
    ::= { sm24tat4xbERPSConfigInstanceEntry 8 }

sm24tat4xbErpsConfigInstanceRPLPort OBJECT-TYPE
    SYNTAX      Integer32
    MAX-ACCESS  read-write
    STATUS      current
    DESCRIPTION
        "This allows to select the east port or west port as the RPL block.
	    0:None
	    1:Port0
	    2:Port1
	    Please set RPLRole after specify RPLPort."
    ::= { sm24tat4xbERPSConfigInstanceEntry 9 }

sm24tat4xbErpsConfigInstanceClear OBJECT-TYPE
    SYNTAX      Integer32
    MAX-ACCESS  read-write
    STATUS      current
    DESCRIPTION
        "If the owner has to be changed, then the clear check box allows to clear the RPL owner for that ERPS ring.
	    0: no clear
	    1: clear"
    ::= { sm24tat4xbERPSConfigInstanceEntry 10 }

sm24tat4xbErpsConfigInstanceTopologyChange OBJECT-TYPE
    SYNTAX      Integer32
    MAX-ACCESS  read-write
    STATUS      current
    DESCRIPTION
        "1: indicates that the topology changes in the sub-ring are propagated in the major ring.
	    0: indicates that the topology changes in the sub-ring are not propagated in the major ring."
    ::= { sm24tat4xbERPSConfigInstanceEntry 11 }

sm24tat4xbErpsConfigInstanceCommand OBJECT-TYPE
    SYNTAX      Integer32
    MAX-ACCESS  read-write
    STATUS      current
    DESCRIPTION
        "0:None
	    1:Manual Switch
		2:Forced Switch
		3:Clear
		Please set InstancePort first.
	    "
    ::= { sm24tat4xbERPSConfigInstanceEntry 12 }

sm24tat4xbErpsConfigInstancePort OBJECT-TYPE
    SYNTAX      Integer32
    MAX-ACCESS  read-write
    STATUS      current
    DESCRIPTION
        "0:None
	    1:Port0
	    2:Port1
	    Please set InstanceCommand after specify InstancePort.
	    "
    ::= { sm24tat4xbERPSConfigInstanceEntry 13 }

sm24tat4xbErpsStatusProtectionState OBJECT-TYPE
    SYNTAX      DisplayString
    MAX-ACCESS  read-only
    STATUS      current
    DESCRIPTION
        "ERPS state according to State Transition Tables in G.8032.
	    "
    ::= { sm24tat4xbERPSConfigInstanceEntry 14 }

sm24tat4xbErpsStatusPort0 OBJECT-TYPE
    SYNTAX      DisplayString
    MAX-ACCESS  read-only
    STATUS      current
    DESCRIPTION
        "OK: State of East port is ok
        SF: State of East port is Signal Fail
	    "
    ::= { sm24tat4xbERPSConfigInstanceEntry 15 }

sm24tat4xbErpsStatusPort1 OBJECT-TYPE
    SYNTAX      DisplayString
    MAX-ACCESS  read-only
    STATUS      current
    DESCRIPTION
        "OK: State of West port is ok
        SF: State of West port is Signal Fail
	    "
    ::= { sm24tat4xbERPSConfigInstanceEntry 16 }

sm24tat4xbErpsStatusTransmitAPS OBJECT-TYPE
    SYNTAX      DisplayString
    MAX-ACCESS  read-only
    STATUS      current
    DESCRIPTION
        "The transmitted APS according to State Transition Tables in G.8032.
	    "
    ::= { sm24tat4xbERPSConfigInstanceEntry 17 }

sm24tat4xbErpsStatusPort0ReceiveAPS OBJECT-TYPE
    SYNTAX      DisplayString
    MAX-ACCESS  read-only
    STATUS      current
    DESCRIPTION
        "The received APS on Port 0 according to State Transition Tables in G.8032.
	    "
    ::= { sm24tat4xbERPSConfigInstanceEntry 18 }

sm24tat4xbErpsStatusPort1ReceiveAPS OBJECT-TYPE
    SYNTAX      DisplayString
    MAX-ACCESS  read-only
    STATUS      current
    DESCRIPTION
        "The received APS on Port 1 according to State Transition Tables in G.8032.
	    "
    ::= { sm24tat4xbERPSConfigInstanceEntry 19 }

sm24tat4xbErpsStatusWTRRemaining OBJECT-TYPE
    SYNTAX      Integer32
    MAX-ACCESS  read-only
    STATUS      current
    DESCRIPTION
        "Remaining WTR timeout in milliseconds.
	    "
    ::= { sm24tat4xbERPSConfigInstanceEntry 20 }

sm24tat4xbErpsStatusRPLUnblocked OBJECT-TYPE
    SYNTAX      DisplayString
    MAX-ACCESS  read-only
    STATUS      current
    DESCRIPTION
        "APS is received on the working flow.
	    "
    ::= { sm24tat4xbERPSConfigInstanceEntry 21 }

sm24tat4xbErpsStatusNoAPSReceived OBJECT-TYPE
    SYNTAX      DisplayString
    MAX-ACCESS  read-only
    STATUS      current
    DESCRIPTION
        "RAPS PDU is not received from the other end.
	    "
    ::= { sm24tat4xbERPSConfigInstanceEntry 22 }

sm24tat4xbErpsStatusPort0BlockStatus OBJECT-TYPE
    SYNTAX      DisplayString
    MAX-ACCESS  read-only
    STATUS      current
    DESCRIPTION
        "Block status for Port 0 (Both traffic and R-APS block status). R-APS channel is never blocked on sub-rings without virtual channel.
	    "
    ::= { sm24tat4xbERPSConfigInstanceEntry 23 }

sm24tat4xbErpsStatusPort1BlockStatus OBJECT-TYPE
    SYNTAX      DisplayString
    MAX-ACCESS  read-only
    STATUS      current
    DESCRIPTION
        "Block status for Port 1 (Both traffic and R-APS block status). R-APS channel is never blocked on sub-rings without virtual channel.
	    "
    ::= { sm24tat4xbERPSConfigInstanceEntry 24 }

sm24tat4xbErpsStatusFOPAlarm OBJECT-TYPE
    SYNTAX      DisplayString
    MAX-ACCESS  read-only
    STATUS      current
    DESCRIPTION
        "Failure of Protocol Defect(FOP) status:
	    FOP is not detected
	    FOP is detected
	    "
    ::= { sm24tat4xbERPSConfigInstanceEntry 25 }

sm24tat4xbErpsConfigInstanceVLANConfigTable  OBJECT-TYPE
    SYNTAX      SEQUENCE OF SM24TAT4XBErpsConfigInstanceVLANConfigEntry
    MAX-ACCESS  not-accessible
    STATUS      current
    DESCRIPTION
        "A table of ERPS VLANConfig."
 ::= { sm24tat4xbERPS 4 }

sm24tat4xbErpsConfigInstanceVLANConfigEntry OBJECT-TYPE
    SYNTAX    SM24TAT4XBErpsConfigInstanceVLANConfigEntry
    MAX-ACCESS    not-accessible
    STATUS    current
    DESCRIPTION
        ""
    INDEX    { sm24tat4xbErpsConfigInstanceVLANConfigIndex }
    ::= { sm24tat4xbErpsConfigInstanceVLANConfigTable 1 }

SM24TAT4XBErpsConfigInstanceVLANConfigEntry ::=
    SEQUENCE {
        sm24tat4xbErpsConfigInstanceVLANConfigIndex        Integer32,
        sm24tat4xbErpsConfigInstanceVLANConfigVLANID        Integer32,
        sm24tat4xbErpsConfigInstanceVLANConfigRowStatus    RowStatus
        }

sm24tat4xbErpsConfigInstanceVLANConfigIndex OBJECT-TYPE
    SYNTAX      Integer32(1..65535)
    MAX-ACCESS  not-accessible
    STATUS      current
    DESCRIPTION
        "Index"
    ::= { sm24tat4xbErpsConfigInstanceVLANConfigEntry 1 }

sm24tat4xbErpsConfigInstanceVLANConfigVLANID OBJECT-TYPE
    SYNTAX      Integer32 (1..4095)
    MAX-ACCESS  read-create
    STATUS      current
    DESCRIPTION
        "ERPS VLAN Config ID. Range:1-4095."
    ::= {sm24tat4xbErpsConfigInstanceVLANConfigEntry 2 }

sm24tat4xbErpsConfigInstanceVLANConfigRowStatus OBJECT-TYPE
    SYNTAX      RowStatus
    MAX-ACCESS  read-create
    STATUS      current
    DESCRIPTION
        "ERPS VLAN Config Row Status."
    ::= {sm24tat4xbErpsConfigInstanceVLANConfigEntry 3 }
-- =======================================================================================================================

sm24tat4xbVLANTranslation    OBJECT IDENTIFIER ::= { sm24tat4xbConfiguration 25 }

sm24tat4xbVLANTranslationPortTable  OBJECT-TYPE
    SYNTAX      SEQUENCE OF SM24TAT4XBVLANTranslationPortEntry
    MAX-ACCESS  not-accessible
    STATUS      current
    DESCRIPTION
        "A table of VLANTranslationPort."
    ::= { sm24tat4xbVLANTranslation 1 }

sm24tat4xbVLANTranslationPortEntry OBJECT-TYPE
    SYNTAX    SM24TAT4XBVLANTranslationPortEntry
    MAX-ACCESS    not-accessible
    STATUS    current
    DESCRIPTION
        "An entry in the VLANTranslationPort table."
    INDEX    { sm24tat4xbVLANTranslationPortIndex }
    ::= { sm24tat4xbVLANTranslationPortTable 1 }

SM24TAT4XBVLANTranslationPortEntry ::=
    SEQUENCE {
        sm24tat4xbVLANTranslationPortIndex        Integer32,
        sm24tat4xbVLANTranslationPortDefault          Integer32,
        sm24tat4xbVLANTranslationPortGroupID          Integer32
        }

sm24tat4xbVLANTranslationPortIndex OBJECT-TYPE
    SYNTAX      Integer32(1..65535)
    MAX-ACCESS  not-accessible
    STATUS      current
    DESCRIPTION
        "VLANTranslationPort index."
    ::= {sm24tat4xbVLANTranslationPortEntry 1 }

sm24tat4xbVLANTranslationPortDefault OBJECT-TYPE
    SYNTAX      Integer32
    MAX-ACCESS  read-write
    STATUS      current
    DESCRIPTION
        "Set the switch port to use the default VLAN Translation Group.
	    1:set
	    0:not set"
    ::= {sm24tat4xbVLANTranslationPortEntry 2 }

sm24tat4xbVLANTranslationPortGroupID OBJECT-TYPE
    SYNTAX      Integer32
    MAX-ACCESS  read-write
    STATUS      current
    DESCRIPTION
        "The VLAN Translation mappings are organized into Groups, identified by the Group ID."
    ::= {sm24tat4xbVLANTranslationPortEntry 3 }



sm24tat4xbVLANTranslationMappingTable  OBJECT-TYPE
    SYNTAX      SEQUENCE OF SM24TAT4XBVLANTranslationMappingEntry
    MAX-ACCESS  not-accessible
    STATUS      current
    DESCRIPTION
        "A table of VLANTranslationMapping."
    ::= { sm24tat4xbVLANTranslation 2 }

sm24tat4xbVLANTranslationMappingEntry OBJECT-TYPE
    SYNTAX    SM24TAT4XBVLANTranslationMappingEntry
    MAX-ACCESS    not-accessible
    STATUS    current
    DESCRIPTION
        "An entry in the VLANTranslationMapping table."
    INDEX    { sm24tat4xbVLANTranslationMappingIndex }
    ::= { sm24tat4xbVLANTranslationMappingTable 1 }

SM24TAT4XBVLANTranslationMappingEntry ::=
    SEQUENCE {
        sm24tat4xbVLANTranslationMappingIndex        Integer32,
        sm24tat4xbVLANTranslationMappingGroupID          Integer32,
        sm24tat4xbVLANTranslationMappingVID          Integer32,
		    sm24tat4xbVLANTranslationMappingTVID         Integer32,
		    sm24tat4xbVLANTranslationMappingRowStatus        RowStatus
        }

sm24tat4xbVLANTranslationMappingIndex OBJECT-TYPE
    SYNTAX      Integer32(1..65535)
    MAX-ACCESS  not-accessible
    STATUS      current
    DESCRIPTION
        "VLANTranslationMapping index."
    ::= {sm24tat4xbVLANTranslationMappingEntry 1 }

sm24tat4xbVLANTranslationMappingGroupID OBJECT-TYPE
    SYNTAX      Integer32
    MAX-ACCESS  read-create
    STATUS      current
    DESCRIPTION
        "The VLAN Translation mappings are organized into Groups, identified by the Group ID."
    ::= {sm24tat4xbVLANTranslationMappingEntry 2 }

sm24tat4xbVLANTranslationMappingVID OBJECT-TYPE
    SYNTAX      Integer32
    MAX-ACCESS  read-create
    STATUS      current
    DESCRIPTION
        "Range:1-4095"
    ::= {sm24tat4xbVLANTranslationMappingEntry 3 }

sm24tat4xbVLANTranslationMappingTVID OBJECT-TYPE
    SYNTAX      Integer32
    MAX-ACCESS  read-create
    STATUS      current
    DESCRIPTION
        "Range:1-4095"
    ::= {sm24tat4xbVLANTranslationMappingEntry 4 }

sm24tat4xbVLANTranslationMappingRowStatus OBJECT-TYPE
    SYNTAX      RowStatus
    MAX-ACCESS  read-create
    STATUS      current
    DESCRIPTION
        "VLANTranslationMapping Row Status."
    ::= {sm24tat4xbVLANTranslationMappingEntry 5 }
-- ========================================================================================================
sm24tat4xbMEP    OBJECT IDENTIFIER ::= { sm24tat4xbConfiguration 26 }

sm24tat4xbMEPTable  OBJECT-TYPE
    SYNTAX      SEQUENCE OF SM24TAT4XBMEPEntry
    MAX-ACCESS  not-accessible
    STATUS      current
    DESCRIPTION
        "A table of MEP."
 ::= { sm24tat4xbMEP 1 }

sm24tat4xbMEPEntry OBJECT-TYPE
    SYNTAX    SM24TAT4XBMEPEntry
    MAX-ACCESS    not-accessible
    STATUS    current
    DESCRIPTION
        "An entry in the MEP table."
    INDEX    { sm24tat4xbMEPIndex }
    ::= { sm24tat4xbMEPTable 1 }

SM24TAT4XBMEPEntry ::=
    SEQUENCE {
    sm24tat4xbMEPIndex             Integer32,
    sm24tat4xbMepInstance              Integer32,
    sm24tat4xbMepDomain            Integer32,
    sm24tat4xbMepMode              Integer32,
		sm24tat4xbMepDirection             Integer32,
		sm24tat4xbMepResidencePort         Integer32,
		sm24tat4xbMepLevel             Integer32,
		sm24tat4xbMepFlowInstance          Integer32,
		sm24tat4xbMepTaggedVID             Integer32,
		sm24tat4xbMepEPSInstance            DisplayString,
		sm24tat4xbMepThisMAC            DisplayString,
		sm24tat4xbMepAlarm             DisplayString,
    sm24tat4xbMepRowStatus             RowStatus
    }

sm24tat4xbMEPIndex OBJECT-TYPE
    SYNTAX      Integer32(1..65535)
    MAX-ACCESS  not-accessible
    STATUS      current
    DESCRIPTION
        "MEP Table index."
    ::= {sm24tat4xbMEPEntry 1 }

sm24tat4xbMepInstance OBJECT-TYPE
    SYNTAX      Integer32
    MAX-ACCESS  read-create
    STATUS      current
    DESCRIPTION
        ""
    ::= {sm24tat4xbMEPEntry 2 }

sm24tat4xbMepDomain OBJECT-TYPE
    SYNTAX      Integer32
    MAX-ACCESS  read-create
    STATUS      current
    DESCRIPTION
        ""
    ::= {sm24tat4xbMEPEntry 3 }

sm24tat4xbMepMode OBJECT-TYPE
    SYNTAX      Integer32
    MAX-ACCESS  read-create
    STATUS      current
    DESCRIPTION
        ""
    ::= {sm24tat4xbMEPEntry 4 }

sm24tat4xbMepDirection OBJECT-TYPE
    SYNTAX      Integer32
    MAX-ACCESS  read-create
    STATUS      current
    DESCRIPTION
        ""
    ::= {sm24tat4xbMEPEntry 5 }

sm24tat4xbMepResidencePort OBJECT-TYPE
    SYNTAX      Integer32
    MAX-ACCESS  read-create
    STATUS      current
    DESCRIPTION
        ""
    ::= {sm24tat4xbMEPEntry 6 }

sm24tat4xbMepLevel OBJECT-TYPE
    SYNTAX      Integer32
    MAX-ACCESS  read-create
    STATUS      current
    DESCRIPTION
        ""
    ::= {sm24tat4xbMEPEntry 7 }

sm24tat4xbMepFlowInstance OBJECT-TYPE
    SYNTAX      Integer32
    MAX-ACCESS  read-create
    STATUS      current
    DESCRIPTION
        ""
    ::= {sm24tat4xbMEPEntry 8 }

sm24tat4xbMepTaggedVID OBJECT-TYPE
    SYNTAX      Integer32
    MAX-ACCESS  read-create
    STATUS      current
    DESCRIPTION
        ""
    ::= {sm24tat4xbMEPEntry 9 }

sm24tat4xbMepEPSInstance OBJECT-TYPE
    SYNTAX      DisplayString
    MAX-ACCESS  read-only
    STATUS      current
    DESCRIPTION
        ""
    ::= {sm24tat4xbMEPEntry 10 }

sm24tat4xbMepThisMAC OBJECT-TYPE
    SYNTAX      DisplayString
    MAX-ACCESS  read-only
    STATUS      current
    DESCRIPTION
        ""
    ::= {sm24tat4xbMEPEntry 11 }

sm24tat4xbMepAlarm OBJECT-TYPE
    SYNTAX      DisplayString
    MAX-ACCESS  read-only
    STATUS      current
    DESCRIPTION
        ""
    ::= {sm24tat4xbMEPEntry 12 }

sm24tat4xbMepRowStatus OBJECT-TYPE
    SYNTAX      RowStatus
    MAX-ACCESS  read-create
    STATUS      current
    DESCRIPTION
        "MEP Row Status."
    ::= {sm24tat4xbMEPEntry 13 }

sm24tat4xbMepInstanceID    OBJECT-TYPE
    SYNTAX      Integer32
    MAX-ACCESS  read-write
    STATUS      current
    DESCRIPTION
	    "Specify MEP Instance ID for the following item and table uesd."
    ::= {sm24tat4xbMEP 2 }


sm24tat4xbMepInstanceConfEntry    OBJECT IDENTIFIER ::= { sm24tat4xbMEP 3 }

sm24tat4xbMepInstanceConfLevel OBJECT-TYPE
    SYNTAX      Integer32
    MAX-ACCESS  read-write
    STATUS      current
    DESCRIPTION
        ""
    ::= {sm24tat4xbMepInstanceConfEntry 2 }

sm24tat4xbMepInstanceConfFormat OBJECT-TYPE
    SYNTAX      Integer32
    MAX-ACCESS  read-write
    STATUS      current
    DESCRIPTION
        ""
    ::= {sm24tat4xbMepInstanceConfEntry 3 }

sm24tat4xbMepInstanceConfDomainName OBJECT-TYPE
    SYNTAX      DisplayString
    MAX-ACCESS  read-write
    STATUS      current
    DESCRIPTION
        ""
    ::= {sm24tat4xbMepInstanceConfEntry 4 }

sm24tat4xbMepInstanceConfMEGid OBJECT-TYPE
    SYNTAX      DisplayString
    MAX-ACCESS  read-write
    STATUS      current
    DESCRIPTION
        ""
    ::= {sm24tat4xbMepInstanceConfEntry 5 }

sm24tat4xbMepInstanceConfMEPid OBJECT-TYPE
    SYNTAX      Integer32
    MAX-ACCESS  read-write
    STATUS      current
    DESCRIPTION
        ""
    ::= {sm24tat4xbMepInstanceConfEntry 6 }

sm24tat4xbMepInstanceConfTaggedVID OBJECT-TYPE
    SYNTAX      Integer32
    MAX-ACCESS  read-write
    STATUS      current
    DESCRIPTION
        ""
    ::= {sm24tat4xbMepInstanceConfEntry 7 }

sm24tat4xbMepInstanceConfSyslog OBJECT-TYPE
    SYNTAX      Integer32
    MAX-ACCESS  read-write
    STATUS      current
    DESCRIPTION
        ""
    ::= {sm24tat4xbMepInstanceConfEntry 8 }

sm24tat4xbMepInstanceConfcLevel OBJECT-TYPE
    SYNTAX      DisplayString
    MAX-ACCESS  read-only
    STATUS      current
    DESCRIPTION
        ""
    ::= {sm24tat4xbMepInstanceConfEntry 9 }

sm24tat4xbMepInstanceConfcMEG OBJECT-TYPE
    SYNTAX      DisplayString
    MAX-ACCESS  read-only
    STATUS      current
    DESCRIPTION
        ""
    ::= {sm24tat4xbMepInstanceConfEntry 10 }

sm24tat4xbMepInstanceConfcMEP OBJECT-TYPE
    SYNTAX      DisplayString
    MAX-ACCESS  read-only
    STATUS      current
    DESCRIPTION
        ""
    ::= {sm24tat4xbMepInstanceConfEntry 11 }

sm24tat4xbMepInstanceConfcAIS OBJECT-TYPE
    SYNTAX      DisplayString
    MAX-ACCESS  read-only
    STATUS      current
    DESCRIPTION
        ""
    ::= {sm24tat4xbMepInstanceConfEntry 12 }

sm24tat4xbMepInstanceConfcLCK OBJECT-TYPE
    SYNTAX      DisplayString
    MAX-ACCESS  read-only
    STATUS      current
    DESCRIPTION
        ""
    ::= {sm24tat4xbMepInstanceConfEntry 13 }

sm24tat4xbMepInstanceConfcLoop OBJECT-TYPE
    SYNTAX      DisplayString
    MAX-ACCESS  read-only
    STATUS      current
    DESCRIPTION
        ""
    ::= {sm24tat4xbMepInstanceConfEntry 14 }

sm24tat4xbMepInstanceConfcConfig OBJECT-TYPE
    SYNTAX      DisplayString
    MAX-ACCESS  read-only
    STATUS      current
    DESCRIPTION
        ""
    ::= {sm24tat4xbMepInstanceConfEntry 15 }

sm24tat4xbMepInstanceConfcDEG OBJECT-TYPE
    SYNTAX      DisplayString
    MAX-ACCESS  read-only
    STATUS      current
    DESCRIPTION
        ""
    ::= {sm24tat4xbMepInstanceConfEntry 16 }

sm24tat4xbMepInstanceConfcSSF OBJECT-TYPE
    SYNTAX      DisplayString
    MAX-ACCESS  read-only
    STATUS      current
    DESCRIPTION
        ""
    ::= {sm24tat4xbMepInstanceConfEntry 17 }

sm24tat4xbMepInstanceConfaBLK OBJECT-TYPE
    SYNTAX      DisplayString
    MAX-ACCESS  read-only
    STATUS      current
    DESCRIPTION
        ""
    ::= {sm24tat4xbMepInstanceConfEntry 18 }

sm24tat4xbMepInstanceConfaTSD OBJECT-TYPE
    SYNTAX      DisplayString
    MAX-ACCESS  read-only
    STATUS      current
    DESCRIPTION
        ""
    ::= {sm24tat4xbMepInstanceConfEntry 19 }

sm24tat4xbMepInstanceConfaTSF OBJECT-TYPE
    SYNTAX      DisplayString
    MAX-ACCESS  read-only
    STATUS      current
    DESCRIPTION
        ""
    ::= {sm24tat4xbMepInstanceConfEntry 20 }


sm24tat4xbPeerMepConfTable  OBJECT-TYPE
    SYNTAX      SEQUENCE OF SM24TAT4XBPeerMepConfEntry
    MAX-ACCESS  not-accessible
    STATUS      current
    DESCRIPTION
        "A table of MEP."
    ::= { sm24tat4xbMEP 4 }

sm24tat4xbPeerMepConfEntry OBJECT-TYPE
    SYNTAX    SM24TAT4XBPeerMepConfEntry
    MAX-ACCESS    not-accessible
    STATUS    current
    DESCRIPTION
        ""
    INDEX    { sm24tat4xbPeerMepConfIndex }
    ::= { sm24tat4xbPeerMepConfTable 1 }

SM24TAT4XBPeerMepConfEntry ::=
    SEQUENCE {
        sm24tat4xbPeerMepConfIndex            Integer32,
        sm24tat4xbPeerMepConfPeerMEPID            Integer32,
		    sm24tat4xbPeerMepConfUnicastPeerMAC          DisplayString,
        sm24tat4xbPeerMepConfcLOC            DisplayString,
        sm24tat4xbPeerMepConfcRDI            DisplayString,
        sm24tat4xbPeerMepConfcPeriod             DisplayString,
        sm24tat4xbPeerMepConfcPriority            DisplayString,
        sm24tat4xbPeerMepConfRowStatus            RowStatus
        }

sm24tat4xbPeerMepConfIndex OBJECT-TYPE
    SYNTAX      Integer32(1..65535)
    MAX-ACCESS  not-accessible
    STATUS      current
    DESCRIPTION
        "Index"
    ::= { sm24tat4xbPeerMepConfEntry 1 }

sm24tat4xbPeerMepConfPeerMEPID OBJECT-TYPE
    SYNTAX      Integer32
    MAX-ACCESS  read-create
    STATUS      current
    DESCRIPTION
        "Peer MEP ID"
    ::= {sm24tat4xbPeerMepConfEntry 2 }

sm24tat4xbPeerMepConfUnicastPeerMAC OBJECT-TYPE
    SYNTAX      DisplayString
    MAX-ACCESS  read-create
    STATUS      current
    DESCRIPTION
        ""
    ::= {sm24tat4xbPeerMepConfEntry 3 }

sm24tat4xbPeerMepConfcLOC OBJECT-TYPE
    SYNTAX      DisplayString
    MAX-ACCESS  read-create
    STATUS      current
    DESCRIPTION
        ""
    ::= {sm24tat4xbPeerMepConfEntry 4 }

sm24tat4xbPeerMepConfcRDI OBJECT-TYPE
    SYNTAX      DisplayString
    MAX-ACCESS  read-create
    STATUS      current
    DESCRIPTION
        ""
    ::= {sm24tat4xbPeerMepConfEntry 5 }

sm24tat4xbPeerMepConfcPeriod OBJECT-TYPE
    SYNTAX      DisplayString
    MAX-ACCESS  read-create
    STATUS      current
    DESCRIPTION
        ""
    ::= {sm24tat4xbPeerMepConfEntry 6 }

sm24tat4xbPeerMepConfcPriority OBJECT-TYPE
    SYNTAX      DisplayString
    MAX-ACCESS  read-create
    STATUS      current
    DESCRIPTION
        ""
    ::= {sm24tat4xbPeerMepConfEntry 7 }

sm24tat4xbPeerMepConfRowStatus OBJECT-TYPE
    SYNTAX      RowStatus
    MAX-ACCESS  read-create
    STATUS      current
    DESCRIPTION
        "Peer Mep Conf Row Status."
    ::= {sm24tat4xbPeerMepConfEntry 8 }

sm24tat4xbFunctionalConf    OBJECT IDENTIFIER ::= { sm24tat4xbMEP 5 }

sm24tat4xbFunctionalConfContinuityCheckEnable OBJECT-TYPE
    SYNTAX      Integer32
    MAX-ACCESS  read-write
    STATUS      current
    DESCRIPTION
        "0:disable
	    1:enable"
    ::= {sm24tat4xbFunctionalConf 2 }

sm24tat4xbFunctionalConfContinuityCheckPriority OBJECT-TYPE
    SYNTAX      Integer32
    MAX-ACCESS  read-write
    STATUS      current
    DESCRIPTION
        "range:0-7"
    ::= {sm24tat4xbFunctionalConf 3 }

sm24tat4xbFunctionalConfContinuityCheckFrameRate OBJECT-TYPE
    SYNTAX      Integer32
    MAX-ACCESS  read-write
    STATUS      current
    DESCRIPTION
        "range:1-7
	    1: 300 f/sec
	    2: 100 f/sec
	    3: 10 f/sec
	    4: 1 f/sec
	    5: 6 f/min
	    6: 1 f/min
	    7: 6 f/hour"
    ::= {sm24tat4xbFunctionalConf 4 }

sm24tat4xbFunctionalConfContinuityCheckTLV OBJECT-TYPE
    SYNTAX      Integer32
    MAX-ACCESS  read-write
    STATUS      current
    DESCRIPTION
        "0:disable
	    1:enable"
    ::= {sm24tat4xbFunctionalConf 5 }

sm24tat4xbFunctionalConfAPSProtocolEnable OBJECT-TYPE
    SYNTAX      Integer32
    MAX-ACCESS  read-write
    STATUS      current
    DESCRIPTION
        "0:disable
	    1:enable"
    ::= {sm24tat4xbFunctionalConf 6 }

sm24tat4xbFunctionalConfAPSProtocolPriority OBJECT-TYPE
    SYNTAX      Integer32
    MAX-ACCESS  read-write
    STATUS      current
    DESCRIPTION
        "range:0-7"
    ::= {sm24tat4xbFunctionalConf 7 }

sm24tat4xbFunctionalConfAPSProtocolCast OBJECT-TYPE
    SYNTAX      Integer32
    MAX-ACCESS  read-write
    STATUS      current
    DESCRIPTION
        "0: Unicast destination address
	    1: Multicast destination address"
    ::= {sm24tat4xbFunctionalConf 8 }

sm24tat4xbFunctionalConfAPSProtocolType OBJECT-TYPE
    SYNTAX      Integer32
    MAX-ACCESS  read-write
    STATUS      current
    DESCRIPTION
        "1: Linear protection APS
	    2: Ring protection APS"
    ::= {sm24tat4xbFunctionalConf 9 }

sm24tat4xbFunctionalConfAPSProtocolLastOctet OBJECT-TYPE
    SYNTAX      Integer32
    MAX-ACCESS  read-write
    STATUS      current
    DESCRIPTION
        "range:0-255"
    ::= {sm24tat4xbFunctionalConf 10 }

sm24tat4xbTLVConf    OBJECT IDENTIFIER ::= { sm24tat4xbMEP 6 }

sm24tat4xbTLVConfOUIFirst OBJECT-TYPE
    SYNTAX      Integer32
    MAX-ACCESS  read-write
    STATUS      current
    DESCRIPTION
        "range:0-255"
    ::= {sm24tat4xbTLVConf 2 }

sm24tat4xbTLVConfOUISecond OBJECT-TYPE
    SYNTAX      Integer32
    MAX-ACCESS  read-write
    STATUS      current
    DESCRIPTION
        "range:0-255"
    ::= {sm24tat4xbTLVConf 3 }

sm24tat4xbTLVConfOUIThird OBJECT-TYPE
    SYNTAX      Integer32
    MAX-ACCESS  read-write
    STATUS      current
    DESCRIPTION
        "range:0-255"
    ::= {sm24tat4xbTLVConf 4 }

sm24tat4xbTLVConfSubType OBJECT-TYPE
    SYNTAX      Integer32
    MAX-ACCESS  read-write
    STATUS      current
    DESCRIPTION
        "range:0-255"
    ::= {sm24tat4xbTLVConf 5 }

sm24tat4xbTLVConfValue OBJECT-TYPE
    SYNTAX      Integer32
    MAX-ACCESS  read-write
    STATUS      current
    DESCRIPTION
        "range:0-255"
    ::= {sm24tat4xbTLVConf 6 }


sm24tat4xbTLVConfStateTable OBJECT-TYPE
    SYNTAX      SEQUENCE OF SM24TAT4XBTLVConfStateEntry
    MAX-ACCESS  not-accessible
    STATUS      current
    DESCRIPTION
        "TLV Conf State Table"
    ::= { sm24tat4xbMEP 7 }

sm24tat4xbTLVConfStateEntry OBJECT-TYPE
    SYNTAX      SM24TAT4XBTLVConfStateEntry
    MAX-ACCESS  not-accessible
    STATUS      current
    DESCRIPTION
        "TLV Conf State Entry"
    INDEX    { sm24tat4xbTLVConfStateIndex  }
    ::= { sm24tat4xbTLVConfStateTable 1 }

SM24TAT4XBTLVConfStateEntry ::= SEQUENCE {
    sm24tat4xbTLVConfStateIndex                Integer32,
    sm24tat4xbTLVConfStatePeerMEPID                Integer32,
    sm24tat4xbTLVConfStateCCOrganizationSpecificOUIFirst    Integer32,
    sm24tat4xbTLVConfStateCCOrganizationSpecificOUISecond      Integer32,
    sm24tat4xbTLVConfStateCCOrganizationSpecificOUIThird    Integer32,
    sm24tat4xbTLVConfStateCCOrganizationSpecificSubType    Integer32,
    sm24tat4xbTLVConfStateCCOrganizationSpecificValue      Integer32,
    sm24tat4xbTLVConfStateCCOrganizationSpecificLastRX     DisplayString,
    sm24tat4xbTLVConfStateCCPortStatusValue            Integer32,
    sm24tat4xbTLVConfStateCCPortStatusLastRX            DisplayString,
    sm24tat4xbTLVConfStateCCInterfaceStatusValue        Integer32,
    sm24tat4xbTLVConfStateCCInterfaceStatusLastRX          DisplayString
}

sm24tat4xbTLVConfStateIndex OBJECT-TYPE
    SYNTAX      Integer32(1..65535)
    MAX-ACCESS  not-accessible
    STATUS      current
    DESCRIPTION
        "Index"
    ::= { sm24tat4xbTLVConfStateEntry 1 }

sm24tat4xbTLVConfStatePeerMEPID OBJECT-TYPE
    SYNTAX      Integer32
    MAX-ACCESS  read-only
    STATUS      current
    DESCRIPTION
        "Peer MEP ID"
    ::= { sm24tat4xbTLVConfStateEntry 2 }

sm24tat4xbTLVConfStateCCOrganizationSpecificOUIFirst OBJECT-TYPE
    SYNTAX      Integer32
    MAX-ACCESS  read-only
    STATUS      current
    DESCRIPTION
        "The last received first value in the OUI field."
    ::= { sm24tat4xbTLVConfStateEntry 3 }

sm24tat4xbTLVConfStateCCOrganizationSpecificOUISecond OBJECT-TYPE
    SYNTAX      Integer32
    MAX-ACCESS  read-only
    STATUS      current
    DESCRIPTION
        "The last received second value in the OS TLV OUI field."
    ::= { sm24tat4xbTLVConfStateEntry 4 }

sm24tat4xbTLVConfStateCCOrganizationSpecificOUIThird OBJECT-TYPE
    SYNTAX      Integer32
    MAX-ACCESS  read-only
    STATUS      current
    DESCRIPTION
        "The last received third value in the OS TLV OUI field."
    ::= { sm24tat4xbTLVConfStateEntry 5 }

sm24tat4xbTLVConfStateCCOrganizationSpecificSubType OBJECT-TYPE
    SYNTAX      Integer32
    MAX-ACCESS  read-only
    STATUS      current
    DESCRIPTION
        "The last received value in the OS TLV Sub-Type field."
    ::= { sm24tat4xbTLVConfStateEntry 6 }

sm24tat4xbTLVConfStateCCOrganizationSpecificValue OBJECT-TYPE
    SYNTAX      Integer32
    MAX-ACCESS  read-only
    STATUS      current
    DESCRIPTION
        "The last received value in the OS TLV Value field."
    ::= { sm24tat4xbTLVConfStateEntry 7 }

sm24tat4xbTLVConfStateCCOrganizationSpecificLastRX OBJECT-TYPE
    SYNTAX      DisplayString
    MAX-ACCESS  read-only
    STATUS      current
    DESCRIPTION
        "OS TLV was received in the last received CCM PDU."
    ::= { sm24tat4xbTLVConfStateEntry 8 }

sm24tat4xbTLVConfStateCCPortStatusValue OBJECT-TYPE
    SYNTAX      Integer32
    MAX-ACCESS  read-only
    STATUS      current
    DESCRIPTION
        "The last received value in the PS TLV Value field."
    ::= { sm24tat4xbTLVConfStateEntry 9 }

sm24tat4xbTLVConfStateCCPortStatusLastRX OBJECT-TYPE
    SYNTAX      DisplayString
    MAX-ACCESS  read-only
    STATUS      current
    DESCRIPTION
        "PS TLV was received in the last received CCM PDU."
    ::= { sm24tat4xbTLVConfStateEntry 10 }

sm24tat4xbTLVConfStateCCInterfaceStatusValue OBJECT-TYPE
    SYNTAX      Integer32
    MAX-ACCESS  read-only
    STATUS      current
    DESCRIPTION
        "The last received value in the IS TLV Value field."
    ::= { sm24tat4xbTLVConfStateEntry 11 }

sm24tat4xbTLVConfStateCCInterfaceStatusLastRX OBJECT-TYPE
    SYNTAX      DisplayString
    MAX-ACCESS  read-only
    STATUS      current
    DESCRIPTION
        "IS TLV was received in the last received CCM PDU."
    ::= { sm24tat4xbTLVConfStateEntry 12 }

sm24tat4xbLinkStateTracking OBJECT-TYPE
    SYNTAX      Integer32
    MAX-ACCESS  read-write
    STATUS      current
    DESCRIPTION
        "0:disable
	    1:enable"
    ::= { sm24tat4xbMEP 8 }


sm24tat4xbFaultManagement    OBJECT IDENTIFIER ::= { sm24tat4xbMEP 9 }

sm24tat4xbFaultMgmtLoopBackConfEnable OBJECT-TYPE
    SYNTAX      Integer32
    MAX-ACCESS  read-write
    STATUS      current
    DESCRIPTION
        "0:disable
	    1:enable"
    ::= { sm24tat4xbFaultManagement 2 }

sm24tat4xbFaultMgmtLoopBackConfDEI OBJECT-TYPE
    SYNTAX      Integer32
    MAX-ACCESS  read-write
    STATUS      current
    DESCRIPTION
        "0:disable
	    1:enable"
    ::= { sm24tat4xbFaultManagement 3 }

sm24tat4xbFaultMgmtLoopBackConfPriority OBJECT-TYPE
    SYNTAX      Integer32
    MAX-ACCESS  read-write
    STATUS      current
    DESCRIPTION
        "range:0-7"
    ::= { sm24tat4xbFaultManagement 4 }

sm24tat4xbFaultMgmtLoopBackConfCast OBJECT-TYPE
    SYNTAX      Integer32
    MAX-ACCESS  read-write
    STATUS      current
    DESCRIPTION
        "0:Unicast destination address
	    1:Multicast destination address"
    ::= { sm24tat4xbFaultManagement 5 }

sm24tat4xbFaultMgmtLoopBackConfPeerMEP OBJECT-TYPE
    SYNTAX      Integer32
    MAX-ACCESS  read-write
    STATUS      current
    DESCRIPTION
        "This is only used if the 'Unicast MAC' is configured to all zero.
	    The LBM unicast MAC will be taken from the 'Unicast Peer MAC' configuration of this peer."
    ::= { sm24tat4xbFaultManagement 6 }

sm24tat4xbFaultMgmtLoopBackConfUnicastMAC OBJECT-TYPE
    SYNTAX      DisplayString
    MAX-ACCESS  read-write
    STATUS      current
    DESCRIPTION
        "This is only used if NOT configured to all zero.
	    This will be used as the LBM PDU unicast MAC.
	    This is the only way to configure Loop Back to-wards a MIP. "
    ::= { sm24tat4xbFaultManagement 7 }

sm24tat4xbFaultMgmtLoopBackConfToSend OBJECT-TYPE
    SYNTAX      Integer32
    MAX-ACCESS  read-write
    STATUS      current
    DESCRIPTION
        "The number of LBM PDU to send in one loop test.
	    The value 0 indicate infinite transmission (test behaviour).
	    This is HW based LBM/LBR and Requires VOE."
    ::= { sm24tat4xbFaultManagement 8 }

sm24tat4xbFaultMgmtLoopBackConfSize OBJECT-TYPE
    SYNTAX      Integer32
    MAX-ACCESS  read-write
    STATUS      current
    DESCRIPTION
        "The LBM frame size."
    ::= { sm24tat4xbFaultManagement 9 }

sm24tat4xbFaultMgmtLoopBackConfInterval OBJECT-TYPE
    SYNTAX      Integer32
    MAX-ACCESS  read-write
    STATUS      current
    DESCRIPTION
        "The interval between transmitting LBM PDU."
    ::= { sm24tat4xbFaultManagement 10 }


sm24tat4xbFaultManagementState    OBJECT IDENTIFIER ::= { sm24tat4xbMEP 10 }


sm24tat4xbFaultMgmtStateTransactionID OBJECT-TYPE
    SYNTAX      Integer32
    MAX-ACCESS  read-only
    STATUS      current
    DESCRIPTION
        "The transaction id of the first LBM transmitted.
	    For each LBM transmitted the transaction id in the PDU is incremented."
    ::= { sm24tat4xbFaultManagementState 1 }


sm24tat4xbFaultMgmtStateTransmitted OBJECT-TYPE
    SYNTAX      Integer32
    MAX-ACCESS  read-only
    STATUS      current
    DESCRIPTION
        "The total number of LBM PDU transmitted."
    ::= { sm24tat4xbFaultManagementState 2 }


sm24tat4xbFaultMgmtStateTable OBJECT-TYPE
    SYNTAX      SEQUENCE OF SM24TAT4XBFaultMgmtStateEntry
    MAX-ACCESS  not-accessible
    STATUS      current
    DESCRIPTION
        " "
    ::= { sm24tat4xbFaultManagementState 3 }

sm24tat4xbFaultMgmtStateEntry OBJECT-TYPE
    SYNTAX      SM24TAT4XBFaultMgmtStateEntry
    MAX-ACCESS  not-accessible
    STATUS      current
    DESCRIPTION
        " "
    INDEX    { sm24tat4xbFaultMgmtStateIndex  }
    ::= { sm24tat4xbFaultMgmtStateTable 1 }

SM24TAT4XBFaultMgmtStateEntry ::= SEQUENCE {
    sm24tat4xbFaultMgmtStateIndex        Integer32,
    sm24tat4xbFaultMgmtStateReplyMAC        DisplayString,
    sm24tat4xbFaultMgmtStateReceived        Integer32,
    sm24tat4xbFaultMgmtStateOutOfOrder      Integer32
}

sm24tat4xbFaultMgmtStateIndex OBJECT-TYPE
    SYNTAX      Integer32(1..65535)
    MAX-ACCESS  not-accessible
    STATUS      current
    DESCRIPTION
        "Index"
    ::= { sm24tat4xbFaultMgmtStateEntry 1 }

sm24tat4xbFaultMgmtStateReplyMAC OBJECT-TYPE
    SYNTAX      DisplayString
    MAX-ACCESS  read-only
    STATUS      current
    DESCRIPTION
        "The MAC of the replying MEP/MIP.
	    In case of multi-cast LBM, replies can be received from all peer MEP in the group.
	    This MAC is not shown in case of 'To Send' == 0."
    ::= { sm24tat4xbFaultMgmtStateEntry 2 }

sm24tat4xbFaultMgmtStateReceived OBJECT-TYPE
    SYNTAX      Integer32
    MAX-ACCESS  read-only
    STATUS      current
    DESCRIPTION
        "The total number of LBR PDU received from this 'Reply MAC'."
    ::= { sm24tat4xbFaultMgmtStateEntry 3 }

sm24tat4xbFaultMgmtStateOutOfOrder OBJECT-TYPE
    SYNTAX      Integer32
    MAX-ACCESS  read-only
    STATUS      current
    DESCRIPTION
        "The number of LBR PDU received from this 'Reply MAC' with incorrect 'Transaction ID'."
    ::= { sm24tat4xbFaultMgmtStateEntry 4 }

sm24tat4xbFaultMgmtTestSignal    OBJECT IDENTIFIER ::= { sm24tat4xbMEP 11 }

sm24tat4xbFaultMgmtTestSignalTx OBJECT-TYPE
    SYNTAX      Integer32
    MAX-ACCESS  read-write
    STATUS      current
    DESCRIPTION
        "Test Signal based on transmitting TST PDU can be enabled/disabled.
	    0:disable
	    1:enable"
    ::= { sm24tat4xbFaultMgmtTestSignal 2 }

sm24tat4xbFaultMgmtTestSignalRx OBJECT-TYPE
    SYNTAX      Integer32
    MAX-ACCESS  read-write
    STATUS      current
    DESCRIPTION
        "Test Signal based on transmitting TST PDU can be enabled/disabled.
	    0:disable
	    1:enable"
    ::= { sm24tat4xbFaultMgmtTestSignal 3 }

sm24tat4xbFaultMgmtTestSignalDEI OBJECT-TYPE
    SYNTAX      Integer32
    MAX-ACCESS  read-write
    STATUS      current
    DESCRIPTION
        "The DEI to be inserted as PCP bits in TAG (if any).
	    0:disable
	    1:enable"
    ::= { sm24tat4xbFaultMgmtTestSignal 4 }

sm24tat4xbFaultMgmtTestSignalPriority OBJECT-TYPE
    SYNTAX      Integer32
    MAX-ACCESS  read-write
    STATUS      current
    DESCRIPTION
        "The priority to be inserted as PCP bits in TAG (if any).
    Range:0-7"
    ::= { sm24tat4xbFaultMgmtTestSignal 5 }

sm24tat4xbFaultMgmtTestSignalPeerMEP OBJECT-TYPE
    SYNTAX      Integer32
    MAX-ACCESS  read-write
    STATUS      current
    DESCRIPTION
        "The TST frame destination MAC will be taken from the 'Unicast Peer MAC' configuration of this peer."
    ::= { sm24tat4xbFaultMgmtTestSignal 6 }

sm24tat4xbFaultMgmtTestSignalRate OBJECT-TYPE
    SYNTAX      Integer32
    MAX-ACCESS  read-write
    STATUS      current
    DESCRIPTION
        "The TST frame transmission bit rate - in Mega bits pr. second.
	    Limit is 400 Mbps. This is the bit rate of a standard frame without any encapsulation.
	    If 1 Mbps rate is selected in a EVC MEP, the added tag will give a higher bitrate on the wire."
    ::= { sm24tat4xbFaultMgmtTestSignal 7 }

sm24tat4xbFaultMgmtTestSignalSize OBJECT-TYPE
    SYNTAX      Integer32
    MAX-ACCESS  read-write
    STATUS      current
    DESCRIPTION
        "The TST frame size. This is entered as the wanted size (in bytes) of a un-tagged frame containing TST OAM PDU - including CRC (four bytes)."
    ::= { sm24tat4xbFaultMgmtTestSignal 8 }

sm24tat4xbFaultMgmtTestSignalPattern OBJECT-TYPE
    SYNTAX      Integer32
    MAX-ACCESS  read-write
    STATUS      current
    DESCRIPTION
        "The 'empty' TST PDU has the size of 12 bytes.
	    In order to achieve the configured frame size a data TLV will be added with a pattern.
	    0:All Zero
	    1:All One
	    2:10101010"
    ::= { sm24tat4xbFaultMgmtTestSignal 9 }

sm24tat4xbFaultMgmtTestSignalSequenceNumber OBJECT-TYPE
    SYNTAX      Integer32
    MAX-ACCESS  read-write
    STATUS      current
    DESCRIPTION
        "0:disable
	    1:enable"
    ::= { sm24tat4xbFaultMgmtTestSignal 10 }

sm24tat4xbFaultMgmtTestSignalState    OBJECT IDENTIFIER ::= { sm24tat4xbMEP 12 }

sm24tat4xbFaultMgmtTestSignalStateTXFrameCount OBJECT-TYPE
    SYNTAX      Integer32
    MAX-ACCESS  read-only
    STATUS      current
    DESCRIPTION
        "The number of transmitted TST frames since last 'Clear'."
    ::= { sm24tat4xbFaultMgmtTestSignalState 2 }

sm24tat4xbFaultMgmtTestSignalStateRXFrameCount OBJECT-TYPE
    SYNTAX      Integer32
    MAX-ACCESS  read-only
    STATUS      current
    DESCRIPTION
        "The number of received TST frames since last 'Clear'."
    ::= { sm24tat4xbFaultMgmtTestSignalState 3 }

sm24tat4xbFaultMgmtTestSignalStateRXRate OBJECT-TYPE
    SYNTAX      Integer32
    MAX-ACCESS  read-only
    STATUS      current
    DESCRIPTION
        "The current received TST frame bit rate in Kbps.
	    This is calculated on a 1 s. basis, starting when first TST frame is received after 'Clear'.
	    The frame size used for this calculation is the first received after 'Clear'"
    ::= { sm24tat4xbFaultMgmtTestSignalState 4 }

sm24tat4xbFaultMgmtTestSignalStateTestTime OBJECT-TYPE
    SYNTAX      Integer32
    MAX-ACCESS  read-only
    STATUS      current
    DESCRIPTION
        "The number of seconds passed since first TST frame received after last 'Clear'."
    ::= { sm24tat4xbFaultMgmtTestSignalState 5 }


sm24tat4xbFaultMgmtTestSignalStateClear OBJECT-TYPE
    SYNTAX      Integer32
    MAX-ACCESS  read-write
    STATUS      current
    DESCRIPTION
        "This will clear all Test Signal State.
	    Transmission of TST frame will be restarted.
	    Calculation of 'Rx frame count', 'RX rate' and 'Test time' will be started when receiving first TST frame."
    ::= { sm24tat4xbFaultMgmtTestSignalState 6 }


sm24tat4xbFaultMgmtClientConfigFlow    OBJECT IDENTIFIER ::= { sm24tat4xbMEP 13 }

sm24tat4xbFaultMgmtClientConfigFlowTable OBJECT-TYPE
    SYNTAX      SEQUENCE OF SM24TAT4XBFaultMgmtClientConfigFlowEntry
    MAX-ACCESS  not-accessible
    STATUS      current
    DESCRIPTION
        " "
    ::= { sm24tat4xbFaultMgmtClientConfigFlow 1 }

sm24tat4xbFaultMgmtClientConfigFlowEntry OBJECT-TYPE
    SYNTAX      SM24TAT4XBFaultMgmtClientConfigFlowEntry
    MAX-ACCESS  not-accessible
    STATUS      current
    DESCRIPTION
        " "
    INDEX    { sm24tat4xbFaultMgmtClientConfigFlowIndex  }
    ::= { sm24tat4xbFaultMgmtClientConfigFlowTable 1 }

SM24TAT4XBFaultMgmtClientConfigFlowEntry ::= SEQUENCE {
    sm24tat4xbFaultMgmtClientConfigFlowIndex     Integer32,
    sm24tat4xbFaultMgmtClientConfigFlowDomain    Integer32,
    sm24tat4xbFaultMgmtClientConfigFlowInstance  Integer32,
    sm24tat4xbFaultMgmtClientConfigFlowLevel     Integer32,
    sm24tat4xbFaultMgmtClientConfigFlowAISprio    Integer32,
    sm24tat4xbFaultMgmtClientConfigFlowLCKprio    Integer32,
    sm24tat4xbFaultMgmtClientConfigFlowRowStatus RowStatus
}

sm24tat4xbFaultMgmtClientConfigFlowIndex OBJECT-TYPE
    SYNTAX      Integer32(1..65535)
    MAX-ACCESS  not-accessible
    STATUS      current
    DESCRIPTION
        "Index"
    ::= { sm24tat4xbFaultMgmtClientConfigFlowEntry 1 }

sm24tat4xbFaultMgmtClientConfigFlowDomain OBJECT-TYPE
    SYNTAX      Integer32
    MAX-ACCESS  read-create
    STATUS      current
    DESCRIPTION
        "The domain of the client layer flow.
	    Ranfew:0-6
	    0:Port
	    1:EVC
	    2:VLAN
	    3:MPLS_LINK
	    4:MPLS_TUNNEL
	    5:MPLS_PW
	    6:MPLS_LSP"
    ::= { sm24tat4xbFaultMgmtClientConfigFlowEntry 2 }

sm24tat4xbFaultMgmtClientConfigFlowInstance OBJECT-TYPE
    SYNTAX      Integer32
    MAX-ACCESS  read-create
    STATUS      current
    DESCRIPTION
        "Client layer flow instance numbers."
    ::= { sm24tat4xbFaultMgmtClientConfigFlowEntry 3 }

sm24tat4xbFaultMgmtClientConfigFlowLevel OBJECT-TYPE
    SYNTAX      Integer32
    MAX-ACCESS  read-create
    STATUS      current
    DESCRIPTION
        "Client layer level - AIS and LCK PDU transmitted in this client layer flow will be on this level."
    ::= { sm24tat4xbFaultMgmtClientConfigFlowEntry 4 }

sm24tat4xbFaultMgmtClientConfigFlowAISprio OBJECT-TYPE
    SYNTAX      Integer32
    MAX-ACCESS  read-create
    STATUS      current
    DESCRIPTION
        "The priority to be used when transmitting AIS in each client flow.
	    Priority resulting in highest possible PCP can be selected.
	    Range:0-7. 255 indicate highest possible is requested"
    ::= { sm24tat4xbFaultMgmtClientConfigFlowEntry 5 }

sm24tat4xbFaultMgmtClientConfigFlowLCKprio OBJECT-TYPE
    SYNTAX      Integer32
    MAX-ACCESS  read-create
    STATUS      current
    DESCRIPTION
        "The priority to be used when transmitting LCK in each client flow.
	    Priority resulting in highest possible PCP can be selected.
	    Range:0-7. 255 indicate highest possible is requested"
    ::= { sm24tat4xbFaultMgmtClientConfigFlowEntry 6 }

sm24tat4xbFaultMgmtClientConfigFlowRowStatus OBJECT-TYPE
    SYNTAX      RowStatus
    MAX-ACCESS  read-create
    STATUS      current
    DESCRIPTION
        "FaultMgmtClientConfigFlow Row Status."
    ::= {sm24tat4xbFaultMgmtClientConfigFlowEntry 7 }


sm24tat4xbFaultMgmtAISLOCK    OBJECT IDENTIFIER ::= { sm24tat4xbMEP 14 }

sm24tat4xbFaultMgmtAISEnable OBJECT-TYPE
    SYNTAX      Integer32
    MAX-ACCESS  read-write
    STATUS      current
    DESCRIPTION
        "Insertion of AIS signal (AIS PDU transmission) in client layer flows, can be enable/disabled.
	    0:disable
	    1:enable"
    ::= { sm24tat4xbFaultMgmtAISLOCK 2 }

sm24tat4xbFaultMgmtAISFrameRate OBJECT-TYPE
    SYNTAX      Integer32
    MAX-ACCESS  read-write
    STATUS      current
    DESCRIPTION
        "Selecting the frame rate of AIS PDU.
	    This is the inverse of transmission period as described in Y.1731.
        1: 300 frames per second
	    2: 100 frames per second
	    3: 10 frames per second
	    4: 1 frames per second
	    5: 6 frames per minute
	    6: 1 frames per minute
	    7: 6 frames per hour"
    ::= { sm24tat4xbFaultMgmtAISLOCK 3 }

sm24tat4xbFaultMgmtAISProtection OBJECT-TYPE
    SYNTAX      Integer32
    MAX-ACCESS  read-write
    STATUS      current
    DESCRIPTION
        "Selecting this means that the first 3 AIS PDU is transmitted as fast as possible - in case of using this for protection in the end point.
	    0:disable
	    1:enable"
    ::= { sm24tat4xbFaultMgmtAISLOCK 4 }


sm24tat4xbFaultMgmtLOCKEnable OBJECT-TYPE
    SYNTAX      Integer32
    MAX-ACCESS  read-write
    STATUS      current
    DESCRIPTION
        "Insertion of LOCK signal (LCK PDU transmission) in client layer flows, can be enable/disabled.
	    0:disable
	    1:enable"
    ::= { sm24tat4xbFaultMgmtAISLOCK 5 }

sm24tat4xbFaultMgmtLOCKFrameRate OBJECT-TYPE
    SYNTAX      Integer32
    MAX-ACCESS  read-write
    STATUS      current
    DESCRIPTION
        "Selecting the frame rate of LCK PDU. This is the inverse of transmission period as described in Y.1731.
        1: 300 frames per second
	    2: 100 frames per second
	    3: 10 frames per second
	    4: 1 frames per second
	    5: 6 frames per minute
	    6: 1 frames per minute
	    7: 6 frames per hour"
    ::= { sm24tat4xbFaultMgmtAISLOCK 6 }

sm24tat4xbPerformanceMonitor  OBJECT IDENTIFIER ::= { sm24tat4xbMEP 15 }

sm24tat4xbDataSetEnable OBJECT-TYPE
    SYNTAX      Integer32
    MAX-ACCESS  read-write
    STATUS      current
    DESCRIPTION
        "
	    When enabled this MEP instance will contribute to the 'PM Data Set' gathered by the PM Session.
	    0:disable
	    1:enable"
    ::= { sm24tat4xbPerformanceMonitor 2 }

sm24tat4xbLossMeasureEnable OBJECT-TYPE
    SYNTAX      Integer32
    MAX-ACCESS  read-write
    STATUS      current
    DESCRIPTION
        "
	    Loss Measurement based on transmitting/receiving CCM or LMM/LMR PDU can be enabled/disabled - see 'Ended'.
	    This is only valid with one Peer MEP configured.
	    0:disable
	    1:enable"
    ::= { sm24tat4xbPerformanceMonitor 3 }

sm24tat4xbLossMeasurePriority OBJECT-TYPE
    SYNTAX      Integer32
    MAX-ACCESS  read-write
    STATUS      current
    DESCRIPTION
        "
	    The priority to be inserted as PCP bits in TAG (if any).
	    In case of enable of Continuity Check and Loss Measurement both implemented on SW based CCM, 'Priority' has to be the same.
	    range:0-7"
    ::= { sm24tat4xbPerformanceMonitor 4 }

sm24tat4xbLossMeasureFrameRate OBJECT-TYPE
    SYNTAX      Integer32
    MAX-ACCESS  read-write
    STATUS      current
    DESCRIPTION
        "
	    1: 300 frames per second
	    2: 100 frames per second
	    3: 10 frames per second
	    4: 1 frames per second
	    5: 6 frames per minute
	    6: 1 frames per minute
	    7: 6 frames per hour"
    ::= { sm24tat4xbPerformanceMonitor 5 }

sm24tat4xbLossMeasureCast OBJECT-TYPE
    SYNTAX      Integer32
    MAX-ACCESS  read-write
    STATUS      current
    DESCRIPTION
        "
	    0: Unicast destination address
	    1: Multicast destination address
	    "
    ::= { sm24tat4xbPerformanceMonitor 6 }

sm24tat4xbLossMeasureEnded OBJECT-TYPE
    SYNTAX      Integer32
    MAX-ACCESS  read-write
    STATUS      current
    DESCRIPTION
        "
	    0: Single ended LM based on LMM/LMR or DM based on DMM/DMR
	    1: Dual ended LM based on CCM or DM based on 1DM
	    "
    ::= { sm24tat4xbPerformanceMonitor 7 }

sm24tat4xbLossMeasureFLRInterval OBJECT-TYPE
    SYNTAX      Integer32
    MAX-ACCESS  read-write
    STATUS      current
    DESCRIPTION
        "
    This is the interval in seconds where the Frame Loss Ratio is calculated.
	    "
    ::= { sm24tat4xbPerformanceMonitor 8 }

sm24tat4xbLossMeasureLossThreshold OBJECT-TYPE
    SYNTAX      Integer32
    MAX-ACCESS  read-write
    STATUS      current
    DESCRIPTION
        "
    Far end loss threshold count is incremented if a loss measurement is above this threshold.
	    "
    ::= { sm24tat4xbPerformanceMonitor 9 }

sm24tat4xbLossMeasureStateTx OBJECT-TYPE
    SYNTAX      Integer32
    MAX-ACCESS  read-only
    STATUS      current
    DESCRIPTION
        "
	    "
    ::= { sm24tat4xbPerformanceMonitor 10 }

sm24tat4xbLossMeasureStateRx OBJECT-TYPE
    SYNTAX      Integer32
    MAX-ACCESS  read-only
    STATUS      current
    DESCRIPTION
        "
	    "
    ::= { sm24tat4xbPerformanceMonitor 11 }

sm24tat4xbLossMeasureStateNearEndLossCount OBJECT-TYPE
    SYNTAX      Integer32
    MAX-ACCESS  read-only
    STATUS      current
    DESCRIPTION
        "The accumulated near end frame loss count - since last 'clear'.
	    "
    ::= { sm24tat4xbPerformanceMonitor 12 }

sm24tat4xbLossMeasureStateFarEndLossCount OBJECT-TYPE
    SYNTAX      Integer32
    MAX-ACCESS  read-only
    STATUS      current
    DESCRIPTION
        "The accumulated far end frame loss count - since last 'clear'.
	    "
    ::= { sm24tat4xbPerformanceMonitor 13 }

sm24tat4xbLossMeasureStateNearEndLossRatio OBJECT-TYPE
    SYNTAX      Integer32
    MAX-ACCESS  read-only
    STATUS      current
    DESCRIPTION
        "The near end frame loss ratio calculated based on the near end frame loss count and far end frame transmitted - in the latest 'FLR Interval'.
	    The result is given in percent.
	    "
    ::= { sm24tat4xbPerformanceMonitor 14 }

sm24tat4xbLossMeasureStateFarEndLossRatio OBJECT-TYPE
    SYNTAX      Integer32
    MAX-ACCESS  read-only
    STATUS      current
    DESCRIPTION
        "The far end frame loss ratio calculated based on the far end frame loss count and near end frame transmitted - in the latest 'FLR Interval'.
	    The result is given in percent.
	    "
    ::= { sm24tat4xbPerformanceMonitor 15 }

sm24tat4xbLossMeasureStateClear OBJECT-TYPE
    SYNTAX      Integer32
    MAX-ACCESS  read-write
    STATUS      current
    DESCRIPTION
        "Set of this check and save will clear the accumulated counters and restart ratio calculation.
	    "
    ::= { sm24tat4xbPerformanceMonitor 16 }

sm24tat4xbLossMeasureAvailabilityEnable OBJECT-TYPE
    SYNTAX      Integer32
    MAX-ACCESS  read-write
    STATUS      current
    DESCRIPTION
        "Enable/disable of loss measurement availability.
	    0:disable
	    1:enable
	    "
    ::= { sm24tat4xbPerformanceMonitor 17 }

sm24tat4xbLossMeasureAvailabilityInterval OBJECT-TYPE
    SYNTAX      Integer32
    MAX-ACCESS  read-write
    STATUS      current
    DESCRIPTION
        "Availability interval - number of measurements with same availability in order to change availability state.

	    "
    ::= { sm24tat4xbPerformanceMonitor 18 }

sm24tat4xbLossMeasureAvailabilityFLRThreshold OBJECT-TYPE
    SYNTAX      Integer32
    MAX-ACCESS  read-write
    STATUS      current
    DESCRIPTION
        "Availability frame loss ratio threshold in per mille.
	    "
    ::= { sm24tat4xbPerformanceMonitor 19 }

sm24tat4xbLossMeasureAvailabilityMaintenance OBJECT-TYPE
    SYNTAX      Integer32
    MAX-ACCESS  read-write
    STATUS      current
    DESCRIPTION
        "Enable/disable of loss measurement availability maintenance.
	    "
    ::= { sm24tat4xbPerformanceMonitor 20 }


sm24tat4xbLossMeasureAvailabilityStateNearAvailabilityCount OBJECT-TYPE
    SYNTAX      Integer32
    MAX-ACCESS  read-only
    STATUS      current
    DESCRIPTION
        "Near end availability count.
	    "
    ::= { sm24tat4xbPerformanceMonitor 21 }

sm24tat4xbLossMeasureAvailabilityStateFarAvailabilityCount OBJECT-TYPE
    SYNTAX      Integer32
    MAX-ACCESS  read-only
    STATUS      current
    DESCRIPTION
        "Far end availability count.
	    "
    ::= { sm24tat4xbPerformanceMonitor 22 }

sm24tat4xbLossMeasureAvailStateNearUnavailabilityCount OBJECT-TYPE
    SYNTAX      Integer32
    MAX-ACCESS  read-only
    STATUS      current
    DESCRIPTION
        "Near end unavailability count.
	    "
    ::= { sm24tat4xbPerformanceMonitor 23 }

sm24tat4xbLossMeasureAvailabilityStateFarUnavailabilityCount OBJECT-TYPE
    SYNTAX      Integer32
    MAX-ACCESS  read-only
    STATUS      current
    DESCRIPTION
        "Far end unavailability count.
	    "
    ::= { sm24tat4xbPerformanceMonitor 24 }

sm24tat4xbLossMeasureAvailabilityStateNearState OBJECT-TYPE
    SYNTAX      Integer32
    MAX-ACCESS  read-only
    STATUS      current
    DESCRIPTION
        "Near end availability state.
	    "
    ::= { sm24tat4xbPerformanceMonitor 25 }

sm24tat4xbLossMeasureAvailabilityStateFarState OBJECT-TYPE
    SYNTAX      Integer32
    MAX-ACCESS  read-only
    STATUS      current
    DESCRIPTION
        "Far end availability state.
	    "
    ::= { sm24tat4xbPerformanceMonitor 26 }

sm24tat4xbLossMeasureHighLossIntervalEnable OBJECT-TYPE
    SYNTAX      Integer32
    MAX-ACCESS  read-write
    STATUS      current
    DESCRIPTION
        "Enable/disable of loss measurement high loss interval.
	    0:disable
	    1:enable
	    "
    ::= { sm24tat4xbPerformanceMonitor 27 }

sm24tat4xbLossMeasureHighLossIntervalFLRThreshold OBJECT-TYPE
    SYNTAX      Integer32
    MAX-ACCESS  read-write
    STATUS      current
    DESCRIPTION
        "High Loss Interval frame loss ratio threshold in per mille.
	    "
    ::= { sm24tat4xbPerformanceMonitor 28 }

sm24tat4xbLossMeasureHighLossIntervalConsecutiveInterval OBJECT-TYPE
    SYNTAX      Integer32
    MAX-ACCESS  read-write
    STATUS      current
    DESCRIPTION
        "High Loss Interval consecutive interval (number of measurements).
	    "
    ::= { sm24tat4xbPerformanceMonitor 29 }

sm24tat4xbLossMeasureHighLossIntervalStateNearCount OBJECT-TYPE
    SYNTAX      Integer32
    MAX-ACCESS  read-only
    STATUS      current
    DESCRIPTION
        "Near end high loss interval count (number of measurements where availability state is available and FLR is above high loss interval FLR threshold.
	    "
    ::= { sm24tat4xbPerformanceMonitor 30 }

sm24tat4xbLossMeasureHighLossIntervalStateFarCount OBJECT-TYPE
    SYNTAX      Integer32
    MAX-ACCESS  read-only
    STATUS      current
    DESCRIPTION
        "Far end high loss interval count (number of measurements where availability state is available and FLR is above high loss interval FLR threshold.
	    "
    ::= { sm24tat4xbPerformanceMonitor 31 }

sm24tat4xbLossMeasureIntervalStateNearConsecutiveCount OBJECT-TYPE
    SYNTAX      Integer32
    MAX-ACCESS  read-only
    STATUS      current
    DESCRIPTION
        "Near end high loss interval consecutive count.
	    "
    ::= { sm24tat4xbPerformanceMonitor 32 }

sm24tat4xbLossMeasureIntervalStateFarConsecutiveCount OBJECT-TYPE
    SYNTAX      Integer32
    MAX-ACCESS  read-only
    STATUS      current
    DESCRIPTION
        "Far end high loss interval consecutive count.
	    "
    ::= { sm24tat4xbPerformanceMonitor 33 }

sm24tat4xbLossMeasureSignalDegradeEnable OBJECT-TYPE
    SYNTAX      Integer32
    MAX-ACCESS  read-write
    STATUS      current
    DESCRIPTION
        "Enable/disable of loss measurement signal degrade.
	    0:disable
	    1:enable
	    "
    ::= { sm24tat4xbPerformanceMonitor 34 }

sm24tat4xbLossMeasureSignalDegradeTXMinimum OBJECT-TYPE
    SYNTAX      Integer32
    MAX-ACCESS  read-write
    STATUS      current
    DESCRIPTION
        "Minimum number of frames that must be transmitted in a measurement before frame loss ratio is tested against loss ratio threshold.

	    "
    ::= { sm24tat4xbPerformanceMonitor 35 }

sm24tat4xbLossMeasureSignalDegradeFLRThreshold OBJECT-TYPE
    SYNTAX      Integer32
    MAX-ACCESS  read-write
    STATUS      current
    DESCRIPTION
        "Signal Degraded frame loss ratio threshold in per mille.
	    "
    ::= { sm24tat4xbPerformanceMonitor 36 }

sm24tat4xbLossMeasureSignalDegradeBadThreshold OBJECT-TYPE
    SYNTAX      Integer32
    MAX-ACCESS  read-write
    STATUS      current
    DESCRIPTION
        "Number of consecutive bad interval measurements required to set degrade state.
	    "
    ::= { sm24tat4xbPerformanceMonitor 37 }

sm24tat4xbLossMeasureSignalDegradeGoodThreshold OBJECT-TYPE
    SYNTAX      Integer32
    MAX-ACCESS  read-write
    STATUS      current
    DESCRIPTION
        "Number of consecutive good interval measurements required to clear degrade state.
	    "
    ::= { sm24tat4xbPerformanceMonitor 38 }

sm24tat4xbDelayMeasureEnable OBJECT-TYPE
    SYNTAX      Integer32
    MAX-ACCESS  read-write
    STATUS      current
    DESCRIPTION
        "Delay Measurement based on transmitting 1DM/DMM PDU can be enabled/disabled.
	    Delay Measurement based on receiving and handling 1DM/DMR PDU is always enabled.
	    0:disable
	    1:enable
	    "
    ::= { sm24tat4xbPerformanceMonitor 39 }

sm24tat4xbDelayMeasurePriority OBJECT-TYPE
    SYNTAX      Integer32
    MAX-ACCESS  read-write
    STATUS      current
    DESCRIPTION
        "The priority to be inserted as PCP bits in TAG (if any).
    Range:0-7
	    "
    ::= { sm24tat4xbPerformanceMonitor 40 }

sm24tat4xbDelayMeasureCast OBJECT-TYPE
    SYNTAX      Integer32
    MAX-ACCESS  read-write
    STATUS      current
    DESCRIPTION
        "Selection of 1DM/DMM PDU transmitted unicast or multicast.
	    The unicast MAC will be configured through 'Peer MEP'.
	    0: Unicast destination address
	    1: Multicast destination address
	    "
    ::= { sm24tat4xbPerformanceMonitor 41 }

sm24tat4xbDelayMeasurePeerMEP OBJECT-TYPE
    SYNTAX      Integer32
    MAX-ACCESS  read-write
    STATUS      current
    DESCRIPTION
        "This is only used if the 'Cast' is configured to Uni.
	    The 1DM/DMR unicast MAC will be taken from the 'Unicast Peer MAC' configuration of this peer.
	    "
    ::= { sm24tat4xbPerformanceMonitor 42 }

sm24tat4xbDelayMeasureEnded OBJECT-TYPE
    SYNTAX      Integer32
    MAX-ACCESS  read-write
    STATUS      current
    DESCRIPTION
        "0:One-Way: One-Way Delay Measurement implemented on 1DM.
        1:Two-Way: Two-Way Delay Measurement implemented on DMM/DMR.
	    "
    ::= { sm24tat4xbPerformanceMonitor 43 }

sm24tat4xbDelayMeasureTxMode OBJECT-TYPE
    SYNTAX      Integer32
    MAX-ACCESS  read-write
    STATUS      current
    DESCRIPTION
        "0:Standardize: Y.1731 standardize way to transmit 1DM/DMR.
        1:Proprietary: Vitesse proprietary way with follow-up packets to transmit 1DM/DMR.
	    "
    ::= { sm24tat4xbPerformanceMonitor 44 }

sm24tat4xbDelayMeasureCalc OBJECT-TYPE
    SYNTAX      Integer32
    MAX-ACCESS  read-write
    STATUS      current
    DESCRIPTION
        "This is only used if the 'Way' is configured to Two-way.
        0:Round trip: The frame delay calculated by the transmitting and receiving timestamps of initiators.
		    Frame Delay = RxTimeb-TxTimeStampf
        1:Flow: The frame delay calculated by the transmitting and receiving timestamps of initiators and remotes.
		    Frame Delay = (RxTimeb-TxTimeStampf)-(TxTimeStampb-RxTimeStampf)
	    "
    ::= { sm24tat4xbPerformanceMonitor 45 }

sm24tat4xbDelayMeasureGap OBJECT-TYPE
    SYNTAX      Integer32
    MAX-ACCESS  read-write
    STATUS      current
    DESCRIPTION
        "The gap between transmitting 1DM/DMM PDU in 10ms. The range is 10 to 65535.
	    "
    ::= { sm24tat4xbPerformanceMonitor 46 }

sm24tat4xbDelayMeasureCount OBJECT-TYPE
    SYNTAX      Integer32
    MAX-ACCESS  read-write
    STATUS      current
    DESCRIPTION
        "The number of last records to calculate. The range is 10 to 2000.
	    "
    ::= { sm24tat4xbPerformanceMonitor 47 }

sm24tat4xbDelayMeasureUnit OBJECT-TYPE
    SYNTAX      Integer32
    MAX-ACCESS  read-write
    STATUS      current
    DESCRIPTION
        "The time resolution.
	    0:us
	    1:ns
	    "
    ::= { sm24tat4xbPerformanceMonitor 48 }

sm24tat4xbDelayMeasureD2forD1 OBJECT-TYPE
    SYNTAX      Integer32
    MAX-ACCESS  read-write
    STATUS      current
    DESCRIPTION
        "Enable to use DMM/DMR packet to calculate one-way DM.
	    0:disable
	    1:enable
	    "
    ::= { sm24tat4xbPerformanceMonitor 49 }

sm24tat4xbDelayMeasureCounterOverflowAction OBJECT-TYPE
    SYNTAX      Integer32
    MAX-ACCESS  read-write
    STATUS      current
    DESCRIPTION
        "The action to counter when overflow happens.
	    0: Keep:When internal total delay counter overflow, DM is disabled automatically
	    1: Reset:When internal total delay counter overflow, counter is reset and DM continues running
	    "
    ::= { sm24tat4xbPerformanceMonitor 50 }

sm24tat4xbDelayMeasureStateOnewayTx OBJECT-TYPE
    SYNTAX      DisplayString
    MAX-ACCESS  read-only
    STATUS      current
    DESCRIPTION
        "The accumulated transmit count - since last 'clear'.
	    "
    ::= { sm24tat4xbPerformanceMonitor 51 }

sm24tat4xbDelayMeasureStateOnewayRx OBJECT-TYPE
    SYNTAX      DisplayString
    MAX-ACCESS  read-only
    STATUS      current
    DESCRIPTION
        "The accumulated receive count - since last 'clear'.
	    "
    ::= { sm24tat4xbPerformanceMonitor 52 }

sm24tat4xbDelayMeasureStateOnewayRxTimeout OBJECT-TYPE
    SYNTAX      DisplayString
    MAX-ACCESS  read-only
    STATUS      current
    DESCRIPTION
        "The accumulated receive timeout count for two-way only - since last 'clear'.
	    "
    ::= { sm24tat4xbPerformanceMonitor 53 }

sm24tat4xbDelayMeasureStateOnewayRxError OBJECT-TYPE
    SYNTAX      DisplayString
    MAX-ACCESS  read-only
    STATUS      current
    DESCRIPTION
        "The accumulated receive error count - since last 'clear'.
	    This is counting if the frame delay is larger than 1 second or if far end residence time is larger than the round trip time.
	    "
    ::= { sm24tat4xbPerformanceMonitor 54 }

sm24tat4xbDelayMeasureStateOnewayAvDelayTot OBJECT-TYPE
    SYNTAX      DisplayString
    MAX-ACCESS  read-only
    STATUS      current
    DESCRIPTION
        "The average total delay - since last 'clear'.
	    "
    ::= { sm24tat4xbPerformanceMonitor 55 }

sm24tat4xbDelayMeasureStateOnewayAvDelaylastN OBJECT-TYPE
    SYNTAX      DisplayString
    MAX-ACCESS  read-only
    STATUS      current
    DESCRIPTION
        "The average delay of the last n packets - since last 'clear'.
	    "
    ::= { sm24tat4xbPerformanceMonitor 56 }

sm24tat4xbDelayMeasureStateOnewayDelayMin OBJECT-TYPE
    SYNTAX      DisplayString
    MAX-ACCESS  read-only
    STATUS      current
    DESCRIPTION
        "The minimum delay - since last 'clear'.
	    "
    ::= { sm24tat4xbPerformanceMonitor 57 }

sm24tat4xbDelayMeasureStateOnewayDelayMax OBJECT-TYPE
    SYNTAX      DisplayString
    MAX-ACCESS  read-only
    STATUS      current
    DESCRIPTION
        "The maximum delay - since last 'clear'.
	    "
    ::= { sm24tat4xbPerformanceMonitor 58 }

sm24tat4xbDelayMeasureStateOnewayAvDelayVarTot OBJECT-TYPE
    SYNTAX      DisplayString
    MAX-ACCESS  read-only
    STATUS      current
    DESCRIPTION
        "The average total delay variation - since last 'clear'.
	    "
    ::= { sm24tat4xbPerformanceMonitor 59 }

sm24tat4xbDelayMeasureStateOnewayAvDelayVarlastN OBJECT-TYPE
    SYNTAX      DisplayString
    MAX-ACCESS  read-only
    STATUS      current
    DESCRIPTION
        "The average delay variation of the last n packets - since last 'clear'.
	    "
    ::= { sm24tat4xbPerformanceMonitor 60 }

sm24tat4xbDelayMeasureStateOnewayDelayVarMin OBJECT-TYPE
    SYNTAX      DisplayString
    MAX-ACCESS  read-only
    STATUS      current
    DESCRIPTION
        "The minimum delay variation - since last 'clear'.
	    "
    ::= { sm24tat4xbPerformanceMonitor 61 }

sm24tat4xbDelayMeasureStateOnewayDelayVarMax OBJECT-TYPE
    SYNTAX      DisplayString
    MAX-ACCESS  read-only
    STATUS      current
    DESCRIPTION
        "The maximum delay variation - since last 'clear'.
	    "
    ::= { sm24tat4xbPerformanceMonitor 62 }

sm24tat4xbDelayMeasureStateOnewayOverflow OBJECT-TYPE
    SYNTAX      DisplayString
    MAX-ACCESS  read-only
    STATUS      current
    DESCRIPTION
        "The number of counter overflow - since last 'clear'.
	    "
    ::= { sm24tat4xbPerformanceMonitor 63 }

sm24tat4xbDelayMeasureStateFtoNTx OBJECT-TYPE
    SYNTAX      Integer32
    MAX-ACCESS  read-only
    STATUS      current
    DESCRIPTION
        "The accumulated transmit count - since last 'clear'.
	    "
    ::= { sm24tat4xbPerformanceMonitor 64 }

sm24tat4xbDelayMeasureStateFtoNRx OBJECT-TYPE
    SYNTAX      Integer32
    MAX-ACCESS  read-only
    STATUS      current
    DESCRIPTION
        "The accumulated receive count - since last 'clear'.
	    "
    ::= { sm24tat4xbPerformanceMonitor 65 }

sm24tat4xbDelayMeasureStateFtoNRxTimeout OBJECT-TYPE
    SYNTAX      Integer32
    MAX-ACCESS  read-only
    STATUS      current
    DESCRIPTION
        "The accumulated receive timeout count for two-way only - since last 'clear'.
	    "
    ::= { sm24tat4xbPerformanceMonitor 66 }

sm24tat4xbDelayMeasureStateFtoNRxError OBJECT-TYPE
    SYNTAX      Integer32
    MAX-ACCESS  read-only
    STATUS      current
    DESCRIPTION
        "The accumulated receive error count - since last 'clear'.
	    This is counting if the frame delay is larger than 1 second or if far end residence time is larger than the round trip time.
	    "
    ::= { sm24tat4xbPerformanceMonitor 67 }

sm24tat4xbDelayMeasureStateFtoNAvDelayTot OBJECT-TYPE
    SYNTAX      Integer32
    MAX-ACCESS  read-only
    STATUS      current
    DESCRIPTION
        "The average total delay - since last 'clear'.
	    "
    ::= { sm24tat4xbPerformanceMonitor 68 }

sm24tat4xbDelayMeasureStateFtoNAvDelaylastN OBJECT-TYPE
    SYNTAX      Integer32
    MAX-ACCESS  read-only
    STATUS      current
    DESCRIPTION
        "The average delay of the last n packets - since last 'clear'.
	    "
    ::= { sm24tat4xbPerformanceMonitor 69 }

sm24tat4xbDelayMeasureStateFtoNDelayMin OBJECT-TYPE
    SYNTAX      Integer32
    MAX-ACCESS  read-only
    STATUS      current
    DESCRIPTION
        "The minimum delay - since last 'clear'.
	    "
    ::= { sm24tat4xbPerformanceMonitor 70 }

sm24tat4xbDelayMeasureStateFtoNDelayMax OBJECT-TYPE
    SYNTAX      Integer32
    MAX-ACCESS  read-only
    STATUS      current
    DESCRIPTION
        "The maximum delay - since last 'clear'.
	    "
    ::= { sm24tat4xbPerformanceMonitor 71 }

sm24tat4xbDelayMeasureStateFtoNAvDelayVarTot OBJECT-TYPE
    SYNTAX      Integer32
    MAX-ACCESS  read-only
    STATUS      current
    DESCRIPTION
        "The average total delay variation - since last 'clear'.
	    "
    ::= { sm24tat4xbPerformanceMonitor 72 }

sm24tat4xbDelayMeasureStateFtoNAvDelayVarlastN OBJECT-TYPE
    SYNTAX      Integer32
    MAX-ACCESS  read-only
    STATUS      current
    DESCRIPTION
        "The average delay variation of the last n packets - since last 'clear'.
	    "
    ::= { sm24tat4xbPerformanceMonitor 73 }

sm24tat4xbDelayMeasureStateFtoNDelayVarMin OBJECT-TYPE
    SYNTAX      Integer32
    MAX-ACCESS  read-only
    STATUS      current
    DESCRIPTION
        "The minimum delay variation - since last 'clear'.
	    "
    ::= { sm24tat4xbPerformanceMonitor 74 }

sm24tat4xbDelayMeasureStateFtoNDelayVarMax OBJECT-TYPE
    SYNTAX      Integer32
    MAX-ACCESS  read-only
    STATUS      current
    DESCRIPTION
        "The maximum delay variation - since last 'clear'.
	    "
    ::= { sm24tat4xbPerformanceMonitor 75 }

sm24tat4xbDelayMeasureStateFtoNOverflow OBJECT-TYPE
    SYNTAX      Integer32
    MAX-ACCESS  read-only
    STATUS      current
    DESCRIPTION
        "The number of counter overflow - since last 'clear'.
	    "
    ::= { sm24tat4xbPerformanceMonitor 76 }

sm24tat4xbDelayMeasureStateNtoFTx OBJECT-TYPE
    SYNTAX      Integer32
    MAX-ACCESS  read-only
    STATUS      current
    DESCRIPTION
        "The accumulated transmit count - since last 'clear'.
	    "
    ::= { sm24tat4xbPerformanceMonitor 77 }

sm24tat4xbDelayMeasureStateNtoFRx OBJECT-TYPE
    SYNTAX      Integer32
    MAX-ACCESS  read-only
    STATUS      current
    DESCRIPTION
        "The accumulated receive count - since last 'clear'.
	    "
    ::= { sm24tat4xbPerformanceMonitor 78 }

sm24tat4xbDelayMeasureStateNtoFRxTimeout OBJECT-TYPE
    SYNTAX      Integer32
    MAX-ACCESS  read-only
    STATUS      current
    DESCRIPTION
        "The accumulated receive timeout count for two-way only - since last 'clear'.
	    "
    ::= { sm24tat4xbPerformanceMonitor 79 }

sm24tat4xbDelayMeasureStateNtoFRxError OBJECT-TYPE
    SYNTAX      Integer32
    MAX-ACCESS  read-only
    STATUS      current
    DESCRIPTION
        "The accumulated receive error count - since last 'clear'.
	    This is counting if the frame delay is larger than 1 second or if far end residence time is larger than the round trip time.
	    "
    ::= { sm24tat4xbPerformanceMonitor 80 }

sm24tat4xbDelayMeasureStateNtoFAvDelayTot OBJECT-TYPE
    SYNTAX      Integer32
    MAX-ACCESS  read-only
    STATUS      current
    DESCRIPTION
        "The average total delay - since last 'clear'.
	    "
    ::= { sm24tat4xbPerformanceMonitor 81 }

sm24tat4xbDelayMeasureStateNtoFAvDelaylastN OBJECT-TYPE
    SYNTAX      Integer32
    MAX-ACCESS  read-only
    STATUS      current
    DESCRIPTION
        "The average delay of the last n packets - since last 'clear'.
	    "
    ::= { sm24tat4xbPerformanceMonitor 82 }

sm24tat4xbDelayMeasureStateNtoFDelayMin OBJECT-TYPE
    SYNTAX      Integer32
    MAX-ACCESS  read-only
    STATUS      current
    DESCRIPTION
        "The minimum delay - since last 'clear'.
	    "
    ::= { sm24tat4xbPerformanceMonitor 83 }

sm24tat4xbDelayMeasureStateNtoFDelayMax OBJECT-TYPE
    SYNTAX      Integer32
    MAX-ACCESS  read-only
    STATUS      current
    DESCRIPTION
        "The maximum delay - since last 'clear'.
	    "
    ::= { sm24tat4xbPerformanceMonitor 84 }

sm24tat4xbDelayMeasureStateNtoFAvDelayVarTot OBJECT-TYPE
    SYNTAX      Integer32
    MAX-ACCESS  read-only
    STATUS      current
    DESCRIPTION
        "The average total delay variation - since last 'clear'.
	    "
    ::= { sm24tat4xbPerformanceMonitor 85 }

sm24tat4xbDelayMeasureStateNtoFAvDelayVarlastN OBJECT-TYPE
    SYNTAX      Integer32
    MAX-ACCESS  read-only
    STATUS      current
    DESCRIPTION
        "The average delay variation of the last n packets - since last 'clear'.
	    "
    ::= { sm24tat4xbPerformanceMonitor 86 }

sm24tat4xbDelayMeasureStateNtoFDelayVarMin OBJECT-TYPE
    SYNTAX      Integer32
    MAX-ACCESS  read-only
    STATUS      current
    DESCRIPTION
        "The minimum delay variation - since last 'clear'.
	    "
    ::= { sm24tat4xbPerformanceMonitor 87 }

sm24tat4xbDelayMeasureStateNtoFDelayVarMax OBJECT-TYPE
    SYNTAX      Integer32
    MAX-ACCESS  read-only
    STATUS      current
    DESCRIPTION
        "The maximum delay variation - since last 'clear'.
	    "
    ::= { sm24tat4xbPerformanceMonitor 88 }

sm24tat4xbDelayMeasureStateNtoFOverflow OBJECT-TYPE
    SYNTAX      Integer32
    MAX-ACCESS  read-only
    STATUS      current
    DESCRIPTION
        "The number of counter overflow - since last 'clear'.
	    "
    ::= { sm24tat4xbPerformanceMonitor 89 }

sm24tat4xbDelayMeasureStateTwowayTx OBJECT-TYPE
    SYNTAX      Integer32
    MAX-ACCESS  read-only
    STATUS      current
    DESCRIPTION
        "The accumulated transmit count - since last 'clear'.
	    "
    ::= { sm24tat4xbPerformanceMonitor 90 }

sm24tat4xbDelayMeasureStateTwowayRx OBJECT-TYPE
    SYNTAX      Integer32
    MAX-ACCESS  read-only
    STATUS      current
    DESCRIPTION
        "The accumulated receive count - since last 'clear'.
	    "
    ::= { sm24tat4xbPerformanceMonitor 91 }

sm24tat4xbDelayMeasureStateTwowayRxTimeout OBJECT-TYPE
    SYNTAX      Integer32
    MAX-ACCESS  read-only
    STATUS      current
    DESCRIPTION
        "The accumulated receive timeout count for two-way only - since last 'clear'.
	    "
    ::= { sm24tat4xbPerformanceMonitor 92 }

sm24tat4xbDelayMeasureStateTwowayRxError OBJECT-TYPE
    SYNTAX      Integer32
    MAX-ACCESS  read-only
    STATUS      current
    DESCRIPTION
        "The accumulated receive error count - since last 'clear'.
	    This is counting if the frame delay is larger than 1 second or if far end residence time is larger than the round trip time.
	    "
    ::= { sm24tat4xbPerformanceMonitor 93 }

sm24tat4xbDelayMeasureStateTwowayAvDelayTot OBJECT-TYPE
    SYNTAX      Integer32
    MAX-ACCESS  read-only
    STATUS      current
    DESCRIPTION
        "The average total delay - since last 'clear'.
	    "
    ::= { sm24tat4xbPerformanceMonitor 94 }

sm24tat4xbDelayMeasureStateTwowayAvDelaylastN OBJECT-TYPE
    SYNTAX      Integer32
    MAX-ACCESS  read-only
    STATUS      current
    DESCRIPTION
        "The average delay of the last n packets - since last 'clear'.
	    "
    ::= { sm24tat4xbPerformanceMonitor 95 }

sm24tat4xbDelayMeasureStateTwowayDelayMin OBJECT-TYPE
    SYNTAX      Integer32
    MAX-ACCESS  read-only
    STATUS      current
    DESCRIPTION
        "The minimum delay - since last 'clear'.
	    "
    ::= { sm24tat4xbPerformanceMonitor 96 }

sm24tat4xbDelayMeasureStateTwowayDelayMax OBJECT-TYPE
    SYNTAX      Integer32
    MAX-ACCESS  read-only
    STATUS      current
    DESCRIPTION
        "The maximum delay - since last 'clear'.
	    "
    ::= { sm24tat4xbPerformanceMonitor 97 }

sm24tat4xbDelayMeasureStateTwowayAvDelayVarTot OBJECT-TYPE
    SYNTAX      Integer32
    MAX-ACCESS  read-only
    STATUS      current
    DESCRIPTION
        "The average total delay variation - since last 'clear'.
	    "
    ::= { sm24tat4xbPerformanceMonitor 98 }

sm24tat4xbDelayMeasureStateTwowayAvDelayVarlastN OBJECT-TYPE
    SYNTAX      Integer32
    MAX-ACCESS  read-only
    STATUS      current
    DESCRIPTION
        "The average delay variation of the last n packets - since last 'clear'.
	    "
    ::= { sm24tat4xbPerformanceMonitor 99 }

sm24tat4xbDelayMeasureStateTwowayDelayVarMin OBJECT-TYPE
    SYNTAX      Integer32
    MAX-ACCESS  read-only
    STATUS      current
    DESCRIPTION
        "The minimum delay variation - since last 'clear'.
	    "
    ::= { sm24tat4xbPerformanceMonitor 100 }

sm24tat4xbDelayMeasureStateTwowayDelayVarMax OBJECT-TYPE
    SYNTAX      Integer32
    MAX-ACCESS  read-only
    STATUS      current
    DESCRIPTION
        "The maximum delay variation - since last 'clear'.
	    "
    ::= { sm24tat4xbPerformanceMonitor 101 }

sm24tat4xbDelayMeasureStateTwowayOverflow OBJECT-TYPE
    SYNTAX      Integer32
    MAX-ACCESS  read-only
    STATUS      current
    DESCRIPTION
        "The number of counter overflow - since last 'clear'.
	    "
    ::= { sm24tat4xbPerformanceMonitor 102 }

sm24tat4xbDelayMeasureStateClear OBJECT-TYPE
    SYNTAX      Integer32
    MAX-ACCESS  read-write
    STATUS      current
    DESCRIPTION
        "Set of this check and save will clear the accumulated counters.
	    1:clear
	    "
    ::= { sm24tat4xbPerformanceMonitor 103 }

sm24tat4xbDelayMeasureBinsMeasurementBinsforFD OBJECT-TYPE
    SYNTAX      Integer32
    MAX-ACCESS  read-write
    STATUS      current
    DESCRIPTION
        "Configurable number of Frame Delay Measurement Bins per Measurement Interval.
	    range: 2-10
	    "
    ::= { sm24tat4xbPerformanceMonitor 104 }

sm24tat4xbDelayMeasureBinsMeasurementBinsforIFDV OBJECT-TYPE
    SYNTAX      Integer32
    MAX-ACCESS  read-write
    STATUS      current
    DESCRIPTION
        "Configurable number of Inter-Frame Delay Variation Measurement Bins per Measurement Interval.
	    range: 2-10
	    "
    ::= { sm24tat4xbPerformanceMonitor 105 }

sm24tat4xbDelayMeasureBinsMeasurementThreshold OBJECT-TYPE
    SYNTAX      Integer32
    MAX-ACCESS  read-write
    STATUS      current
    DESCRIPTION
        "Configurable the Measurement Threshold for each Measurement Bin.
	    "
    ::= { sm24tat4xbPerformanceMonitor 106 }




sm24tat4xbPerformanceMonitorDelayMeasurementBinsforFDTable OBJECT-TYPE
    SYNTAX      SEQUENCE OF SM24TAT4XBPerformanceMonitorDelayMeasurementBinsforFDEntry
    MAX-ACCESS  not-accessible
    STATUS      current
    DESCRIPTION
        " "
    ::= { sm24tat4xbMEP 16 }

sm24tat4xbPerformanceMonitorDelayMeasurementBinsforFDEntry OBJECT-TYPE
    SYNTAX      SM24TAT4XBPerformanceMonitorDelayMeasurementBinsforFDEntry
    MAX-ACCESS  not-accessible
    STATUS      current
    DESCRIPTION
        " "
    INDEX    { sm24tat4xbPerformanceMonitorDelayMeasurementBinsforFDIndex  }
    ::= { sm24tat4xbPerformanceMonitorDelayMeasurementBinsforFDTable 1 }

SM24TAT4XBPerformanceMonitorDelayMeasurementBinsforFDEntry ::= SEQUENCE {
    sm24tat4xbPerformanceMonitorDelayMeasurementBinsforFDIndex    Integer32,
    sm24tat4xbPerformanceMonitorDelayMeasurementBinsforFDOneway    Integer32,
    sm24tat4xbPerformanceMonitorDelayMeasurementBinsforFDFtoN     Integer32,
    sm24tat4xbPerformanceMonitorDelayMeasurementBinsforFDNtoF     Integer32,
    sm24tat4xbPerformanceMonitorDelayMeasurementBinsforFDTwoway    Integer32

}

sm24tat4xbPerformanceMonitorDelayMeasurementBinsforFDIndex OBJECT-TYPE
    SYNTAX      Integer32(1..65535)
    MAX-ACCESS  not-accessible
    STATUS      current
    DESCRIPTION
        "Index"
    ::= { sm24tat4xbPerformanceMonitorDelayMeasurementBinsforFDEntry 1 }

sm24tat4xbPerformanceMonitorDelayMeasurementBinsforFDOneway OBJECT-TYPE
    SYNTAX      Integer32
    MAX-ACCESS  read-only
    STATUS      current
    DESCRIPTION
        " "
    ::= { sm24tat4xbPerformanceMonitorDelayMeasurementBinsforFDEntry 2 }

sm24tat4xbPerformanceMonitorDelayMeasurementBinsforFDFtoN OBJECT-TYPE
    SYNTAX      Integer32
    MAX-ACCESS  read-only
    STATUS      current
    DESCRIPTION
        " "
    ::= { sm24tat4xbPerformanceMonitorDelayMeasurementBinsforFDEntry 3 }

sm24tat4xbPerformanceMonitorDelayMeasurementBinsforFDNtoF OBJECT-TYPE
    SYNTAX      Integer32
    MAX-ACCESS  read-only
    STATUS      current
    DESCRIPTION
        " "
    ::= { sm24tat4xbPerformanceMonitorDelayMeasurementBinsforFDEntry 4 }

sm24tat4xbPerformanceMonitorDelayMeasurementBinsforFDTwoway OBJECT-TYPE
    SYNTAX      Integer32
    MAX-ACCESS  read-only
    STATUS      current
    DESCRIPTION
        " "
    ::= { sm24tat4xbPerformanceMonitorDelayMeasurementBinsforFDEntry 5 }




sm24tat4xbPerformanceMonitorDelayMeasurementBinsforIFDVTable OBJECT-TYPE
    SYNTAX      SEQUENCE OF SM24TAT4XBPerformanceMonitorDelayMeasurementBinsforIFDVEntry
    MAX-ACCESS  not-accessible
    STATUS      current
    DESCRIPTION
        " "
    ::= { sm24tat4xbMEP 17 }

sm24tat4xbPerformanceMonitorDelayMeasurementBinsforIFDVEntry OBJECT-TYPE
    SYNTAX      SM24TAT4XBPerformanceMonitorDelayMeasurementBinsforIFDVEntry
    MAX-ACCESS  not-accessible
    STATUS      current
    DESCRIPTION
        " "
    INDEX    { sm24tat4xbPerformanceMonitorDelayMeasureBinsforIFDVIndex  }
    ::= { sm24tat4xbPerformanceMonitorDelayMeasurementBinsforIFDVTable 1 }

SM24TAT4XBPerformanceMonitorDelayMeasurementBinsforIFDVEntry ::= SEQUENCE {
    sm24tat4xbPerformanceMonitorDelayMeasureBinsforIFDVIndex    Integer32,
    sm24tat4xbPerformanceMonitorDelayMeasureBinsforIFDVOneway    Integer32,
    sm24tat4xbPerformanceMonitorDelayMeasureBinsforIFDVFtoN     Integer32,
    sm24tat4xbPerformanceMonitorDelayMeasureBinsforIFDVNtoF     Integer32,
    sm24tat4xbPerformanceMonitorDelayMeasureBinsforIFDVTwoway    Integer32

}

sm24tat4xbPerformanceMonitorDelayMeasureBinsforIFDVIndex OBJECT-TYPE
    SYNTAX      Integer32(1..65535)
    MAX-ACCESS  not-accessible
    STATUS      current
    DESCRIPTION
        "Index"
    ::= { sm24tat4xbPerformanceMonitorDelayMeasurementBinsforIFDVEntry 1 }

sm24tat4xbPerformanceMonitorDelayMeasureBinsforIFDVOneway OBJECT-TYPE
    SYNTAX      Integer32
    MAX-ACCESS  read-only
    STATUS      current
    DESCRIPTION
        " "
    ::= { sm24tat4xbPerformanceMonitorDelayMeasurementBinsforIFDVEntry 2 }

sm24tat4xbPerformanceMonitorDelayMeasureBinsforIFDVFtoN OBJECT-TYPE
    SYNTAX      Integer32
    MAX-ACCESS  read-only
    STATUS      current
    DESCRIPTION
        " "
    ::= { sm24tat4xbPerformanceMonitorDelayMeasurementBinsforIFDVEntry 3 }

sm24tat4xbPerformanceMonitorDelayMeasureBinsforIFDVNtoF OBJECT-TYPE
    SYNTAX      Integer32
    MAX-ACCESS  read-only
    STATUS      current
    DESCRIPTION
        " "
    ::= { sm24tat4xbPerformanceMonitorDelayMeasurementBinsforIFDVEntry 4 }

sm24tat4xbPerformanceMonitorDelayMeasureBinsforIFDVTwoway OBJECT-TYPE
    SYNTAX      Integer32
    MAX-ACCESS  read-only
    STATUS      current
    DESCRIPTION
        " "
    ::= { sm24tat4xbPerformanceMonitorDelayMeasurementBinsforIFDVEntry 5 }
-- =============================================================================================================
sm24tat4xbPTP    OBJECT IDENTIFIER ::= { sm24tat4xbConfiguration 28 }

sm24tat4xbPTPExternalEnable OBJECT-TYPE
    SYNTAX      Integer32
    MAX-ACCESS  read-write
    STATUS      current
    DESCRIPTION
        "This Selection box will allow you to configure the External Clock output.
		The following values are possible:
		1. True : Enable the external clock output
		0. False : Disable the external clock output
		"
    ::= { sm24tat4xbPTP 1 }

sm24tat4xbPTPAdjustMethod OBJECT-TYPE
    SYNTAX      Integer32
    MAX-ACCESS  read-write
    STATUS      current
    DESCRIPTION
        "This Selection box will allow you to configure the Frequency adjustment configuration.
		0: LTC frequency : Select Local Time Counter (LTC) frequency control
		1: SyncE-DPLL : Select SyncE DPLL frequency control, if allowed by SyncE
		2: Oscillator : Select an oscillator independent of SyncE for frequency control, if supported by the HW
		3: LTC phase : Select Local Time Counter (LTC) phase control (assumes that the frequency is locked by means of SyncE)
		"
    ::= { sm24tat4xbPTP 2 }

sm24tat4xbPTPClockFrequency OBJECT-TYPE
    SYNTAX      Integer32
    MAX-ACCESS  read-write
    STATUS      current
    DESCRIPTION
        "This will allow to set the Clock Frequency.
        The possible range of values are 1 - 25000000 (1 - 25MHz)
	    "
    ::= { sm24tat4xbPTP 3 }



sm24tat4xbPTPClockConfTable  OBJECT-TYPE
    SYNTAX      SEQUENCE OF SM24TAT4XBPTPClockConfEntry
    MAX-ACCESS  not-accessible
    STATUS      current
    DESCRIPTION
        "A table of PTP Clock Conf."
    ::= { sm24tat4xbPTP 5 }

sm24tat4xbPTPClockConfEntry OBJECT-TYPE
    SYNTAX    SM24TAT4XBPTPClockConfEntry
    MAX-ACCESS    not-accessible
    STATUS    current
    DESCRIPTION
        "An entry in the PTP Clock Conf table."
    INDEX    { sm24tat4xbPTPClockConfIndex }
    ::= { sm24tat4xbPTPClockConfTable 1 }

SM24TAT4XBPTPClockConfEntry ::=
    SEQUENCE {
    sm24tat4xbPTPClockConfIndex            Integer32,
    sm24tat4xbPTPClockConfClockInstance        Integer32,
    sm24tat4xbPTPClockConfDeviceType        Integer32,
		sm24tat4xbPTPClockConfProfile          Integer32,
    sm24tat4xbPTPClockConfRowStatus        RowStatus
    }

sm24tat4xbPTPClockConfIndex OBJECT-TYPE
    SYNTAX      Integer32(1..65535)
    MAX-ACCESS  not-accessible
    STATUS      current
    DESCRIPTION
        "PTP Clock Conf index."
    ::= {sm24tat4xbPTPClockConfEntry 1 }

sm24tat4xbPTPClockConfClockInstance OBJECT-TYPE
    SYNTAX      Integer32
    MAX-ACCESS  read-create
    STATUS      current
    DESCRIPTION
        "Indicates the Instance of a particular Clock Instance [0..3]."
    ::= {sm24tat4xbPTPClockConfEntry 2 }

sm24tat4xbPTPClockConfDeviceType OBJECT-TYPE
    SYNTAX      Integer32
    MAX-ACCESS  read-create
    STATUS      current
    DESCRIPTION
        "Indicates the Type of the Clock Instance. There are five Device Types.
	    0: Inactive - passive clock instance
		1: Ord-Bound - clock's Device Type is Ordinary-Boundary Clock.
		2: P2p Transp - clock's Device Type is Peer to Peer Transparent Clock.
		3: E2e Transp - clock's Device Type is End to End Transparent Clock.
		4: Master Only - clock's Device Type is Master Only.
		5: Slave Only - clock's Device Type is Slave Only.
		6: Boundary Clock frontend clock instance, only 1-step, 1-way is supported."
    ::= {sm24tat4xbPTPClockConfEntry 3 }

sm24tat4xbPTPClockConfProfile OBJECT-TYPE
    SYNTAX      Integer32
    MAX-ACCESS  read-create
    STATUS      current
    DESCRIPTION
        "0:No profile
	    1:1588
	    2:G8265.1
	    3:G8275.1
	    "
    ::= {sm24tat4xbPTPClockConfEntry 4 }

sm24tat4xbPTPClockConfRowStatus OBJECT-TYPE
    SYNTAX      RowStatus
    MAX-ACCESS  read-create
    STATUS      current
    DESCRIPTION
        "PTP Clock Conf Row Status."
    ::= {sm24tat4xbPTPClockConfEntry 5 }

sm24tat4xbPTPClockInstance OBJECT-TYPE
    SYNTAX      Integer32
    MAX-ACCESS  read-write
    STATUS      current
    DESCRIPTION
        "Specify the PTP clock instance for the following item used [0..3]."
    ::= {sm24tat4xbPTP 6 }


sm24tat4xbPTPClockConfAndStatus    OBJECT IDENTIFIER ::= { sm24tat4xbPTP 7 }

sm24tat4xbEntryClockInstance OBJECT-TYPE
    SYNTAX      Integer32
    MAX-ACCESS  read-only
    STATUS      current
    DESCRIPTION
        ""
    ::= {sm24tat4xbPTPClockConfAndStatus 2 }

sm24tat4xbEntryDeviceType OBJECT-TYPE
    SYNTAX      DisplayString
    MAX-ACCESS  read-only
    STATUS      current
    DESCRIPTION
        ""
    ::= {sm24tat4xbPTPClockConfAndStatus 3 }

sm24tat4xbEntryProfile OBJECT-TYPE
    SYNTAX      DisplayString
    MAX-ACCESS  read-only
    STATUS      current
    DESCRIPTION
        ""
    ::= {sm24tat4xbPTPClockConfAndStatus 4 }

sm24tat4xbEntryApplyProfileDefaults OBJECT-TYPE
    SYNTAX      Integer32
    MAX-ACCESS  read-write
    STATUS      current
    DESCRIPTION
        "-1:n/a
	    0:normal state
	    1:apply profile default"
    ::= {sm24tat4xbPTPClockConfAndStatus 5 }

sm24tat4xbEntryPTPTime OBJECT-TYPE
    SYNTAX      DisplayString
    MAX-ACCESS  read-only
    STATUS      current
    DESCRIPTION
        "Shows the actual PTP time with nanosecond resolution."
    ::= {sm24tat4xbPTPClockConfAndStatus 6 }

sm24tat4xbEntryClockAdjustmentMethod OBJECT-TYPE
    SYNTAX      DisplayString
    MAX-ACCESS  read-only
    STATUS      current
    DESCRIPTION
        "Shows the actual clock adjustment method. The method depends on the available hardware."
    ::= {sm24tat4xbPTPClockConfAndStatus 7 }

sm24tat4xbEntrySynchronizeToSystemClock OBJECT-TYPE
    SYNTAX      Integer32
    MAX-ACCESS  read-write
    STATUS      current
    DESCRIPTION
        "Activate this button to synchronize the System Clock to PTP Time.
	    1:Synchronize to system clock."
    ::= {sm24tat4xbPTPClockConfAndStatus 8 }

sm24tat4xbEntryClockCurrentDataSetstpRm OBJECT-TYPE
    SYNTAX      Integer32
    MAX-ACCESS  read-only
    STATUS      current
    DESCRIPTION
        "Steps Removed : It is the number of PTP clocks traversed from the grandmaster to the local slave clock."
    ::= {sm24tat4xbPTPClockConfAndStatus 9 }

sm24tat4xbEntryClockCurrentDataSetOffsetFromMaster OBJECT-TYPE
    SYNTAX      DisplayString
    MAX-ACCESS  read-only
    STATUS      current
    DESCRIPTION
        "Time difference between the master clock and the local slave clock, measured in ns."
    ::= {sm24tat4xbPTPClockConfAndStatus 10 }

sm24tat4xbEntryClockCurrentDataSetMeanPathDelay OBJECT-TYPE
    SYNTAX      DisplayString
    MAX-ACCESS  read-only
    STATUS      current
    DESCRIPTION
        "The mean propagation time for the link between the master and the local slave."
    ::= {sm24tat4xbPTPClockConfAndStatus 11 }

sm24tat4xbEntryClockCurrentDataSetSlavePort OBJECT-TYPE
    SYNTAX      Integer32
    MAX-ACCESS  read-only
    STATUS      current
    DESCRIPTION
        "Shows which port is in slave mode. The value is 0 if no ports are in slave mode."
    ::= {sm24tat4xbPTPClockConfAndStatus 12 }

sm24tat4xbEntryClockCurrentDataSetSlaveState OBJECT-TYPE
    SYNTAX      DisplayString
    MAX-ACCESS  read-only
    STATUS      current
    DESCRIPTION
        "Shows synchronization state of the slave."
    ::= {sm24tat4xbPTPClockConfAndStatus 13 }

sm24tat4xbEntryClockCurrentDataSetHoldover OBJECT-TYPE
    SYNTAX      DisplayString
    MAX-ACCESS  read-only
    STATUS      current
    DESCRIPTION
        "After the slave has been in Locked mode during the stabilization period,
	    this value shows the actual clock offset between the freerun and the actual holdover frequency,
	    the value is shown in parts pr billion (ppb).
	    During the stabilization period, the value is shown as N.A.
	    The stabilization period is 60 sec as default, it can be changed from the CLI interface."
    ::= {sm24tat4xbPTPClockConfAndStatus 14 }

sm24tat4xbEntryClockParentDataSetParentPortID OBJECT-TYPE
    SYNTAX      DisplayString
    MAX-ACCESS  read-only
    STATUS      current
    DESCRIPTION
        "Clock identity for the parent clock, if the local clock is not a slave, the value is the clocks own id."
    ::= {sm24tat4xbPTPClockConfAndStatus 15 }

sm24tat4xbEntryClockParentDataSetPort OBJECT-TYPE
    SYNTAX      Integer32
    MAX-ACCESS  read-only
    STATUS      current
    DESCRIPTION
        "Port Id for the parent master port"
    ::= {sm24tat4xbPTPClockConfAndStatus 16 }

sm24tat4xbEntryClockParentDataSetPStat OBJECT-TYPE
    SYNTAX      DisplayString
    MAX-ACCESS  read-only
    STATUS      current
    DESCRIPTION
        "Parents Stats (always false)."
    ::= {sm24tat4xbPTPClockConfAndStatus 17 }

sm24tat4xbEntryClockParentDataSetVar OBJECT-TYPE
    SYNTAX      Integer32
    MAX-ACCESS  read-only
    STATUS      current
    DESCRIPTION
        "It is observed parent offset scaled log variance"
    ::= {sm24tat4xbPTPClockConfAndStatus 18 }

sm24tat4xbEntryClockParentDataSetRate OBJECT-TYPE
    SYNTAX      Integer32
    MAX-ACCESS  read-only
    STATUS      current
    DESCRIPTION
        "Observed Parent Clock Phase Change Rate. i.e. the slave clocks rate offset compared to the master.
	    (unit = ns per s)."
    ::= {sm24tat4xbPTPClockConfAndStatus 19 }

sm24tat4xbEntryClockParentDataSetGrandMasterID OBJECT-TYPE
    SYNTAX      DisplayString
    MAX-ACCESS  read-only
    STATUS      current
    DESCRIPTION
        "Clock identity for the grand master clock, if the local clock is not a slave, the value is the clocks own id."
    ::= {sm24tat4xbPTPClockConfAndStatus 20 }

sm24tat4xbParentDataSetGrandMasterClockQuality OBJECT-TYPE
    SYNTAX      DisplayString
    MAX-ACCESS  read-only
    STATUS      current
    DESCRIPTION
        "The clock quality announced by the grand master (See description of Clock Default DataSet:Clock Quality)"
    ::= {sm24tat4xbPTPClockConfAndStatus 21 }

sm24tat4xbEntryClockParentDataSetPri1 OBJECT-TYPE
    SYNTAX      Integer32
    MAX-ACCESS  read-only
    STATUS      current
    DESCRIPTION
        "Clock priority 1 announced by the grand master"
    ::= {sm24tat4xbPTPClockConfAndStatus 22 }

sm24tat4xbEntryClockParentDataSetPri2 OBJECT-TYPE
    SYNTAX      Integer32
    MAX-ACCESS  read-only
    STATUS      current
    DESCRIPTION
        "Clock priority 2 announced by the grand master."
    ::= {sm24tat4xbPTPClockConfAndStatus 23 }

sm24tat4xbEntryClockDefaultDataSetClockID OBJECT-TYPE
    SYNTAX      Integer32
    MAX-ACCESS  read-only
    STATUS      current
    DESCRIPTION
        "An internal instance id (0..3)"
    ::= {sm24tat4xbPTPClockConfAndStatus 24 }

sm24tat4xbEntryClockDefaultDataSetDeviceType OBJECT-TYPE
    SYNTAX      DisplayString
    MAX-ACCESS  read-only
    STATUS      current
    DESCRIPTION
        "Indicates the Type of the Clock Instance. There are five Device Types.
		1. Ord-Bound - Clock's Device Type is Ordinary-Boundary Clock.
		2. P2p Transp - Clock's Device Type is Peer to Peer Transparent Clock.
		3. E2e Transp - Clock's Device Type is End to End Transparent Clock.
		4. Master Only - Clock's Device Type is Master Only.
		5. Slave Only - Clock's Device Type is Slave Only."
    ::= {sm24tat4xbPTPClockConfAndStatus 25 }

sm24tat4xbEntryClockDefaultDataSet2StepFlag OBJECT-TYPE
    SYNTAX      Integer32
    MAX-ACCESS  read-write
    STATUS      current
    DESCRIPTION
        "True if two-step Sync events and Pdelay_Resp events are used
	    0:false
	    1:true"
    ::= {sm24tat4xbPTPClockConfAndStatus 26 }

sm24tat4xbEntryClockDefaultDataSetPorts OBJECT-TYPE
    SYNTAX      Integer32
    MAX-ACCESS  read-only
    STATUS      current
    DESCRIPTION
        "The total number of physical ports in the node"
    ::= {sm24tat4xbPTPClockConfAndStatus 27 }

sm24tat4xbEntryClockDefaultDataSetClockIdentity OBJECT-TYPE
    SYNTAX      DisplayString
    MAX-ACCESS  read-only
    STATUS      current
    DESCRIPTION
        "It shows unique clock identifier"
    ::= {sm24tat4xbPTPClockConfAndStatus 28 }

sm24tat4xbEntryClockDefaultDataSetDom OBJECT-TYPE
    SYNTAX      Integer32
    MAX-ACCESS  read-write
    STATUS      current
    DESCRIPTION
        "Clock domain [0..127]."
    ::= {sm24tat4xbPTPClockConfAndStatus 29 }

sm24tat4xbEntryClockDefaultDataSetClockQuality OBJECT-TYPE
    SYNTAX      DisplayString
    MAX-ACCESS  read-only
    STATUS      current
    DESCRIPTION
        "The clock quality is determined by the system, and holds 3 parts: Clock Class, Clock Accuracy and OffsetScaledLog Variance as defined in IEEE1588.
        The Clock Accuracy values are defined in IEEE1588 table 6 (Currently the clock Accuracy is set to 'Unknown' as default)."
    ::= {sm24tat4xbPTPClockConfAndStatus 30 }

sm24tat4xbEntryClockDefaultDataSetPri1 OBJECT-TYPE
    SYNTAX      Integer32
    MAX-ACCESS  read-write
    STATUS      current
    DESCRIPTION
        "Clock priority 1 [0..255] used by the BMC master select algorithm."
    ::= {sm24tat4xbPTPClockConfAndStatus 31 }

sm24tat4xbEntryClockDefaultDataSetPri2 OBJECT-TYPE
    SYNTAX      Integer32
    MAX-ACCESS  read-write
    STATUS      current
    DESCRIPTION
        "Clock priority 2 [0..255] used by the BMC master select algorithm."
    ::= {sm24tat4xbPTPClockConfAndStatus 32 }

sm24tat4xbEntryClockDefaultDataSetProtocol OBJECT-TYPE
    SYNTAX      Integer32
    MAX-ACCESS  read-write
    STATUS      current
    DESCRIPTION
        "0:Ethernet
	    1:Ethernet Mixed
	    2:IP4Multi
	    3:IP4Mixed
	    4:IP4Uni
	    5:OAM"
    ::= {sm24tat4xbPTPClockConfAndStatus 33 }

sm24tat4xbEntryClockDefaultDataSetOneWay OBJECT-TYPE
    SYNTAX      Integer32
    MAX-ACCESS  read-write
    STATUS      current
    DESCRIPTION
        "If true, one way measurements are used.
	    This parameter applies only to a slave.
	    In one-way mode no delay measurements are performed, i.e. this is applicable only if frequency synchronization is needed.
	    The master always responds to delay requests.
	    0:false
	    1:true"
    ::= {sm24tat4xbPTPClockConfAndStatus 34 }

sm24tat4xbEntryClockDefaultDataSetVLANTagEnable OBJECT-TYPE
    SYNTAX      Integer32
    MAX-ACCESS  read-write
    STATUS      current
    DESCRIPTION
        "The VLAN Tag Enable parameter is ignored, because the tagging is controlled by the VLAN configuration.
	    0:false
	    1:true"
    ::= {sm24tat4xbPTPClockConfAndStatus 35 }

sm24tat4xbEntryClockDefaultDataSetVID OBJECT-TYPE
    SYNTAX      Integer32
    MAX-ACCESS  read-write
    STATUS      current
    DESCRIPTION
        "TVLAN Identifier used for tagging the VLAN packets.
	    range:1-4095"
    ::= {sm24tat4xbPTPClockConfAndStatus 36 }

sm24tat4xbEntryClockDefaultDataSetPCP OBJECT-TYPE
    SYNTAX      Integer32
    MAX-ACCESS  read-write
    STATUS      current
    DESCRIPTION
        "Priority Code Point value used for PTP frames. range:0-7"
    ::= {sm24tat4xbPTPClockConfAndStatus 37 }

sm24tat4xbEntryClockDefaultDataSetDSCP OBJECT-TYPE
    SYNTAX      Integer32
    MAX-ACCESS  read-write
    STATUS      current
    DESCRIPTION
        ""
    ::= {sm24tat4xbPTPClockConfAndStatus 38 }

sm24tat4xbEntryClockTimePropertiesDataSetUtcOffset OBJECT-TYPE
    SYNTAX      Integer32
    MAX-ACCESS  read-write
    STATUS      current
    DESCRIPTION
        "range: 0-10000"
    ::= {sm24tat4xbPTPClockConfAndStatus 39 }

sm24tat4xbEntryClockTimePropertiesDataSetValid OBJECT-TYPE
    SYNTAX      Integer32
    MAX-ACCESS  read-write
    STATUS      current
    DESCRIPTION
        "0:false
	    1:true"
    ::= {sm24tat4xbPTPClockConfAndStatus 40 }

sm24tat4xbEntryClockTimePropertiesDataSetLeap59 OBJECT-TYPE
    SYNTAX      Integer32
    MAX-ACCESS  read-write
    STATUS      current
    DESCRIPTION
        "0:false
	    1:true"
    ::= {sm24tat4xbPTPClockConfAndStatus 41 }

sm24tat4xbEntryClockTimePropertiesDataSetLeap61 OBJECT-TYPE
    SYNTAX      Integer32
    MAX-ACCESS  read-write
    STATUS      current
    DESCRIPTION
        "0:false
	    1:true"
    ::= {sm24tat4xbPTPClockConfAndStatus 42 }

sm24tat4xbEntryClockTimePropertiesDataSetTimeTrac OBJECT-TYPE
    SYNTAX      Integer32
    MAX-ACCESS  read-write
    STATUS      current
    DESCRIPTION
        "0:false
	    1:true"
    ::= {sm24tat4xbPTPClockConfAndStatus 43 }

sm24tat4xbEntryClockTimePropertiesDataSetFreqTrac OBJECT-TYPE
    SYNTAX      Integer32
    MAX-ACCESS  read-write
    STATUS      current
    DESCRIPTION
        "0:false
	    1:true"
    ::= {sm24tat4xbPTPClockConfAndStatus 44 }

sm24tat4xbTimePropertiesDataSetPTPTimeScale OBJECT-TYPE
    SYNTAX      Integer32
    MAX-ACCESS  read-write
    STATUS      current
    DESCRIPTION
        "0:false
	    1:true"
    ::= {sm24tat4xbPTPClockConfAndStatus 45 }

sm24tat4xbEntryClockTimePropertiesDataSetTimeSource OBJECT-TYPE
    SYNTAX      Integer32
    MAX-ACCESS  read-write
    STATUS      current
    DESCRIPTION
        "range: 0-255"
    ::= {sm24tat4xbPTPClockConfAndStatus 46 }

sm24tat4xbEntryFilterParametersFilterType OBJECT-TYPE
    SYNTAX      Integer32
    MAX-ACCESS  read-write
    STATUS      current
    DESCRIPTION
        "Shows the filter type used which can be either the basic filter or an advanced filter that can be configured to use only a fraction of the packets received
	    (i.e. the packets that have experienced the least latency).
	    0:BASIC"
    ::= {sm24tat4xbPTPClockConfAndStatus 47 }

sm24tat4xbEntryFilterParametersDelayFilter OBJECT-TYPE
    SYNTAX      Integer32
    MAX-ACCESS  read-write
    STATUS      current
    DESCRIPTION
        "range:0-6"
    ::= {sm24tat4xbPTPClockConfAndStatus 48 }

sm24tat4xbEntryFilterParametersPeriod OBJECT-TYPE
    SYNTAX      Integer32
    MAX-ACCESS  read-write
    STATUS      current
    DESCRIPTION
        "range:1-10000"
    ::= {sm24tat4xbPTPClockConfAndStatus 49 }

sm24tat4xbEntryFilterParametersDist OBJECT-TYPE
    SYNTAX      Integer32
    MAX-ACCESS  read-write
    STATUS      current
    DESCRIPTION
        "range:1-10"
    ::= {sm24tat4xbPTPClockConfAndStatus 50 }

sm24tat4xbEntryServoParametersDisplay OBJECT-TYPE
    SYNTAX      Integer32
    MAX-ACCESS  read-write
    STATUS      current
    DESCRIPTION
        "If true then Offset From Master, MeanPathDelay and clockAdjustment are logged on the debug terminal
	    0:false
	    1:true"
    ::= {sm24tat4xbPTPClockConfAndStatus 51 }

sm24tat4xbEntryServoParametersPEnable OBJECT-TYPE
    SYNTAX      Integer32
    MAX-ACCESS  read-write
    STATUS      current
    DESCRIPTION
        "If true the P part of the algorithm is included
	    0:false
	    1:true"
    ::= {sm24tat4xbPTPClockConfAndStatus 52 }

sm24tat4xbEntryServoParametersIEnable OBJECT-TYPE
    SYNTAX      Integer32
    MAX-ACCESS  read-write
    STATUS      current
    DESCRIPTION
        "If true the I part of the algorithm is included
	    0:false
	    1:true"
    ::= {sm24tat4xbPTPClockConfAndStatus 53 }

sm24tat4xbEntryServoParametersDEnable OBJECT-TYPE
    SYNTAX      Integer32
    MAX-ACCESS  read-write
    STATUS      current
    DESCRIPTION
        "If true the D part of the algorithm is included
	    0:false
	    1:true"
    ::= {sm24tat4xbPTPClockConfAndStatus 54 }

sm24tat4xbEntryServoParametersPConstant OBJECT-TYPE
    SYNTAX      Integer32
    MAX-ACCESS  read-write
    STATUS      current
    DESCRIPTION
        "range:0-1000"
    ::= {sm24tat4xbPTPClockConfAndStatus 55 }

sm24tat4xbEntryServoParametersIConstant OBJECT-TYPE
    SYNTAX      Integer32
    MAX-ACCESS  read-write
    STATUS      current
    DESCRIPTION
        "range:0-10000"
    ::= {sm24tat4xbPTPClockConfAndStatus 56 }

sm24tat4xbEntryServoParametersDConstant OBJECT-TYPE
    SYNTAX      Integer32
    MAX-ACCESS  read-write
    STATUS      current
    DESCRIPTION
        "range:0-1000"
    ::= {sm24tat4xbPTPClockConfAndStatus 57 }


sm24tat4xbPTPClockPortDataSetConfTable OBJECT-TYPE
    SYNTAX      SEQUENCE OF SM24TAT4XBPTPClockPortDataSetConfEntry
    MAX-ACCESS  not-accessible
    STATUS      current
    DESCRIPTION
        " "
    ::= { sm24tat4xbPTP 8 }

sm24tat4xbPTPClockPortDataSetConfEntry OBJECT-TYPE
    SYNTAX      SM24TAT4XBPTPClockPortDataSetConfEntry
    MAX-ACCESS  not-accessible
    STATUS      current
    DESCRIPTION
        " "
    INDEX    { sm24tat4xbPTPClockPortDataSetConfPort  }
    ::= { sm24tat4xbPTPClockPortDataSetConfTable 1 }

SM24TAT4XBPTPClockPortDataSetConfEntry ::= SEQUENCE {
    sm24tat4xbPTPClockPortDataSetConfPort        Integer32,
    sm24tat4xbPTPClockConfEntryPortConfEnable        Integer32,
    sm24tat4xbPTPClockConfEntryPortConfStat         DisplayString,
    sm24tat4xbPTPClockConfEntryPortConfMDR          Integer32,
    sm24tat4xbPTPClockConfEntryPortConfPeerMeanPathDel  DisplayString,
    sm24tat4xbPTPClockConfEntryPortConfAnv          Integer32,
    sm24tat4xbPTPClockConfEntryPortConfATo          Integer32,
    sm24tat4xbPTPClockConfEntryPortConfSyv          Integer32,
    sm24tat4xbPTPClockConfEntryPortConfDlm          Integer32,
    sm24tat4xbPTPClockConfEntryPortConfMPR          Integer32,
    sm24tat4xbPTPClockConfEntryPortConfDelayAsymmetry    Integer32,
    sm24tat4xbPTPClockConfEntryPortConfIngressLatency    Integer32,
    sm24tat4xbPTPClockConfEntryPortConfEgressLatency    Integer32,
    sm24tat4xbPTPClockConfEntryPortConfVersion      Integer32
}

sm24tat4xbPTPClockPortDataSetConfPort OBJECT-TYPE
    SYNTAX      Integer32(1..65535)
    MAX-ACCESS  not-accessible
    STATUS      current
    DESCRIPTION
        "Index"
    ::= { sm24tat4xbPTPClockPortDataSetConfEntry 1 }

sm24tat4xbPTPClockConfEntryPortConfEnable OBJECT-TYPE
    SYNTAX      Integer32
    MAX-ACCESS  read-write
    STATUS      current
    DESCRIPTION
        "0:false
	    1:true"
    ::= { sm24tat4xbPTPClockPortDataSetConfEntry 2 }

sm24tat4xbPTPClockConfEntryPortConfStat OBJECT-TYPE
    SYNTAX      DisplayString
    MAX-ACCESS  read-only
    STATUS      current
    DESCRIPTION
        "Dynamic member portState: Current state of the port."
    ::= { sm24tat4xbPTPClockPortDataSetConfEntry 3 }

sm24tat4xbPTPClockConfEntryPortConfMDR OBJECT-TYPE
    SYNTAX      Integer32
    MAX-ACCESS  read-only
    STATUS      current
    DESCRIPTION
        "Dynamic member log Min Delay Req Interval: The delay request interval announced by the master."
    ::= { sm24tat4xbPTPClockPortDataSetConfEntry 4 }

sm24tat4xbPTPClockConfEntryPortConfPeerMeanPathDel OBJECT-TYPE
    SYNTAX      DisplayString
    MAX-ACCESS  read-only
    STATUS      current
    DESCRIPTION
        "The path delay measured by the port in P2P mode. In E2E mode this value is 0"
    ::= { sm24tat4xbPTPClockPortDataSetConfEntry 5 }



sm24tat4xbPTPClockConfEntryPortConfAnv OBJECT-TYPE
    SYNTAX      Integer32
    MAX-ACCESS  read-write
    STATUS      current
    DESCRIPTION
        "The interval for issuing announce messages in master state. Range is -3 to 4."
    ::= { sm24tat4xbPTPClockPortDataSetConfEntry 6 }

sm24tat4xbPTPClockConfEntryPortConfATo OBJECT-TYPE
    SYNTAX      Integer32
    MAX-ACCESS  read-write
    STATUS      current
    DESCRIPTION
        "The timeout for receiving announce messages on the port. Range is 1 to 10."
    ::= { sm24tat4xbPTPClockPortDataSetConfEntry 7 }

sm24tat4xbPTPClockConfEntryPortConfSyv OBJECT-TYPE
    SYNTAX      Integer32
    MAX-ACCESS  read-write
    STATUS      current
    DESCRIPTION
        "The interval for issuing sync messages in master. Range is -7 to 4."
    ::= { sm24tat4xbPTPClockPortDataSetConfEntry 8 }

sm24tat4xbPTPClockConfEntryPortConfDlm OBJECT-TYPE
    SYNTAX      Integer32
    MAX-ACCESS  read-write
    STATUS      current
    DESCRIPTION
        "Configurable member delayMechanism: The delay mechanism used for the port:
		e2e	End to end delay measurement
		p2p	Peer to peer delay measurement.
		Can be defined per port in an Ordinary/Boundary clock.
		In a transparent clock all ports use the same delay mechanism, determined by the clock type.
		1:e2e
		2:p2p"
    ::= { sm24tat4xbPTPClockPortDataSetConfEntry 9 }

sm24tat4xbPTPClockConfEntryPortConfMPR OBJECT-TYPE
    SYNTAX      Integer32
    MAX-ACCESS  read-write
    STATUS      current
    DESCRIPTION
        "The interval for issuing Delay_Req messages for the port in E2e mode. This value is announced from the master to the slave in an announce message. The value is reflected in the MDR field in the Slave
        The interval for issuing Pdelay_Req messages for the port in P2P mode
        Note: The interpretation of this parameter has changed from release 2.40. In earlier versions the value was interpreted relative to the Sync interval, this was a violation of the standard, so now the value is interpreted as an interval. I.e. MPR = 0 => 1 Delay_Req pr sec, independent of the Sync rate.
        Range is -7 to 5."
    ::= { sm24tat4xbPTPClockPortDataSetConfEntry 10 }

sm24tat4xbPTPClockConfEntryPortConfDelayAsymmetry OBJECT-TYPE
    SYNTAX      Integer32
    MAX-ACCESS  read-write
    STATUS      current
    DESCRIPTION
        "If the transmission delay for a link in not symmetric, the asymmetry can be configured here, see IEEE 1588 Section 7.4.2 Communication path asymmetry
        Range is -100000 to 100000."
    ::= { sm24tat4xbPTPClockPortDataSetConfEntry 11 }

sm24tat4xbPTPClockConfEntryPortConfIngressLatency OBJECT-TYPE
    SYNTAX      Integer32
    MAX-ACCESS  read-write
    STATUS      current
    DESCRIPTION
        "Ingress latency measured in ns, as defined in IEEE 1588 Section 7.3.4.2.
        Range is -100000 to 100000."
    ::= { sm24tat4xbPTPClockPortDataSetConfEntry 12 }

sm24tat4xbPTPClockConfEntryPortConfEgressLatency OBJECT-TYPE
    SYNTAX      Integer32
    MAX-ACCESS  read-write
    STATUS      current
    DESCRIPTION
        "Egress latency measured in ns, as defined in IEEE 1588 Section 7.3.4.2.
        Range is -100000 to 100000."
    ::= { sm24tat4xbPTPClockPortDataSetConfEntry 13 }

sm24tat4xbPTPClockConfEntryPortConfVersion OBJECT-TYPE
    SYNTAX      Integer32
    MAX-ACCESS  read-only
    STATUS      current
    DESCRIPTION
        "The current implementation only supports PTP version 2"
    ::= { sm24tat4xbPTPClockPortDataSetConfEntry 14 }


sm24tat4xbPTPClockUnicastSlaveConfTable OBJECT-TYPE
    SYNTAX      SEQUENCE OF SM24TAT4XBPTPClockUnicastSlaveConfEntry
    MAX-ACCESS  not-accessible
    STATUS      current
    DESCRIPTION
        " "
    ::= { sm24tat4xbPTP 9 }

sm24tat4xbPTPClockUnicastSlaveConfEntry OBJECT-TYPE
    SYNTAX      SM24TAT4XBPTPClockUnicastSlaveConfEntry
    MAX-ACCESS  not-accessible
    STATUS      current
    DESCRIPTION
        " "
    INDEX    { sm24tat4xbPTPClockConfEntryUnicastSlaveConfIndex  }
    ::= { sm24tat4xbPTPClockUnicastSlaveConfTable 1 }

SM24TAT4XBPTPClockUnicastSlaveConfEntry ::= SEQUENCE {
    sm24tat4xbPTPClockConfEntryUnicastSlaveConfIndex          Integer32,
    sm24tat4xbPTPClockConfEntryUnicastSlaveConfDuration        Integer32,
    sm24tat4xbPTPClockConfEntryUnicastSlaveConfIPAddress      IpAddress,
    sm24tat4xbPTPClockConfEntryUnicastSlaveConfGrant          Integer32,
    sm24tat4xbPTPClockConfEntryUnicastSlaveConfCommState      DisplayString
}

sm24tat4xbPTPClockConfEntryUnicastSlaveConfIndex OBJECT-TYPE
    SYNTAX      Integer32(1..65535)
    MAX-ACCESS  not-accessible
    STATUS      current
    DESCRIPTION
        "Index"
    ::= { sm24tat4xbPTPClockUnicastSlaveConfEntry 1 }

sm24tat4xbPTPClockConfEntryUnicastSlaveConfDuration OBJECT-TYPE
    SYNTAX      Integer32
    MAX-ACCESS  read-write
    STATUS      current
    DESCRIPTION
        "The number of seconds a master is requested to send Announce/Sync messages.
	    The request is repeated from the slave each Duration/4 seconds.
	    range:10-1000"
    ::= { sm24tat4xbPTPClockUnicastSlaveConfEntry 2 }

sm24tat4xbPTPClockConfEntryUnicastSlaveConfIPAddress OBJECT-TYPE
    SYNTAX      IpAddress
    MAX-ACCESS  read-write
    STATUS      current
    DESCRIPTION
        "IPv4 Address of the Master clock"
    ::= { sm24tat4xbPTPClockUnicastSlaveConfEntry 3 }

sm24tat4xbPTPClockConfEntryUnicastSlaveConfGrant OBJECT-TYPE
    SYNTAX      Integer32
    MAX-ACCESS  read-only
    STATUS      current
    DESCRIPTION
        "The granted repetition period for the sync message"
    ::= { sm24tat4xbPTPClockUnicastSlaveConfEntry 4 }

sm24tat4xbPTPClockConfEntryUnicastSlaveConfCommState OBJECT-TYPE
    SYNTAX      DisplayString
    MAX-ACCESS  read-only
    STATUS      current
    DESCRIPTION
        "The state of the communication with the master, possible values are:
		IDLE : The entry is not in use.
		INIT : Announce is sent to the master (Waiting for a response).
		CONN : The master has responded.
		SELL : The assigned master is selected as current master.
		SYNC : The master is sending Sync messages."
    ::= { sm24tat4xbPTPClockUnicastSlaveConfEntry 5 }
-- =======================================================================================================================
sm24tat4xbETHLINKOAM    OBJECT IDENTIFIER ::= { sm24tat4xbConfiguration 29 }

sm24tat4xbEthLinkOAMPortConfTable OBJECT-TYPE
    SYNTAX      SEQUENCE OF SM24TAT4XBEthLinkOAMPortConfEntry
    MAX-ACCESS  not-accessible
    STATUS      current
    DESCRIPTION
        " "
    ::= { sm24tat4xbETHLINKOAM 1 }

sm24tat4xbEthLinkOAMPortConfEntry OBJECT-TYPE
    SYNTAX      SM24TAT4XBEthLinkOAMPortConfEntry
    MAX-ACCESS  not-accessible
    STATUS      current
    DESCRIPTION
        " "
    INDEX    { sm24tat4xbEthLinkOAMPortConfIndex  }
    ::= { sm24tat4xbEthLinkOAMPortConfTable 1 }

SM24TAT4XBEthLinkOAMPortConfEntry ::= SEQUENCE {
    sm24tat4xbEthLinkOAMPortConfIndex        Integer32,
    sm24tat4xbEthLinkOAMPortConfOAMEnable        Integer32,
    sm24tat4xbEthLinkOAMPortConfOAMMode         Integer32,
    sm24tat4xbEthLinkOAMPortConfLoopbackSupport     Integer32,
    sm24tat4xbEthLinkOAMPortConfLinkMonitorSupport  Integer32,
    sm24tat4xbEthLinkOAMPortConfMIBRetrievalSupport Integer32,
    sm24tat4xbEthLinkOAMPortConfLoopbackOperation    Integer32
}

sm24tat4xbEthLinkOAMPortConfIndex OBJECT-TYPE
    SYNTAX      Integer32(1..65535)
    MAX-ACCESS  not-accessible
    STATUS      current
    DESCRIPTION
        "Index"
    ::= { sm24tat4xbEthLinkOAMPortConfEntry 1 }

sm24tat4xbEthLinkOAMPortConfOAMEnable OBJECT-TYPE
    SYNTAX      Integer32
    MAX-ACCESS  read-write
    STATUS      current
    DESCRIPTION
        "Controls whether Link OAM is enabled on this switch port.
	    Enabling Link OAM provides the network operators the ability to monitor the health of the network and
	    quickly determine the location of failing links or fault conditions.
	    0:disable
	    1:enable"
    ::= { sm24tat4xbEthLinkOAMPortConfEntry 2 }

sm24tat4xbEthLinkOAMPortConfOAMMode OBJECT-TYPE
    SYNTAX      Integer32
    MAX-ACCESS  read-write
    STATUS      current
    DESCRIPTION
        "Configures the OAM Mode as Active or Passive. The default mode is Passive.
	    0:Passive mode
	    1:Active mode"
    ::= { sm24tat4xbEthLinkOAMPortConfEntry 3 }

sm24tat4xbEthLinkOAMPortConfLoopbackSupport OBJECT-TYPE
    SYNTAX      Integer32
    MAX-ACCESS  read-write
    STATUS      current
    DESCRIPTION
        "Controls whether the loopback support is enabled for the switch port.
	    0:disable
	    1:enable"
    ::= { sm24tat4xbEthLinkOAMPortConfEntry 4 }

sm24tat4xbEthLinkOAMPortConfLinkMonitorSupport OBJECT-TYPE
    SYNTAX      Integer32
    MAX-ACCESS  read-write
    STATUS      current
    DESCRIPTION
        "Controls whether the Link Monitor support is enabled for the switch port.
	    0:disable
	    1:enable"
    ::= { sm24tat4xbEthLinkOAMPortConfEntry 5 }

sm24tat4xbEthLinkOAMPortConfMIBRetrievalSupport OBJECT-TYPE
    SYNTAX      Integer32
    MAX-ACCESS  read-write
    STATUS      current
    DESCRIPTION
        "Controls whether the MIB Retrieval Support is enabled for the switch port.
	    0:disable
	    1:enable"
    ::= { sm24tat4xbEthLinkOAMPortConfEntry 6 }

sm24tat4xbEthLinkOAMPortConfLoopbackOperation OBJECT-TYPE
    SYNTAX      Integer32
    MAX-ACCESS  read-write
    STATUS      current
    DESCRIPTION
        "If the Loopback support is enabled, enabling this field will start a loopback operation for the port.
	    0:disable
	    1:enable"
    ::= { sm24tat4xbEthLinkOAMPortConfEntry 7 }



sm24tat4xbEthLinkOAMPortDetailStatusTable OBJECT-TYPE
    SYNTAX      SEQUENCE OF SM24TAT4XBEthLinkOAMPortDetailStatusEntry
    MAX-ACCESS  not-accessible
    STATUS      current
    DESCRIPTION
        "Eth Link OAM Port Detail Status table"
    ::= { sm24tat4xbETHLINKOAM 2 }

sm24tat4xbEthLinkOAMPortDetailStatusEntry OBJECT-TYPE
    SYNTAX      SM24TAT4XBEthLinkOAMPortDetailStatusEntry
    MAX-ACCESS  not-accessible
    STATUS      current
    DESCRIPTION
        "Eth Link OAM Port Detail Status entry"
    INDEX    { sm24tat4xbEthLinkOAMPortDetailStatusIndex  }
    ::= { sm24tat4xbEthLinkOAMPortDetailStatusTable 1 }

SM24TAT4XBEthLinkOAMPortDetailStatusEntry ::= SEQUENCE {
    sm24tat4xbEthLinkOAMPortDetailStatusIndex            Integer32,
    sm24tat4xbEthLinkOAMPortPDUPermission                DisplayString,
    sm24tat4xbEthLinkOAMPortDiscoveryState              DisplayString,
    sm24tat4xbEthLinkOAMPortPeerMACAddress              DisplayString,
    sm24tat4xbEthLinkOAMPortLocalMode                DisplayString,
    sm24tat4xbEthLinkOAMPortLocalUnidirectionalOperationSupport     DisplayString,
    sm24tat4xbEthLinkOAMPortLocalRemoteLoopbackSupport          DisplayString,
    sm24tat4xbEthLinkOAMPortLocalLinkMonitoringSupport          DisplayString,
    sm24tat4xbEthLinkOAMPortLocalMIBRetrievalSupport        DisplayString,
    sm24tat4xbEthLinkOAMPortLocalMTUSize                Integer32,
    sm24tat4xbEthLinkOAMPortLocalMultiplexerState            DisplayString,
    sm24tat4xbEthLinkOAMPortLocalParserState            DisplayString,
    sm24tat4xbEthLinkOAMPortLocalOrganizationalUniqueIdent      DisplayString,
    sm24tat4xbEthLinkOAMPortLocalPDURevision            Integer32,
    sm24tat4xbEthLinkOAMPortPeerMode                DisplayString,
    sm24tat4xbEthLinkOAMPortPeerUnidirectionalOperationSupport      DisplayString,
    sm24tat4xbEthLinkOAMPortPeerRemoteLoopbackSupport        DisplayString,
    sm24tat4xbEthLinkOAMPortPeerLinkMonitoringSupport        DisplayString,
    sm24tat4xbEthLinkOAMPortPeerMIBRetrievalSupport         DisplayString,
    sm24tat4xbEthLinkOAMPortPeerMTUSize                 DisplayString,
    sm24tat4xbEthLinkOAMPortPeerMultiplexerState            DisplayString,
    sm24tat4xbEthLinkOAMPortPeerParserState             DisplayString,
    sm24tat4xbEthLinkOAMPortPeerOrganizationalUniqueIdent        DisplayString,
    sm24tat4xbEthLinkOAMPortPDURevision                 DisplayString
}

sm24tat4xbEthLinkOAMPortDetailStatusIndex OBJECT-TYPE
    SYNTAX      Integer32(1..65535)
    MAX-ACCESS  not-accessible
    STATUS      current
    DESCRIPTION
        "Index"
    ::= { sm24tat4xbEthLinkOAMPortDetailStatusEntry 1 }

sm24tat4xbEthLinkOAMPortPDUPermission OBJECT-TYPE
    SYNTAX      DisplayString
    MAX-ACCESS  read-only
    STATUS      current
    DESCRIPTION
        "This field is available only for the Local DTE.
	    It displays the current permission rules set for the local DTE.
	    Possible values are Link fault, Receive only, Information exchange only, ANY."
    ::= { sm24tat4xbEthLinkOAMPortDetailStatusEntry 2 }

sm24tat4xbEthLinkOAMPortDiscoveryState OBJECT-TYPE
    SYNTAX      DisplayString
    MAX-ACCESS  read-only
    STATUS      current
    DESCRIPTION
        "Displays the current state of the discovery process.
	    Possible states are Fault state, Active state, Passive state,
	    SEND_LOCAL_REMOTE_STATE, SEND_LOCAL_REMOTE_OK_STATE, SEND_ANY_STATE."
    ::= { sm24tat4xbEthLinkOAMPortDetailStatusEntry 3 }

sm24tat4xbEthLinkOAMPortPeerMACAddress OBJECT-TYPE
    SYNTAX      DisplayString
    MAX-ACCESS  read-only
    STATUS      current
    DESCRIPTION
        " "
    ::= { sm24tat4xbEthLinkOAMPortDetailStatusEntry 4 }

sm24tat4xbEthLinkOAMPortLocalMode OBJECT-TYPE
    SYNTAX      DisplayString
    MAX-ACCESS  read-only
    STATUS      current
    DESCRIPTION
        "The Mode in which the Link OAM is operating, Active or Passive."
    ::= { sm24tat4xbEthLinkOAMPortDetailStatusEntry 5 }

sm24tat4xbEthLinkOAMPortLocalUnidirectionalOperationSupport OBJECT-TYPE
    SYNTAX      DisplayString
    MAX-ACCESS  read-only
    STATUS      current
    DESCRIPTION
        "This feature is not available to be configured by the user. The status of this configuration is retrieved from the PHY."
    ::= { sm24tat4xbEthLinkOAMPortDetailStatusEntry 6 }

sm24tat4xbEthLinkOAMPortLocalRemoteLoopbackSupport OBJECT-TYPE
    SYNTAX      DisplayString
    MAX-ACCESS  read-only
    STATUS      current
    DESCRIPTION
        "If status is enabled, DTE is capable of OAM remote loopback mode."
    ::= { sm24tat4xbEthLinkOAMPortDetailStatusEntry 7 }

sm24tat4xbEthLinkOAMPortLocalLinkMonitoringSupport OBJECT-TYPE
    SYNTAX      DisplayString
    MAX-ACCESS  read-only
    STATUS      current
    DESCRIPTION
        "If status is enabled, DTE supports interpreting Link Events."
    ::= { sm24tat4xbEthLinkOAMPortDetailStatusEntry 8 }

sm24tat4xbEthLinkOAMPortLocalMIBRetrievalSupport OBJECT-TYPE
    SYNTAX      DisplayString
    MAX-ACCESS  read-only
    STATUS      current
    DESCRIPTION
        "If status ie enabled DTE supports sending Variable Response OAMPDUs."
    ::= { sm24tat4xbEthLinkOAMPortDetailStatusEntry 9 }

sm24tat4xbEthLinkOAMPortLocalMTUSize OBJECT-TYPE
    SYNTAX      Integer32
    MAX-ACCESS  read-only
    STATUS      current
    DESCRIPTION
        "It represents the largest OAMPDU, in octets, supported by the DTE.
	    This value is compared to the remotes Maximum PDU Size and the smaller of the two is used."
    ::= { sm24tat4xbEthLinkOAMPortDetailStatusEntry 10 }

sm24tat4xbEthLinkOAMPortLocalMultiplexerState OBJECT-TYPE
    SYNTAX      DisplayString
    MAX-ACCESS  read-only
    STATUS      current
    DESCRIPTION
        "When in forwarding state, the Device is forwarding non-OAMPDUs to the lower sublayer.
	    Incase of discarding, the device discards all the non-OAMPDU's."
    ::= { sm24tat4xbEthLinkOAMPortDetailStatusEntry 11 }

sm24tat4xbEthLinkOAMPortLocalParserState OBJECT-TYPE
    SYNTAX      DisplayString
    MAX-ACCESS  read-only
    STATUS      current
    DESCRIPTION
        "When in forwarding state, Device is forwarding non-OAMPDUs to higher sublayer.
	    When in loopback, Device is looping back non-OAMPDUs to the lower sublayer.
	    When in discarding state, Device is discarding non-OAMPDUs."
    ::= { sm24tat4xbEthLinkOAMPortDetailStatusEntry 12 }

sm24tat4xbEthLinkOAMPortLocalOrganizationalUniqueIdent OBJECT-TYPE
    SYNTAX      DisplayString
    MAX-ACCESS  read-only
    STATUS      current
    DESCRIPTION
        "24-bit Organizationally Unique Identifier of the vendor."
    ::= { sm24tat4xbEthLinkOAMPortDetailStatusEntry 13 }

sm24tat4xbEthLinkOAMPortLocalPDURevision OBJECT-TYPE
    SYNTAX      Integer32
    MAX-ACCESS  read-only
    STATUS      current
    DESCRIPTION
        "It indicates the current revision of the Information TLV.
	    The value of this field shall start at zero and be incremented each time something in the Information TLV changes.
	    Upon reception of an Information TLV from a peer, an OAM client may use this field to decide if it needs to be processed
	    (an Information TLV that is identical to the previous Information TLV doesn't need to be parsed as nothing in it has changed)."
    ::= { sm24tat4xbEthLinkOAMPortDetailStatusEntry 14 }

sm24tat4xbEthLinkOAMPortPeerMode OBJECT-TYPE
    SYNTAX      DisplayString
    MAX-ACCESS  read-only
    STATUS      current
    DESCRIPTION
        "The Mode in which the Link OAM is operating, Active or Passive."
    ::= { sm24tat4xbEthLinkOAMPortDetailStatusEntry 15 }

sm24tat4xbEthLinkOAMPortPeerUnidirectionalOperationSupport OBJECT-TYPE
    SYNTAX      DisplayString
    MAX-ACCESS  read-only
    STATUS      current
    DESCRIPTION
        "This feature is not available to be configured by the user.
	    The status of this configuration is retrieved from the PHY."
    ::= { sm24tat4xbEthLinkOAMPortDetailStatusEntry 16 }

sm24tat4xbEthLinkOAMPortPeerRemoteLoopbackSupport OBJECT-TYPE
    SYNTAX      DisplayString
    MAX-ACCESS  read-only
    STATUS      current
    DESCRIPTION
        "If status is enabled, DTE is capable of OAM remote loopback mode."
    ::= { sm24tat4xbEthLinkOAMPortDetailStatusEntry 17 }

sm24tat4xbEthLinkOAMPortPeerLinkMonitoringSupport OBJECT-TYPE
    SYNTAX      DisplayString
    MAX-ACCESS  read-only
    STATUS      current
    DESCRIPTION
        "If status is enabled, DTE supports interpreting Link Events."
    ::= { sm24tat4xbEthLinkOAMPortDetailStatusEntry 18 }

sm24tat4xbEthLinkOAMPortPeerMIBRetrievalSupport OBJECT-TYPE
    SYNTAX      DisplayString
    MAX-ACCESS  read-only
    STATUS      current
    DESCRIPTION
        "If status ie enabled DTE supports sending Variable Response OAMPDUs."
    ::= { sm24tat4xbEthLinkOAMPortDetailStatusEntry 19 }

sm24tat4xbEthLinkOAMPortPeerMTUSize OBJECT-TYPE
    SYNTAX      DisplayString
    MAX-ACCESS  read-only
    STATUS      current
    DESCRIPTION
        "It represents the largest OAMPDU, in octets, supported by the DTE.
	    This value is compared to the remotes Maximum PDU Size and the smaller of the two is used."
    ::= { sm24tat4xbEthLinkOAMPortDetailStatusEntry 20 }

sm24tat4xbEthLinkOAMPortPeerMultiplexerState OBJECT-TYPE
    SYNTAX      DisplayString
    MAX-ACCESS  read-only
    STATUS      current
    DESCRIPTION
        "When in forwarding state, the Device is forwarding non-OAMPDUs to the lower sublayer.
	    Incase of discarding, the device discards all the non-OAMPDU's."
    ::= { sm24tat4xbEthLinkOAMPortDetailStatusEntry 21 }

sm24tat4xbEthLinkOAMPortPeerParserState OBJECT-TYPE
    SYNTAX      DisplayString
    MAX-ACCESS  read-only
    STATUS      current
    DESCRIPTION
        "When in forwarding state, Device is forwarding non-OAMPDUs to higher sublayer.
	    When in loopback, Device is looping back non-OAMPDUs to the lower sublayer.
	    When in discarding state, Device is discarding non-OAMPDUs."
    ::= { sm24tat4xbEthLinkOAMPortDetailStatusEntry 22 }

sm24tat4xbEthLinkOAMPortPeerOrganizationalUniqueIdent OBJECT-TYPE
    SYNTAX      DisplayString
    MAX-ACCESS  read-only
    STATUS      current
    DESCRIPTION
        "24-bit Organizationally Unique Identifier of the vendor."
    ::= { sm24tat4xbEthLinkOAMPortDetailStatusEntry 23 }

sm24tat4xbEthLinkOAMPortPDURevision                  OBJECT-TYPE
    SYNTAX      DisplayString
    MAX-ACCESS  read-only
    STATUS      current
    DESCRIPTION
        "It indicates the current revision of the Information TLV.
	    The value of this field shall start at zero and be incremented each time something in the Information TLV changes.
	    Upon reception of an Information TLV from a peer, an OAM client may use this field to decide if it needs to be processed
	    (an Information TLV that is identical to the previous Information TLV doesn't need to be parsed as nothing in it has changed)."
    ::= { sm24tat4xbEthLinkOAMPortDetailStatusEntry 24 }


sm24tat4xbEthLinkOAMPortLinkEventConfTable OBJECT-TYPE
    SYNTAX      SEQUENCE OF SM24TAT4XBEthLinkOAMPortLinkEventConfEntry
    MAX-ACCESS  not-accessible
    STATUS      current
    DESCRIPTION
        "Eth Link OAM Port Link Event Conf Table"
    ::= { sm24tat4xbETHLINKOAM 3 }

sm24tat4xbEthLinkOAMPortLinkEventConfEntry OBJECT-TYPE
    SYNTAX      SM24TAT4XBEthLinkOAMPortLinkEventConfEntry
    MAX-ACCESS  not-accessible
    STATUS      current
    DESCRIPTION
        "Eth Link OAM Port Link Event Conf Entry"
    INDEX    { sm24tat4xbEventConfIndex  }
    ::= { sm24tat4xbEthLinkOAMPortLinkEventConfTable 1 }

SM24TAT4XBEthLinkOAMPortLinkEventConfEntry ::= SEQUENCE {
    sm24tat4xbEventConfIndex                 Integer32,
    sm24tat4xbEventConfErrorFrameEventErrorWindow        Integer32,
    sm24tat4xbEventConfErrorFrameEventErrorThreshold     Integer32,
    sm24tat4xbEventConfSymbolPeriodErrorEventErrorWindow     Integer32,
    sm24tat4xbEventConfSymbolPeriodErrorEventErrorThreshold  Integer32,
    sm24tat4xbEventConfSecondsSummaryEventErrorWindow    Integer32,
    sm24tat4xbEventConfSecondsSummaryEventErrorThreshold     Integer32
}

sm24tat4xbEventConfIndex OBJECT-TYPE
    SYNTAX      Integer32(1..65535)
    MAX-ACCESS  not-accessible
    STATUS      current
    DESCRIPTION
        "Index"
    ::= { sm24tat4xbEthLinkOAMPortLinkEventConfEntry 1 }

sm24tat4xbEventConfErrorFrameEventErrorWindow OBJECT-TYPE
    SYNTAX      Integer32
    MAX-ACCESS  read-write
    STATUS      current
    DESCRIPTION
        "The Errored Frame Event counts the number of errored frames detected during the specified period.
	    Represents the window period in the order of 1 sec for the observation of various link events.
	    range: 1-60"
    ::= { sm24tat4xbEthLinkOAMPortLinkEventConfEntry 2 }

sm24tat4xbEventConfErrorFrameEventErrorThreshold OBJECT-TYPE
    SYNTAX      Integer32
    MAX-ACCESS  read-write
    STATUS      current
    DESCRIPTION
        "The Errored Frame Event counts the number of errored frames detected during the specified period.
	    Represents the threshold value for the window period for the appropriate Link event so as to notify the peer of this error.
	    range:0-0xffffffff"
    ::= { sm24tat4xbEthLinkOAMPortLinkEventConfEntry 3 }

sm24tat4xbEventConfSymbolPeriodErrorEventErrorWindow OBJECT-TYPE
    SYNTAX      Integer32
    MAX-ACCESS  read-write
    STATUS      current
    DESCRIPTION
        "The Errored Symbol Period Event counts the number of symbol errors that occurred during the specified period.
	    Represents the window period in the order of 1 sec for the observation of various link events.
	    range: 1-60"
    ::= { sm24tat4xbEthLinkOAMPortLinkEventConfEntry 4 }

sm24tat4xbEventConfSymbolPeriodErrorEventErrorThreshold OBJECT-TYPE
    SYNTAX      Integer32
    MAX-ACCESS  read-write
    STATUS      current
    DESCRIPTION
        "The Errored Symbol Period Event counts the number of symbol errors that occurred during the specified period.
	    Represents the threshold value for the window period for the appropriate Link event so as to notify the peer of this error.
	    range:0-0xffffffff"
    ::= { sm24tat4xbEthLinkOAMPortLinkEventConfEntry 5 }

sm24tat4xbEventConfSecondsSummaryEventErrorWindow OBJECT-TYPE
    SYNTAX      Integer32
    MAX-ACCESS  read-write
    STATUS      current
    DESCRIPTION
        "The Errored Frame Seconds Summary Event TLV counts the number of errored frame seconds that occurred during the specified period.
	    Represents the window period in the order of 1 sec for the observation of various link events.
	    range: 10-900"
    ::= { sm24tat4xbEthLinkOAMPortLinkEventConfEntry 6 }

sm24tat4xbEventConfSecondsSummaryEventErrorThreshold OBJECT-TYPE
    SYNTAX      Integer32
    MAX-ACCESS  read-write
    STATUS      current
    DESCRIPTION
        "The Errored Frame Seconds Summary Event TLV counts the number of errored frame seconds that occurred during the specified period.
	    Represents the threshold value for the window period for the appropriate Link event so as to notify the peer of this error.
	    range:0-0xffff"
    ::= { sm24tat4xbEthLinkOAMPortLinkEventConfEntry 7 }




sm24tat4xbEthLinkOAMPortDetailedStatisticsTable OBJECT-TYPE
    SYNTAX      SEQUENCE OF SM24TAT4XBEthLinkOAMPortDetailedStatisticsEntry
    MAX-ACCESS  not-accessible
    STATUS      current
    DESCRIPTION
        "Eth Link OAM Port Detailed Statistics Table"
    ::= { sm24tat4xbETHLINKOAM 4 }

sm24tat4xbEthLinkOAMPortDetailedStatisticsEntry OBJECT-TYPE
    SYNTAX      SM24TAT4XBEthLinkOAMPortDetailedStatisticsEntry
    MAX-ACCESS  not-accessible
    STATUS      current
    DESCRIPTION
        "Eth Link OAM Port Detailed Statistics Entry"
    INDEX    { sm24tat4xbStatisticsIndex  }
    ::= { sm24tat4xbEthLinkOAMPortDetailedStatisticsTable 1 }

SM24TAT4XBEthLinkOAMPortDetailedStatisticsEntry ::= SEQUENCE {
    sm24tat4xbStatisticsIndex                 Integer32,
    sm24tat4xbStatisticsRxOAMInformationPDUs          Integer32,
    sm24tat4xbStatisticsRxUniqueErrorEventNotification    Integer32,
    sm24tat4xbStatisticsRxDuplicateErrorEventNotification Integer32,
    sm24tat4xbStatisticsRxLoopbackControl         Integer32,
    sm24tat4xbStatisticsRxVariableRequest         Integer32,
    sm24tat4xbStatisticsRxVariableResponse        Integer32,
    sm24tat4xbStatisticsRxOrgSpecificPDUs         Integer32,
    sm24tat4xbStatisticsRxUnsupportedCodes        Integer32,
    sm24tat4xbStatisticsRxLinkFaultPDUs            Integer32,
    sm24tat4xbStatisticsRxDyingGasp            Integer32,
    sm24tat4xbStatisticsRxCriticalEventPDUs        Integer32,
    sm24tat4xbStatisticsTxOAMInformationPDUs          Integer32,
    sm24tat4xbStatisticsTxUniqueErrorEventNotification    Integer32,
    sm24tat4xbStatisticsTxDuplicateErrorEventNotification Integer32,
    sm24tat4xbStatisticsTxLoopbackControl         Integer32,
    sm24tat4xbStatisticsTxVariableRequest         Integer32,
    sm24tat4xbStatisticsTxVariableResponse        Integer32,
    sm24tat4xbStatisticsTxOrgSpecificPDUs         Integer32,
    sm24tat4xbStatisticsTxUnsupportedCodes        Integer32,
    sm24tat4xbStatisticsTxLinkFaultPDUs            Integer32,
    sm24tat4xbStatisticsTxDyingGasp            Integer32,
    sm24tat4xbStatisticsTxCriticalEventPDUs        Integer32,
    sm24tat4xbStatisticsClear                 Integer32
}

sm24tat4xbStatisticsIndex OBJECT-TYPE
    SYNTAX      Integer32(1..65535)
    MAX-ACCESS  not-accessible
    STATUS      current
    DESCRIPTION
        "Index"
    ::= { sm24tat4xbEthLinkOAMPortDetailedStatisticsEntry 1 }

sm24tat4xbStatisticsRxOAMInformationPDUs OBJECT-TYPE
    SYNTAX      Integer32
    MAX-ACCESS  read-only
    STATUS      current
    DESCRIPTION
        "The number of received and transmitted OAM Information PDU's.
	    Discontinuities of this counter can occur at re-initialization of the management system."
    ::= { sm24tat4xbEthLinkOAMPortDetailedStatisticsEntry 2 }

sm24tat4xbStatisticsRxUniqueErrorEventNotification OBJECT-TYPE
    SYNTAX      Integer32
    MAX-ACCESS  read-only
    STATUS      current
    DESCRIPTION
        "A count of the number of unique Event OAMPDUs received and transmitted on this interface.
	    Event Notifications may be sent in duplicate to increase the probability of successfully being received,
	    given the possibility that a frame may be lost in transit.
	    Duplicate Event Notification transmissions are counted by
	    Duplicate Event Notification counters for Tx and Rx respectively.
	    A unique Event Notification OAMPDU is indicated as an Event Notification OAMPDU with
	    a Sequence Number field that is distinct from the previously transmitted Event Notification OAMPDU Sequence Number."
    ::= { sm24tat4xbEthLinkOAMPortDetailedStatisticsEntry 3 }

sm24tat4xbStatisticsRxDuplicateErrorEventNotification OBJECT-TYPE
    SYNTAX      Integer32
    MAX-ACCESS  read-only
    STATUS      current
    DESCRIPTION
        "A count of the number of duplicate Event OAMPDUs received and transmitted on this interface.
	    Event Notification OAMPDUs may be sent in duplicate to increase the probability of successfully being received,
	    given the possibility that a frame may be lost in transit.
	    A duplicate Event Notification OAMPDU is indicated as an Event Notification OAMPDU with
	    a Sequence Number field that is identical to the previously transmitted Event Notification OAMPDU Sequence Number."
    ::= { sm24tat4xbEthLinkOAMPortDetailedStatisticsEntry 4 }

sm24tat4xbStatisticsRxLoopbackControl OBJECT-TYPE
    SYNTAX      Integer32
    MAX-ACCESS  read-only
    STATUS      current
    DESCRIPTION
        "A count of the number of Loopback Control OAMPDUs received and transmitted on this interface."
    ::= { sm24tat4xbEthLinkOAMPortDetailedStatisticsEntry 5 }

sm24tat4xbStatisticsRxVariableRequest OBJECT-TYPE
    SYNTAX      Integer32
    MAX-ACCESS  read-only
    STATUS      current
    DESCRIPTION
        "A count of the number of Variable Request OAMPDUs received and transmitted on this interface."
    ::= { sm24tat4xbEthLinkOAMPortDetailedStatisticsEntry 6 }

sm24tat4xbStatisticsRxVariableResponse OBJECT-TYPE
    SYNTAX      Integer32
    MAX-ACCESS  read-only
    STATUS      current
    DESCRIPTION
        "A count of the number of Variable Response OAMPDUs received and transmitted on this interface."
    ::= { sm24tat4xbEthLinkOAMPortDetailedStatisticsEntry 7 }

sm24tat4xbStatisticsRxOrgSpecificPDUs OBJECT-TYPE
    SYNTAX      Integer32
    MAX-ACCESS  read-only
    STATUS      current
    DESCRIPTION
        "A count of the number of Organization Specific OAMPDUs transmitted on this interface."
    ::= { sm24tat4xbEthLinkOAMPortDetailedStatisticsEntry 8 }

sm24tat4xbStatisticsRxUnsupportedCodes OBJECT-TYPE
    SYNTAX      Integer32
    MAX-ACCESS  read-only
    STATUS      current
    DESCRIPTION
        "A count of the number of OAMPDUs transmitted on this interface with an unsupported op-code."
    ::= { sm24tat4xbEthLinkOAMPortDetailedStatisticsEntry 9 }

sm24tat4xbStatisticsRxLinkFaultPDUs OBJECT-TYPE
    SYNTAX      Integer32
    MAX-ACCESS  read-only
    STATUS      current
    DESCRIPTION
        "A count of the number of Link fault PDU's received and transmitted on this interface."
    ::= { sm24tat4xbEthLinkOAMPortDetailedStatisticsEntry 10 }

sm24tat4xbStatisticsRxDyingGasp OBJECT-TYPE
    SYNTAX      Integer32
    MAX-ACCESS  read-only
    STATUS      current
    DESCRIPTION
        "A count of the number of Dying Gasp events received and transmitted on this interface."
    ::= { sm24tat4xbEthLinkOAMPortDetailedStatisticsEntry 11 }

sm24tat4xbStatisticsRxCriticalEventPDUs OBJECT-TYPE
    SYNTAX      Integer32
    MAX-ACCESS  read-only
    STATUS      current
    DESCRIPTION
        "A count of the number of Critical event PDU's received and transmitted on this interface."
    ::= { sm24tat4xbEthLinkOAMPortDetailedStatisticsEntry 12 }

sm24tat4xbStatisticsTxOAMInformationPDUs OBJECT-TYPE
    SYNTAX      Integer32
    MAX-ACCESS  read-only
    STATUS      current
    DESCRIPTION
        "The number of received and transmitted OAM Information PDU's.
	    Discontinuities of this counter can occur at re-initialization of the management system."
    ::= { sm24tat4xbEthLinkOAMPortDetailedStatisticsEntry 13 }

sm24tat4xbStatisticsTxUniqueErrorEventNotification OBJECT-TYPE
    SYNTAX      Integer32
    MAX-ACCESS  read-only
    STATUS      current
    DESCRIPTION
        "A count of the number of unique Event OAMPDUs received and transmitted on this interface.
	    Event Notifications may be sent in duplicate to increase the probability of successfully being received,
	    given the possibility that a frame may be lost in transit.
	    Duplicate Event Notification transmissions are counted by
	    Duplicate Event Notification counters for Tx and Rx respectively.
	    A unique Event Notification OAMPDU is indicated as an Event Notification OAMPDU with
	    a Sequence Number field that is distinct from the previously transmitted Event Notification OAMPDU Sequence Number."
    ::= { sm24tat4xbEthLinkOAMPortDetailedStatisticsEntry 14 }

sm24tat4xbStatisticsTxDuplicateErrorEventNotification OBJECT-TYPE
    SYNTAX      Integer32
    MAX-ACCESS  read-only
    STATUS      current
    DESCRIPTION
        "A count of the number of duplicate Event OAMPDUs received and transmitted on this interface.
	    Event Notification OAMPDUs may be sent in duplicate to increase the probability of successfully being received,
	    given the possibility that a frame may be lost in transit.
	    A duplicate Event Notification OAMPDU is indicated as an Event Notification OAMPDU with
	    a Sequence Number field that is identical to the previously transmitted Event Notification OAMPDU Sequence Number."
    ::= { sm24tat4xbEthLinkOAMPortDetailedStatisticsEntry 15 }

sm24tat4xbStatisticsTxLoopbackControl OBJECT-TYPE
    SYNTAX      Integer32
    MAX-ACCESS  read-only
    STATUS      current
    DESCRIPTION
        "A count of the number of Loopback Control OAMPDUs received and transmitted on this interface."
    ::= { sm24tat4xbEthLinkOAMPortDetailedStatisticsEntry 16 }

sm24tat4xbStatisticsTxVariableRequest OBJECT-TYPE
    SYNTAX      Integer32
    MAX-ACCESS  read-only
    STATUS      current
    DESCRIPTION
        "A count of the number of Variable Request OAMPDUs received and transmitted on this interface."
    ::= { sm24tat4xbEthLinkOAMPortDetailedStatisticsEntry 17 }

sm24tat4xbStatisticsTxVariableResponse OBJECT-TYPE
    SYNTAX      Integer32
    MAX-ACCESS  read-only
    STATUS      current
    DESCRIPTION
        "A count of the number of Variable Response OAMPDUs received and transmitted on this interface."
    ::= { sm24tat4xbEthLinkOAMPortDetailedStatisticsEntry 18 }

sm24tat4xbStatisticsTxOrgSpecificPDUs OBJECT-TYPE
    SYNTAX      Integer32
    MAX-ACCESS  read-only
    STATUS      current
    DESCRIPTION
        "A count of the number of Organization Specific OAMPDUs transmitted on this interface."
    ::= { sm24tat4xbEthLinkOAMPortDetailedStatisticsEntry 19 }

sm24tat4xbStatisticsTxUnsupportedCodes OBJECT-TYPE
    SYNTAX      Integer32
    MAX-ACCESS  read-only
    STATUS      current
    DESCRIPTION
        "A count of the number of OAMPDUs transmitted on this interface with an unsupported op-code."
    ::= { sm24tat4xbEthLinkOAMPortDetailedStatisticsEntry 20 }

sm24tat4xbStatisticsTxLinkFaultPDUs OBJECT-TYPE
    SYNTAX      Integer32
    MAX-ACCESS  read-only
    STATUS      current
    DESCRIPTION
        "A count of the number of Link fault PDU's received and transmitted on this interface."
    ::= { sm24tat4xbEthLinkOAMPortDetailedStatisticsEntry 21 }

sm24tat4xbStatisticsTxDyingGasp OBJECT-TYPE
    SYNTAX      Integer32
    MAX-ACCESS  read-only
    STATUS      current
    DESCRIPTION
        "A count of the number of Dying Gasp events received and transmitted on this interface."
    ::= { sm24tat4xbEthLinkOAMPortDetailedStatisticsEntry 22 }

sm24tat4xbStatisticsTxCriticalEventPDUs OBJECT-TYPE
    SYNTAX      Integer32
    MAX-ACCESS  read-only
    STATUS      current
    DESCRIPTION
        "A count of the number of Critical event PDU's received and transmitted on this interface."
    ::= { sm24tat4xbEthLinkOAMPortDetailedStatisticsEntry 23 }

sm24tat4xbStatisticsClear OBJECT-TYPE
    SYNTAX      Integer32
    MAX-ACCESS  read-write
    STATUS      current
    DESCRIPTION
        "Clears the counters for the selected port."
    ::= { sm24tat4xbEthLinkOAMPortDetailedStatisticsEntry 24 }


sm24tat4xbEthLinkOAMPortEventDetailedStatisticsTable OBJECT-TYPE
    SYNTAX      SEQUENCE OF SM24TAT4XBEthLinkOAMPortEventDetailedStatisticsEntry
    MAX-ACCESS  not-accessible
    STATUS      current
    DESCRIPTION
        "Eth Link OAM Port Event Detailed Statistics Table"
    ::= { sm24tat4xbETHLINKOAM 5 }

sm24tat4xbEthLinkOAMPortEventDetailedStatisticsEntry OBJECT-TYPE
    SYNTAX      SM24TAT4XBEthLinkOAMPortEventDetailedStatisticsEntry
    MAX-ACCESS  not-accessible
    STATUS      current
    DESCRIPTION
        "Eth Link OAM Port Event Detailed Statistics Entry"
    INDEX    { sm24tat4xbDetailedStatisticsIndex  }
    ::= { sm24tat4xbEthLinkOAMPortEventDetailedStatisticsTable 1 }

SM24TAT4XBEthLinkOAMPortEventDetailedStatisticsEntry ::= SEQUENCE {
    sm24tat4xbDetailedStatisticsIndex              Integer32,
    sm24tat4xbStatisticsLocalSequenceNumber            Integer32,
    sm24tat4xbStatisticsLocalFrameErrorEventTimestamp      Integer32,
    sm24tat4xbStatisticsLocalFrameErrorEventWindow         Integer32,
    sm24tat4xbStatisticsLocalFrameErrorEventThreshold      Integer32,
    sm24tat4xbStatisticsLocalFrameErrors            Integer32,
    sm24tat4xbStatisticsLocalTotalFrameErrors          Counter64,
    sm24tat4xbStatisticsLocalTotalFrameErrorEvents         Integer32,
    sm24tat4xbStatisticsLocalFramePeriodErrorEventTimestamp    Integer32,
    sm24tat4xbStatisticsLocalFramePeriodErrorEventWindow    Integer32,
    sm24tat4xbStatisticsLocalFramePeriodErrorEventThreshold    Integer32,
    sm24tat4xbStatisticsLocalFramePeriodErrors         Integer32,
    sm24tat4xbStatisticsLocalTotalFramePeriodErrors        Counter64,
    sm24tat4xbStatisticsLocalTotalFramePeriodErrorEvents    Integer32,
    sm24tat4xbStatisticsLocalSymbolPeriodErrorEventTimestamp    Integer32,
    sm24tat4xbStatisticsLocalSymbolPeriodErrorEventWindow      Counter64,
    sm24tat4xbStatisticsLocalSymbolPeriodErrorEventThreshold    Counter64,
    sm24tat4xbStatisticsLocalSymbolPeriodErrors        Counter64,
    sm24tat4xbStatisticsLocalSymbolFramePeriodErrors        Counter64,
    sm24tat4xbStatisticsLocalSymbolFramePeriodErrorEvents      Integer32,
    sm24tat4xbStatisticsLocalEventSecondsSummaryTimeStamp      Integer32,
    sm24tat4xbStatisticsLocalEventSecondsSummaryWindow     Integer32,
    sm24tat4xbStatisticsLocalEventSecondsSummaryThreshold      Integer32,
    sm24tat4xbStatisticsLocalEventSecondsSummaryEvents     Integer32,
    sm24tat4xbStatisticsLocalEventSecondsSummaryErrorTotal     Integer32,
    sm24tat4xbStatisticsLocalEventSecondsSummaryEventTotal     Integer32,
    sm24tat4xbStatisticsRemoteFrameErrorEventTimestamp     Integer32,
    sm24tat4xbStatisticsRemoteFrameErrorEventWindow        Integer32,
    sm24tat4xbStatisticsRemoteFrameErrorEventThreshold     Integer32,
    sm24tat4xbStatisticsRemoteFrameErrors              Integer32,
    sm24tat4xbStatisticsRemoteTotalFrameErrors         Counter64,
    sm24tat4xbStatisticsRemoteTotalFrameErrorEvents        Integer32,
    sm24tat4xbStatisticsRemoteFramePeriodErrorEventTimestamp    Integer32,
    sm24tat4xbStatisticsRemoteFramePeriodErrorEventWindow      Integer32,
    sm24tat4xbStatisticsRemoteFramePeriodErrorEventThreshold    Integer32,
    sm24tat4xbStatisticsRemoteFramePeriodErrors        Integer32,
    sm24tat4xbStatisticsRemoteTotalFramePeriodErrors        Counter64,
    sm24tat4xbStatisticsRemoteTotalFramePeriodErrorEvents      Integer32,
    sm24tat4xbStatisticsRemoteSymbolPeriodErrorEventTimestamp  Integer32,
    sm24tat4xbStatisticsRemoteSymbolPeriodErrorEventWindow     Counter64,
    sm24tat4xbStatisticsRemoteSymbolPeriodErrorEventThreshold  Counter64,
    sm24tat4xbStatisticsRemoteSymbolPeriodErrors        Counter64,
    sm24tat4xbStatisticsRemoteSymbolFramePeriodErrors      Counter64,
    sm24tat4xbStatisticsRemoteSymbolFramePeriodErrorEvents     Integer32,
    sm24tat4xbStatisticsRemoteEventSecondsSummaryTimeStamp     Integer32,
    sm24tat4xbStatisticsRemoteEventSecondsSummaryWindow    Integer32,
    sm24tat4xbStatisticsRemoteEventSecondsSummaryThreshold     Integer32,
    sm24tat4xbStatisticsRemoteEventSecondsSummaryEvents    Integer32,
    sm24tat4xbStatisticsRemoteEventSecondsSummaryErrorTotal    Integer32,
    sm24tat4xbStatisticsRemoteEventSecondsSummaryEventTotal    Integer32
}

sm24tat4xbDetailedStatisticsIndex OBJECT-TYPE
    SYNTAX      Integer32(1..65535)
    MAX-ACCESS  not-accessible
    STATUS      current
    DESCRIPTION
        "Index"
    ::= { sm24tat4xbEthLinkOAMPortEventDetailedStatisticsEntry 1 }

sm24tat4xbStatisticsLocalSequenceNumber OBJECT-TYPE
    SYNTAX      Integer32
    MAX-ACCESS  read-only
    STATUS      current
    DESCRIPTION
        "This two-octet field indicates the total number of events occurred at the remote end."
    ::= { sm24tat4xbEthLinkOAMPortEventDetailedStatisticsEntry 2 }

sm24tat4xbStatisticsLocalFrameErrorEventTimestamp OBJECT-TYPE
    SYNTAX      Integer32
    MAX-ACCESS  read-only
    STATUS      current
    DESCRIPTION
        "This two-octet field indicates the time reference when the event was generated, in terms of 100 ms intervals."
    ::= { sm24tat4xbEthLinkOAMPortEventDetailedStatisticsEntry 3 }

sm24tat4xbStatisticsLocalFrameErrorEventWindow OBJECT-TYPE
    SYNTAX      Integer32
    MAX-ACCESS  read-only
    STATUS      current
    DESCRIPTION
        "This two-octet field indicates the duration of the period in terms of 100 ms intervals. 1)
	    The default value is one second. 2) The lower bound is one second. 3)
	    The upper bound is one minute."
    ::= { sm24tat4xbEthLinkOAMPortEventDetailedStatisticsEntry 4 }

sm24tat4xbStatisticsLocalFrameErrorEventThreshold OBJECT-TYPE
    SYNTAX      Integer32
    MAX-ACCESS  read-only
    STATUS      current
    DESCRIPTION
        "This four-octet field indicates the number of detected errored frames in the period is required
	    to be equal to or greater than in order for the event to be generated. 1)
	    The default value is one frame error. 2)
	    The lower bound is zero frame errors. 3)
	    The upper bound is unspecified."
    ::= { sm24tat4xbEthLinkOAMPortEventDetailedStatisticsEntry 5 }

sm24tat4xbStatisticsLocalFrameErrors OBJECT-TYPE
    SYNTAX      Integer32
    MAX-ACCESS  read-only
    STATUS      current
    DESCRIPTION
        "This four-octet field indicates the number of detected errored frames in the period."
    ::= { sm24tat4xbEthLinkOAMPortEventDetailedStatisticsEntry 6 }

sm24tat4xbStatisticsLocalTotalFrameErrors OBJECT-TYPE
    SYNTAX      Counter64
    MAX-ACCESS  read-only
    STATUS      current
    DESCRIPTION
        "This eight-octet field indicates the sum of errored frames that have been detected since the OAM sublayer was reset."
    ::= { sm24tat4xbEthLinkOAMPortEventDetailedStatisticsEntry 7 }

sm24tat4xbStatisticsLocalTotalFrameErrorEvents OBJECT-TYPE
    SYNTAX      Integer32
    MAX-ACCESS  read-only
    STATUS      current
    DESCRIPTION
        "This four-octet field indicates the number of Errored Frame Event TLVs that
	    have been generated since the OAM sublayer was reset."
    ::= { sm24tat4xbEthLinkOAMPortEventDetailedStatisticsEntry 8 }

sm24tat4xbStatisticsLocalFramePeriodErrorEventTimestamp OBJECT-TYPE
    SYNTAX      Integer32
    MAX-ACCESS  read-only
    STATUS      current
    DESCRIPTION
        "This two-octet field indicates the time reference when the event was generated, in terms of 100 ms intervals."
    ::= { sm24tat4xbEthLinkOAMPortEventDetailedStatisticsEntry 9 }

sm24tat4xbStatisticsLocalFramePeriodErrorEventWindow OBJECT-TYPE
    SYNTAX      Integer32
    MAX-ACCESS  read-only
    STATUS      current
    DESCRIPTION
        "This four-octet field indicates the duration of period in terms of frames."
    ::= { sm24tat4xbEthLinkOAMPortEventDetailedStatisticsEntry 10 }

sm24tat4xbStatisticsLocalFramePeriodErrorEventThreshold OBJECT-TYPE
    SYNTAX      Integer32
    MAX-ACCESS  read-only
    STATUS      current
    DESCRIPTION
        "This four-octet field indicates the number of errored frames in the period is required
	    to be equal to or greater than in order for the event to be generated."
    ::= { sm24tat4xbEthLinkOAMPortEventDetailedStatisticsEntry 11 }

sm24tat4xbStatisticsLocalFramePeriodErrors OBJECT-TYPE
    SYNTAX      Integer32
    MAX-ACCESS  read-only
    STATUS      current
    DESCRIPTION
        "This four-octet field indicates the number of frame errors in the period."
    ::= { sm24tat4xbEthLinkOAMPortEventDetailedStatisticsEntry 12 }

sm24tat4xbStatisticsLocalTotalFramePeriodErrors OBJECT-TYPE
    SYNTAX      Counter64
    MAX-ACCESS  read-only
    STATUS      current
    DESCRIPTION
        "This eight-octet field indicates the sum of frame errors that have been detected since the OAM sublayer was reset."
    ::= { sm24tat4xbEthLinkOAMPortEventDetailedStatisticsEntry 13 }

sm24tat4xbStatisticsLocalTotalFramePeriodErrorEvents OBJECT-TYPE
    SYNTAX      Integer32
    MAX-ACCESS  read-only
    STATUS      current
    DESCRIPTION
        "This four-octet field indicates the number of Errored Frame Period Event TLVs
	    that have been generated since the OAM sublayer was reset."
    ::= { sm24tat4xbEthLinkOAMPortEventDetailedStatisticsEntry 14 }

sm24tat4xbStatisticsLocalSymbolPeriodErrorEventTimestamp OBJECT-TYPE
    SYNTAX      Integer32
    MAX-ACCESS  read-only
    STATUS      current
    DESCRIPTION
        "This two-octet field indicates the time reference when the event was generated, in terms of 100 ms intervals."
    ::= { sm24tat4xbEthLinkOAMPortEventDetailedStatisticsEntry 15 }

sm24tat4xbStatisticsLocalSymbolPeriodErrorEventWindow OBJECT-TYPE
    SYNTAX      Counter64
    MAX-ACCESS  read-only
    STATUS      current
    DESCRIPTION
        "This eight-octet field indicates the number of symbols in the period."
    ::= { sm24tat4xbEthLinkOAMPortEventDetailedStatisticsEntry 16 }

sm24tat4xbStatisticsLocalSymbolPeriodErrorEventThreshold OBJECT-TYPE
    SYNTAX      Counter64
    MAX-ACCESS  read-only
    STATUS      current
    DESCRIPTION
        "This eight-octet field indicates the number of errored symbols in the period is required to
	    be equal to or greater than in order for the event to be generated."
    ::= { sm24tat4xbEthLinkOAMPortEventDetailedStatisticsEntry 17 }

sm24tat4xbStatisticsLocalSymbolPeriodErrors OBJECT-TYPE
    SYNTAX      Counter64
    MAX-ACCESS  read-only
    STATUS      current
    DESCRIPTION
        "This eight-octet field indicates the number of symbol errors in the period."
    ::= { sm24tat4xbEthLinkOAMPortEventDetailedStatisticsEntry 18 }

sm24tat4xbStatisticsLocalSymbolFramePeriodErrors OBJECT-TYPE
    SYNTAX      Counter64
    MAX-ACCESS  read-only
    STATUS      current
    DESCRIPTION
        "This eight-octet field indicates the sum of symbol errors since the OAM sublayer was reset."
    ::= { sm24tat4xbEthLinkOAMPortEventDetailedStatisticsEntry 19 }

sm24tat4xbStatisticsLocalSymbolFramePeriodErrorEvents OBJECT-TYPE
    SYNTAX      Integer32
    MAX-ACCESS  read-only
    STATUS      current
    DESCRIPTION
        "This four-octet field indicates the number of Errored Symbol Period Event TLVs that
	    have been generated since the OAM sublayer was reset."
    ::= { sm24tat4xbEthLinkOAMPortEventDetailedStatisticsEntry 20 }

sm24tat4xbStatisticsLocalEventSecondsSummaryTimeStamp OBJECT-TYPE
    SYNTAX      Integer32
    MAX-ACCESS  read-only
    STATUS      current
    DESCRIPTION
        "This two-octet field indicates the time reference when the event was generated,
	    in terms of 100 ms intervals, encoded as a 16-bit unsigned integer."
    ::= { sm24tat4xbEthLinkOAMPortEventDetailedStatisticsEntry 21 }

sm24tat4xbStatisticsLocalEventSecondsSummaryWindow OBJECT-TYPE
    SYNTAX      Integer32
    MAX-ACCESS  read-only
    STATUS      current
    DESCRIPTION
        "This two-octet field indicates the duration of the period in terms of 100 ms intervals, encoded as a 16-bit unsigned integer."
    ::= { sm24tat4xbEthLinkOAMPortEventDetailedStatisticsEntry 22 }

sm24tat4xbStatisticsLocalEventSecondsSummaryThreshold OBJECT-TYPE
    SYNTAX      Integer32
    MAX-ACCESS  read-only
    STATUS      current
    DESCRIPTION
        "This two-octet field indicates the number of errored frame seconds in the period is required
	    to be equal to or greater than in order for the event to be generated, encoded as a 16-bit unsigned integer."
    ::= { sm24tat4xbEthLinkOAMPortEventDetailedStatisticsEntry 23 }

sm24tat4xbStatisticsLocalEventSecondsSummaryEvents OBJECT-TYPE
    SYNTAX      Integer32
    MAX-ACCESS  read-only
    STATUS      current
    DESCRIPTION
        "This two-octet field indicates the number of errored frame seconds in the period, encoded as a 16-bit unsigned integer."
    ::= { sm24tat4xbEthLinkOAMPortEventDetailedStatisticsEntry 24 }

sm24tat4xbStatisticsLocalEventSecondsSummaryErrorTotal OBJECT-TYPE
    SYNTAX      Integer32
    MAX-ACCESS  read-only
    STATUS      current
    DESCRIPTION
        "This four-octet field indicates the sum of errored frame seconds that have been detected since the OAM sublayer was reset."
    ::= { sm24tat4xbEthLinkOAMPortEventDetailedStatisticsEntry 25 }

sm24tat4xbStatisticsLocalEventSecondsSummaryEventTotal OBJECT-TYPE
    SYNTAX      Integer32
    MAX-ACCESS  read-only
    STATUS      current
    DESCRIPTION
        "This four-octet field indicates the number of Errored Frame Seconds Summary Event TLVs that
	    have been generated since the OAM sublayer was reset, encoded as a 32bit unsigned integer."
    ::= { sm24tat4xbEthLinkOAMPortEventDetailedStatisticsEntry 26 }

sm24tat4xbStatisticsRemoteFrameErrorEventTimestamp OBJECT-TYPE
    SYNTAX      Integer32
    MAX-ACCESS  read-only
    STATUS      current
    DESCRIPTION
        "This two-octet field indicates the time reference when the event was generated, in terms of 100 ms intervals."
    ::= { sm24tat4xbEthLinkOAMPortEventDetailedStatisticsEntry 27 }

sm24tat4xbStatisticsRemoteFrameErrorEventWindow OBJECT-TYPE
    SYNTAX      Integer32
    MAX-ACCESS  read-only
    STATUS      current
    DESCRIPTION
        "This two-octet field indicates the duration of the period in terms of 100 ms intervals. 1)
	    The default value is one second. 2) The lower bound is one second. 3)
	    The upper bound is one minute."
    ::= { sm24tat4xbEthLinkOAMPortEventDetailedStatisticsEntry 28 }

sm24tat4xbStatisticsRemoteFrameErrorEventThreshold OBJECT-TYPE
    SYNTAX      Integer32
    MAX-ACCESS  read-only
    STATUS      current
    DESCRIPTION
        "This four-octet field indicates the number of detected errored frames in the period is required
	    to be equal to or greater than in order for the event to be generated. 1)
	    The default value is one frame error. 2)
	    The lower bound is zero frame errors. 3)
	    The upper bound is unspecified."
    ::= { sm24tat4xbEthLinkOAMPortEventDetailedStatisticsEntry 29 }

sm24tat4xbStatisticsRemoteFrameErrors OBJECT-TYPE
    SYNTAX      Integer32
    MAX-ACCESS  read-only
    STATUS      current
    DESCRIPTION
        "This four-octet field indicates the number of detected errored frames in the period."
    ::= { sm24tat4xbEthLinkOAMPortEventDetailedStatisticsEntry 30 }

sm24tat4xbStatisticsRemoteTotalFrameErrors OBJECT-TYPE
    SYNTAX      Counter64
    MAX-ACCESS  read-only
    STATUS      current
    DESCRIPTION
        "This eight-octet field indicates the sum of errored frames that have been detected since the OAM sublayer was reset."
    ::= { sm24tat4xbEthLinkOAMPortEventDetailedStatisticsEntry 31 }

sm24tat4xbStatisticsRemoteTotalFrameErrorEvents OBJECT-TYPE
    SYNTAX      Integer32
    MAX-ACCESS  read-only
    STATUS      current
    DESCRIPTION
        "This four-octet field indicates the number of Errored Frame Event TLVs that
	    have been generated since the OAM sublayer was reset."
    ::= { sm24tat4xbEthLinkOAMPortEventDetailedStatisticsEntry 32 }

sm24tat4xbStatisticsRemoteFramePeriodErrorEventTimestamp OBJECT-TYPE
    SYNTAX      Integer32
    MAX-ACCESS  read-only
    STATUS      current
    DESCRIPTION
        "This two-octet field indicates the time reference when the event was generated, in terms of 100 ms intervals."
    ::= { sm24tat4xbEthLinkOAMPortEventDetailedStatisticsEntry 33 }

sm24tat4xbStatisticsRemoteFramePeriodErrorEventWindow OBJECT-TYPE
    SYNTAX      Integer32
    MAX-ACCESS  read-only
    STATUS      current
    DESCRIPTION
        "This four-octet field indicates the duration of period in terms of frames."
    ::= { sm24tat4xbEthLinkOAMPortEventDetailedStatisticsEntry 34 }

sm24tat4xbStatisticsRemoteFramePeriodErrorEventThreshold OBJECT-TYPE
    SYNTAX      Integer32
    MAX-ACCESS  read-only
    STATUS      current
    DESCRIPTION
        "This four-octet field indicates the number of errored frames in the period is required
	    to be equal to or greater than in order for the event to be generated."
    ::= { sm24tat4xbEthLinkOAMPortEventDetailedStatisticsEntry 35 }

sm24tat4xbStatisticsRemoteFramePeriodErrors OBJECT-TYPE
    SYNTAX      Integer32
    MAX-ACCESS  read-only
    STATUS      current
    DESCRIPTION
        "This four-octet field indicates the number of frame errors in the period."
    ::= { sm24tat4xbEthLinkOAMPortEventDetailedStatisticsEntry 36 }

sm24tat4xbStatisticsRemoteTotalFramePeriodErrors OBJECT-TYPE
    SYNTAX      Counter64
    MAX-ACCESS  read-only
    STATUS      current
    DESCRIPTION
        "This eight-octet field indicates the sum of frame errors that have been detected since the OAM sublayer was reset."
    ::= { sm24tat4xbEthLinkOAMPortEventDetailedStatisticsEntry 37 }

sm24tat4xbStatisticsRemoteTotalFramePeriodErrorEvents OBJECT-TYPE
    SYNTAX      Integer32
    MAX-ACCESS  read-only
    STATUS      current
    DESCRIPTION
        "This four-octet field indicates the number of Errored Frame Period Event TLVs
	    that have been generated since the OAM sublayer was reset."
    ::= { sm24tat4xbEthLinkOAMPortEventDetailedStatisticsEntry 38 }

sm24tat4xbStatisticsRemoteSymbolPeriodErrorEventTimestamp OBJECT-TYPE
    SYNTAX      Integer32
    MAX-ACCESS  read-only
    STATUS      current
    DESCRIPTION
        "This two-octet field indicates the time reference when the event was generated, in terms of 100 ms intervals."
    ::= { sm24tat4xbEthLinkOAMPortEventDetailedStatisticsEntry 39 }

sm24tat4xbStatisticsRemoteSymbolPeriodErrorEventWindow OBJECT-TYPE
    SYNTAX      Counter64
    MAX-ACCESS  read-only
    STATUS      current
    DESCRIPTION
        "This eight-octet field indicates the number of symbols in the period."
    ::= { sm24tat4xbEthLinkOAMPortEventDetailedStatisticsEntry 40 }

sm24tat4xbStatisticsRemoteSymbolPeriodErrorEventThreshold OBJECT-TYPE
    SYNTAX      Counter64
    MAX-ACCESS  read-only
    STATUS      current
    DESCRIPTION
        "This eight-octet field indicates the number of errored symbols in the period is required to
	    be equal to or greater than in order for the event to be generated."
    ::= { sm24tat4xbEthLinkOAMPortEventDetailedStatisticsEntry 41 }

sm24tat4xbStatisticsRemoteSymbolPeriodErrors OBJECT-TYPE
    SYNTAX      Counter64
    MAX-ACCESS  read-only
    STATUS      current
    DESCRIPTION
        "This eight-octet field indicates the number of symbol errors in the period."
    ::= { sm24tat4xbEthLinkOAMPortEventDetailedStatisticsEntry 42 }

sm24tat4xbStatisticsRemoteSymbolFramePeriodErrors OBJECT-TYPE
    SYNTAX      Counter64
    MAX-ACCESS  read-only
    STATUS      current
    DESCRIPTION
        "This eight-octet field indicates the sum of symbol errors since the OAM sublayer was reset."
    ::= { sm24tat4xbEthLinkOAMPortEventDetailedStatisticsEntry 43 }

sm24tat4xbStatisticsRemoteSymbolFramePeriodErrorEvents OBJECT-TYPE
    SYNTAX      Integer32
    MAX-ACCESS  read-only
    STATUS      current
    DESCRIPTION
        "This four-octet field indicates the number of Errored Symbol Period Event TLVs that
	    have been generated since the OAM sublayer was reset."
    ::= { sm24tat4xbEthLinkOAMPortEventDetailedStatisticsEntry 44 }

sm24tat4xbStatisticsRemoteEventSecondsSummaryTimeStamp OBJECT-TYPE
    SYNTAX      Integer32
    MAX-ACCESS  read-only
    STATUS      current
    DESCRIPTION
        "This two-octet field indicates the time reference when the event was generated,
	    in terms of 100 ms intervals, encoded as a 16-bit unsigned integer."
    ::= { sm24tat4xbEthLinkOAMPortEventDetailedStatisticsEntry 45 }

sm24tat4xbStatisticsRemoteEventSecondsSummaryWindow OBJECT-TYPE
    SYNTAX      Integer32
    MAX-ACCESS  read-only
    STATUS      current
    DESCRIPTION
        "This two-octet field indicates the duration of the period in terms of 100 ms intervals, encoded as a 16-bit unsigned integer."
    ::= { sm24tat4xbEthLinkOAMPortEventDetailedStatisticsEntry 46 }

sm24tat4xbStatisticsRemoteEventSecondsSummaryThreshold OBJECT-TYPE
    SYNTAX      Integer32
    MAX-ACCESS  read-only
    STATUS      current
    DESCRIPTION
        "This two-octet field indicates the number of errored frame seconds in the period is required
	    to be equal to or greater than in order for the event to be generated, encoded as a 16-bit unsigned integer."
    ::= { sm24tat4xbEthLinkOAMPortEventDetailedStatisticsEntry 47 }

sm24tat4xbStatisticsRemoteEventSecondsSummaryEvents OBJECT-TYPE
    SYNTAX      Integer32
    MAX-ACCESS  read-only
    STATUS      current
    DESCRIPTION
        "This two-octet field indicates the number of errored frame seconds in the period, encoded as a 16-bit unsigned integer."
    ::= { sm24tat4xbEthLinkOAMPortEventDetailedStatisticsEntry 48 }

sm24tat4xbStatisticsRemoteEventSecondsSummaryErrorTotal OBJECT-TYPE
    SYNTAX      Integer32
    MAX-ACCESS  read-only
    STATUS      current
    DESCRIPTION
        "This four-octet field indicates the sum of errored frame seconds that have been detected since the OAM sublayer was reset."
    ::= { sm24tat4xbEthLinkOAMPortEventDetailedStatisticsEntry 49 }

sm24tat4xbStatisticsRemoteEventSecondsSummaryEventTotal OBJECT-TYPE
    SYNTAX      Integer32
    MAX-ACCESS  read-only
    STATUS      current
    DESCRIPTION
        "This four-octet field indicates the number of Errored Frame Seconds Summary Event TLVs that
	    have been generated since the OAM sublayer was reset, encoded as a 32bit unsigned integer."
    ::= { sm24tat4xbEthLinkOAMPortEventDetailedStatisticsEntry 50 }


sm24tat4xbIPMC    OBJECT IDENTIFIER ::= { sm24tat4xbConfiguration 32 }

sm24tat4xbIGMPSnooping    OBJECT IDENTIFIER ::= { sm24tat4xbIPMC 1 }

sm24tat4xbIGMPSnoopingBasicConfigSnoopingEnabled OBJECT-TYPE
    SYNTAX      Integer32(0|1)
    MAX-ACCESS  read-write
    STATUS      current
    DESCRIPTION
        "Snooping Enabled
        0:Disable
        1:Enable"
    ::= {     sm24tat4xbIGMPSnooping 2 }

sm24tat4xbIGMPSnoopingUnregisteredIPMCv4FloodingEnabled OBJECT-TYPE
    SYNTAX      Integer32(0|1)
    MAX-ACCESS  read-write
    STATUS      current
    DESCRIPTION
        "Unregistered IPMCv4 Flooding Enabled
        0:Disable
        1:Enable"
    ::= {     sm24tat4xbIGMPSnooping 3 }

sm24tat4xbIGMPSnoopingBasicConfigIGMPSSMRange OBJECT-TYPE
    SYNTAX      IpAddress
    MAX-ACCESS  read-write
    STATUS      current
    DESCRIPTION
        "IGMP SSM Range
        IPv4 multicast address."
    ::= {     sm24tat4xbIGMPSnooping 4 }

sm24tat4xbIGMPSnoopingBasicConfigIGMPSSMRangeLength OBJECT-TYPE
    SYNTAX      Integer32(4..32)
    MAX-ACCESS  read-write
    STATUS      current
    DESCRIPTION
        "IGMP SSM Range prefix. "
    ::= {     sm24tat4xbIGMPSnooping 5 }

sm24tat4xbIGMPSnoopingBasicConfigLeaveProxyEnabled OBJECT-TYPE
    SYNTAX      Integer32(0|1)
    MAX-ACCESS  read-write
    STATUS      current
    DESCRIPTION
        "Leave Proxy Enabled
        0:Disable
        1:Enable"
    ::= {     sm24tat4xbIGMPSnooping 6 }

sm24tat4xbIGMPSnoopingBasicConfigProxyEnabled OBJECT-TYPE
    SYNTAX      Integer32(0|1)
    MAX-ACCESS  read-write
    STATUS      current
    DESCRIPTION
        "Proxy Enabled
        0:Disable
        1:Enable"
    ::= {     sm24tat4xbIGMPSnooping 7 }



sm24tat4xbIGMPSnoopingPortRelatedTable OBJECT-TYPE
    SYNTAX      SEQUENCE OF SM24TAT4XBIGMPSnoopingPortRelatedEntry
    MAX-ACCESS  not-accessible
    STATUS      current
    DESCRIPTION
        " "
    ::= { sm24tat4xbIGMPSnooping 8 }

sm24tat4xbIGMPSnoopingPortRelatedEntry OBJECT-TYPE
    SYNTAX      SM24TAT4XBIGMPSnoopingPortRelatedEntry
    MAX-ACCESS  not-accessible
    STATUS      current
    DESCRIPTION
        " "
    INDEX    { sm24tat4xbIGMPSnoopingPortRelatedPort  }
    ::= { sm24tat4xbIGMPSnoopingPortRelatedTable 1 }

SM24TAT4XBIGMPSnoopingPortRelatedEntry ::= SEQUENCE {
    sm24tat4xbIGMPSnoopingPortRelatedPort    Integer32,
    sm24tat4xbIGMPSnoopingPortRouterPort    Integer32,
    sm24tat4xbIGMPSnoopingPortFastLeave     Integer32,
    sm24tat4xbIGMPSnoopingPortThrottling    Integer32,
    sm24tat4xbIGMPSnoopingPortFilteringProfile  DisplayString
}

sm24tat4xbIGMPSnoopingPortRelatedPort OBJECT-TYPE
    SYNTAX      Integer32(1..65535)
    MAX-ACCESS  not-accessible
    STATUS      current
    DESCRIPTION
        "Index"
    ::= {     sm24tat4xbIGMPSnoopingPortRelatedEntry 1 }

sm24tat4xbIGMPSnoopingPortRouterPort OBJECT-TYPE
    SYNTAX      Integer32(0|1)
    MAX-ACCESS  read-write
    STATUS      current
    DESCRIPTION
        "Router Port
        0:Disable
        1:Enable"
    ::= {     sm24tat4xbIGMPSnoopingPortRelatedEntry 2 }

sm24tat4xbIGMPSnoopingPortFastLeave OBJECT-TYPE
    SYNTAX      Integer32(0|1)
    MAX-ACCESS  read-write
    STATUS      current
    DESCRIPTION
        "Fast Leave
        0:Disable
        1:Enable"
    ::= {     sm24tat4xbIGMPSnoopingPortRelatedEntry 3 }

sm24tat4xbIGMPSnoopingPortThrottling OBJECT-TYPE
    SYNTAX      Integer32(0..10)
    MAX-ACCESS  read-write
    STATUS      current
    DESCRIPTION
        "Throttling.
        Range: 0:unlimited, 1-10"
    ::= {     sm24tat4xbIGMPSnoopingPortRelatedEntry 4 }

sm24tat4xbIGMPSnoopingPortFilteringProfile OBJECT-TYPE
    SYNTAX      DisplayString
    MAX-ACCESS  read-write
    STATUS      current
    DESCRIPTION
        "Filtering Profile"
    ::= {     sm24tat4xbIGMPSnoopingPortRelatedEntry 5 }

sm24tat4xbIGMPSnoopingVLANConfigTable OBJECT-TYPE
    SYNTAX      SEQUENCE OF SM24TAT4XBIGMPSnoopingVLANConfigEntry
    MAX-ACCESS  not-accessible
    STATUS      current
    DESCRIPTION
        " "
    ::= { sm24tat4xbIGMPSnooping 9 }

sm24tat4xbIGMPSnoopingVLANConfigEntry OBJECT-TYPE
    SYNTAX      SM24TAT4XBIGMPSnoopingVLANConfigEntry
    MAX-ACCESS  not-accessible
    STATUS      current
    DESCRIPTION
        " "
    INDEX    { sm24tat4xbIGMPSnoopingVLANConfigIndex  }
    ::= { sm24tat4xbIGMPSnoopingVLANConfigTable 1 }

SM24TAT4XBIGMPSnoopingVLANConfigEntry ::= SEQUENCE {
    sm24tat4xbIGMPSnoopingVLANConfigIndex        Integer32,
    sm24tat4xbIGMPSnoopingVLANConfigVLANID        Integer32,
    sm24tat4xbIGMPSnoopingVLANConfigSnoopingEnabled  Integer32,
    sm24tat4xbIGMPSnoopingVLANConfigQuerierElection  Integer32,
    sm24tat4xbIGMPSnoopingVLANConfigQuerierAddress    IpAddress,
    sm24tat4xbIGMPSnoopingVLANConfigCompatibility    Integer32,
    sm24tat4xbIGMPSnoopingVLANConfigPRI          Integer32,
    sm24tat4xbIGMPSnoopingVLANConfigRV        Integer32,
    sm24tat4xbIGMPSnoopingVLANConfigQI        Integer32,
    sm24tat4xbIGMPSnoopingVLANConfigQRI          Integer32,
    sm24tat4xbIGMPSnoopingVLANConfigLLQI         Integer32,
    sm24tat4xbIGMPSnoopingVLANConfigURI          Integer32
}

sm24tat4xbIGMPSnoopingVLANConfigIndex OBJECT-TYPE
    SYNTAX      Integer32(1..65535)
    MAX-ACCESS  not-accessible
    STATUS      current
    DESCRIPTION
        "Index"
    ::= {     sm24tat4xbIGMPSnoopingVLANConfigEntry 1 }

sm24tat4xbIGMPSnoopingVLANConfigVLANID OBJECT-TYPE
    SYNTAX      Integer32
    MAX-ACCESS  read-only
    STATUS      current
    DESCRIPTION
        "VLAN ID"
    ::= {     sm24tat4xbIGMPSnoopingVLANConfigEntry 2 }

sm24tat4xbIGMPSnoopingVLANConfigSnoopingEnabled OBJECT-TYPE
    SYNTAX      Integer32(0|1)
    MAX-ACCESS  read-write
    STATUS      current
    DESCRIPTION
        "IGMP Snooping Enabled
        0:Disable
        1:Enable"
    ::= {     sm24tat4xbIGMPSnoopingVLANConfigEntry 3 }

sm24tat4xbIGMPSnoopingVLANConfigQuerierElection OBJECT-TYPE
    SYNTAX      Integer32(0|1)
    MAX-ACCESS  read-write
    STATUS      current
    DESCRIPTION
        "Querier Election
        0:Disable
        1:Enable"
    ::= {     sm24tat4xbIGMPSnoopingVLANConfigEntry 4 }

sm24tat4xbIGMPSnoopingVLANConfigQuerierAddress OBJECT-TYPE
    SYNTAX      IpAddress
    MAX-ACCESS  read-write
    STATUS      current
    DESCRIPTION
        "Querier Address"
    ::= {     sm24tat4xbIGMPSnoopingVLANConfigEntry 5 }

sm24tat4xbIGMPSnoopingVLANConfigCompatibility OBJECT-TYPE
    SYNTAX      Integer32(0..3)
    MAX-ACCESS  read-write
    STATUS      current
    DESCRIPTION
        "Compatibility
        0:IGMP-Auto
        1:Forced IGMPv1
        2:Forced IGMPv2
        3:Forced IGMPv3"
    ::= {     sm24tat4xbIGMPSnoopingVLANConfigEntry 6 }

sm24tat4xbIGMPSnoopingVLANConfigPRI OBJECT-TYPE
    SYNTAX      Integer32(0..7)
    MAX-ACCESS  read-write
    STATUS      current
    DESCRIPTION
        "Priority of Interface.
    "
    ::= {     sm24tat4xbIGMPSnoopingVLANConfigEntry 7 }

sm24tat4xbIGMPSnoopingVLANConfigRV OBJECT-TYPE
    SYNTAX      Integer32(1..255)
    MAX-ACCESS  read-write
    STATUS      current
    DESCRIPTION
        "Robustness Variable."
    ::= {     sm24tat4xbIGMPSnoopingVLANConfigEntry 8 }

sm24tat4xbIGMPSnoopingVLANConfigQI OBJECT-TYPE
    SYNTAX      Integer32(1..31744)
    MAX-ACCESS  read-write
    STATUS      current
    DESCRIPTION
        "Query Interval."
    ::= {     sm24tat4xbIGMPSnoopingVLANConfigEntry 9 }

sm24tat4xbIGMPSnoopingVLANConfigQRI OBJECT-TYPE
    SYNTAX      Integer32(0..31744)
    MAX-ACCESS  read-write
    STATUS      current
    DESCRIPTION
        "Query Response Interval."
    ::= {     sm24tat4xbIGMPSnoopingVLANConfigEntry 10 }

sm24tat4xbIGMPSnoopingVLANConfigLLQI OBJECT-TYPE
    SYNTAX      Integer32(0..31744)
    MAX-ACCESS  read-write
    STATUS      current
    DESCRIPTION
        "Last Member Query Interval."
    ::= {     sm24tat4xbIGMPSnoopingVLANConfigEntry 11 }

sm24tat4xbIGMPSnoopingVLANConfigURI OBJECT-TYPE
    SYNTAX      Integer32(0..31744)
    MAX-ACCESS  read-write
    STATUS      current
    DESCRIPTION
        "Unsolicited Report Interval."
    ::= {     sm24tat4xbIGMPSnoopingVLANConfigEntry 12 }


sm24tat4xbIGMPSnoopingStatusClear OBJECT-TYPE
    SYNTAX      Integer32(0|1)
    MAX-ACCESS  read-write
    STATUS      current
    DESCRIPTION
        "Clears all Statistics counters."
    ::= { sm24tat4xbIGMPSnooping 10 }


sm24tat4xbIGMPSnoopingStatusTable OBJECT-TYPE
    SYNTAX      SEQUENCE OF SM24TAT4XBIGMPSnoopingStatusEntry
    MAX-ACCESS  not-accessible
    STATUS      current
    DESCRIPTION
        " "
    ::= { sm24tat4xbIGMPSnooping 11 }

sm24tat4xbIGMPSnoopingStatusEntry OBJECT-TYPE
    SYNTAX      SM24TAT4XBIGMPSnoopingStatusEntry
    MAX-ACCESS  not-accessible
    STATUS      current
    DESCRIPTION
        " "
    INDEX    { sm24tat4xbIGMPSnoopingStatusIndex  }
    ::= { sm24tat4xbIGMPSnoopingStatusTable 1 }

SM24TAT4XBIGMPSnoopingStatusEntry ::= SEQUENCE {
    sm24tat4xbIGMPSnoopingStatusIndex        Integer32,
    sm24tat4xbIGMPSnoopingStatusVLANID          Integer32,
    sm24tat4xbIGMPSnoopingStatusQuerierVersion      DisplayString,
    sm24tat4xbIGMPSnoopingStatusHostVersion     DisplayString,
    sm24tat4xbIGMPSnoopingStatusQuerierStatus    Integer32,
    sm24tat4xbIGMPSnoopingStatusQueriesTransmitted  Integer32,
    sm24tat4xbIGMPSnoopingStatusQueriesReceived     Integer32,
    sm24tat4xbIGMPSnoopingStatusV1ReportsReceived    Integer32,
    sm24tat4xbIGMPSnoopingStatusV2ReportsReceived    Integer32,
    sm24tat4xbIGMPSnoopingStatusV3ReportsReceived    Integer32,
    sm24tat4xbIGMPSnoopingStatusV2LeavesReceived    Integer32
}

sm24tat4xbIGMPSnoopingStatusIndex OBJECT-TYPE
    SYNTAX      Integer32(1..65535)
    MAX-ACCESS  not-accessible
    STATUS      current
    DESCRIPTION
        "Index"
    ::= {     sm24tat4xbIGMPSnoopingStatusEntry 1 }

sm24tat4xbIGMPSnoopingStatusVLANID OBJECT-TYPE
    SYNTAX      Integer32
    MAX-ACCESS  read-only
    STATUS      current
    DESCRIPTION
        "VLAN ID"
    ::= {     sm24tat4xbIGMPSnoopingStatusEntry 2 }

sm24tat4xbIGMPSnoopingStatusQuerierVersion OBJECT-TYPE
    SYNTAX      DisplayString
    MAX-ACCESS  read-only
    STATUS      current
    DESCRIPTION
        "Querier Version"
    ::= {     sm24tat4xbIGMPSnoopingStatusEntry 3 }

sm24tat4xbIGMPSnoopingStatusHostVersion OBJECT-TYPE
    SYNTAX      DisplayString
    MAX-ACCESS  read-only
    STATUS      current
    DESCRIPTION
        "Host Version"
    ::= {     sm24tat4xbIGMPSnoopingStatusEntry 4 }

sm24tat4xbIGMPSnoopingStatusQuerierStatus OBJECT-TYPE
    SYNTAX      Integer32
    MAX-ACCESS  read-only
    STATUS      current
    DESCRIPTION
        "Querier Status.
        0:Init
        1:Idle
        2:Active"
    ::= {     sm24tat4xbIGMPSnoopingStatusEntry 5 }

sm24tat4xbIGMPSnoopingStatusQueriesTransmitted OBJECT-TYPE
    SYNTAX      Integer32
    MAX-ACCESS  read-only
    STATUS      current
    DESCRIPTION
        "Queries Transmitted."
    ::= {     sm24tat4xbIGMPSnoopingStatusEntry 6 }

sm24tat4xbIGMPSnoopingStatusQueriesReceived OBJECT-TYPE
    SYNTAX      Integer32
    MAX-ACCESS  read-only
    STATUS      current
    DESCRIPTION
        "Queries Received."
    ::= {     sm24tat4xbIGMPSnoopingStatusEntry 7 }

sm24tat4xbIGMPSnoopingStatusV1ReportsReceived OBJECT-TYPE
    SYNTAX      Integer32
    MAX-ACCESS  read-only
    STATUS      current
    DESCRIPTION
        "V1 Reports Received"
    ::= {     sm24tat4xbIGMPSnoopingStatusEntry 8 }

sm24tat4xbIGMPSnoopingStatusV2ReportsReceived OBJECT-TYPE
    SYNTAX      Integer32
    MAX-ACCESS  read-only
    STATUS      current
    DESCRIPTION
        "V2 Reports Received"
    ::= {     sm24tat4xbIGMPSnoopingStatusEntry 9 }

sm24tat4xbIGMPSnoopingStatusV3ReportsReceived OBJECT-TYPE
    SYNTAX      Integer32
    MAX-ACCESS  read-only
    STATUS      current
    DESCRIPTION
        "V3 Reports Received"
    ::= {     sm24tat4xbIGMPSnoopingStatusEntry 10 }

sm24tat4xbIGMPSnoopingStatusV2LeavesReceived OBJECT-TYPE
    SYNTAX      Integer32
    MAX-ACCESS  read-only
    STATUS      current
    DESCRIPTION
        "V2 Leaves Received"
    ::= {     sm24tat4xbIGMPSnoopingStatusEntry 11 }

sm24tat4xbIGMPSnoopingStatusRouterPortTable OBJECT-TYPE
    SYNTAX      SEQUENCE OF SM24TAT4XBIGMPSnoopingStatusRouterPortEntry
    MAX-ACCESS  not-accessible
    STATUS      current
    DESCRIPTION
        " "
    ::= { sm24tat4xbIGMPSnooping 12 }

sm24tat4xbIGMPSnoopingStatusRouterPortEntry OBJECT-TYPE
    SYNTAX      SM24TAT4XBIGMPSnoopingStatusRouterPortEntry
    MAX-ACCESS  not-accessible
    STATUS      current
    DESCRIPTION
        " "
    INDEX    { sm24tat4xbIGMPSnoopingStatusRouterPortIndex  }
    ::= { sm24tat4xbIGMPSnoopingStatusRouterPortTable 1 }

SM24TAT4XBIGMPSnoopingStatusRouterPortEntry ::= SEQUENCE {
    sm24tat4xbIGMPSnoopingStatusRouterPortIndex    Integer32,
    sm24tat4xbIGMPSnoopingStatusRouterPortPort     Integer32
}

sm24tat4xbIGMPSnoopingStatusRouterPortIndex OBJECT-TYPE
    SYNTAX      Integer32(1..65535)
    MAX-ACCESS  not-accessible
    STATUS      current
    DESCRIPTION
        "Index"
    ::= {     sm24tat4xbIGMPSnoopingStatusRouterPortEntry 1 }

sm24tat4xbIGMPSnoopingStatusRouterPortPort OBJECT-TYPE
    SYNTAX      Integer32
    MAX-ACCESS  read-only
    STATUS      current
    DESCRIPTION
        "Switch port number.
        0:DISABLE
        1:IDLE
        2:ACTIVE"
    ::= {     sm24tat4xbIGMPSnoopingStatusRouterPortEntry 2 }



sm24tat4xbIGMPSnoopingGroupInfoTable OBJECT-TYPE
    SYNTAX      SEQUENCE OF SM24TAT4XBIGMPSnoopingGroupInfoEntry
    MAX-ACCESS  not-accessible
    STATUS      current
    DESCRIPTION
        " "
    ::= { sm24tat4xbIGMPSnooping 13 }

sm24tat4xbIGMPSnoopingGroupInfoEntry OBJECT-TYPE
    SYNTAX      SM24TAT4XBIGMPSnoopingGroupInfoEntry
    MAX-ACCESS  not-accessible
    STATUS      current
    DESCRIPTION
        " "
    INDEX    { sm24tat4xbIGMPSnoopingGroupInfoIndex  }
    ::= { sm24tat4xbIGMPSnoopingGroupInfoTable 1 }

SM24TAT4XBIGMPSnoopingGroupInfoEntry ::= SEQUENCE {
    sm24tat4xbIGMPSnoopingGroupInfoIndex    Integer32,
    sm24tat4xbIGMPSnoopingGroupInfoVLANID      Integer32,
    sm24tat4xbIGMPSnoopingGroupInfoGroups      IpAddress,
    sm24tat4xbIGMPSnoopingGroupInfoPortMembers DisplayString
}

sm24tat4xbIGMPSnoopingGroupInfoIndex OBJECT-TYPE
    SYNTAX      Integer32(1..65535)
    MAX-ACCESS  not-accessible
    STATUS      current
    DESCRIPTION
        "Index"
    ::= {     sm24tat4xbIGMPSnoopingGroupInfoEntry 1 }

sm24tat4xbIGMPSnoopingGroupInfoVLANID OBJECT-TYPE
    SYNTAX      Integer32
    MAX-ACCESS  read-only
    STATUS      current
    DESCRIPTION
        "VLAN ID"
    ::= {     sm24tat4xbIGMPSnoopingGroupInfoEntry 2 }

sm24tat4xbIGMPSnoopingGroupInfoGroups OBJECT-TYPE
    SYNTAX      IpAddress
    MAX-ACCESS  read-only
    STATUS      current
    DESCRIPTION
        "Groups"
    ::= {     sm24tat4xbIGMPSnoopingGroupInfoEntry 3 }

sm24tat4xbIGMPSnoopingGroupInfoPortMembers OBJECT-TYPE
    SYNTAX      DisplayString
    MAX-ACCESS  read-only
    STATUS      current
    DESCRIPTION
        "Port Members"
    ::= {     sm24tat4xbIGMPSnoopingGroupInfoEntry 4 }



sm24tat4xbIGMPSFMInfoTable OBJECT-TYPE
    SYNTAX      SEQUENCE OF SM24TAT4XBIGMPSFMInfoEntry
    MAX-ACCESS  not-accessible
    STATUS      current
    DESCRIPTION
        " "
    ::= { sm24tat4xbIGMPSnooping 14 }

sm24tat4xbIGMPSFMInfoEntry OBJECT-TYPE
    SYNTAX      SM24TAT4XBIGMPSFMInfoEntry
    MAX-ACCESS  not-accessible
    STATUS      current
    DESCRIPTION
        " "
    INDEX    { sm24tat4xbIGMPSFMInfoIndex  }
    ::= { sm24tat4xbIGMPSFMInfoTable 1 }

SM24TAT4XBIGMPSFMInfoEntry ::= SEQUENCE {
    sm24tat4xbIGMPSFMInfoIndex        Integer32,
    sm24tat4xbIGMPSFMInfoVLANID        Integer32,
    sm24tat4xbIGMPSFMInfoGroup        IpAddress,
    sm24tat4xbIGMPSFMInfoPort         Integer32,
    sm24tat4xbIGMPSFMInfoMode         Integer32,
    sm24tat4xbIGMPSFMInfoSourceAddress    DisplayString,
    sm24tat4xbIGMPSFMInfoType         Integer32,
    sm24tat4xbIGMPSFMInfoHardwareFilterSwitch Integer32

}

sm24tat4xbIGMPSFMInfoIndex OBJECT-TYPE
    SYNTAX      Integer32(1..65535)
    MAX-ACCESS  not-accessible
    STATUS      current
    DESCRIPTION
        "Index"
    ::= {     sm24tat4xbIGMPSFMInfoEntry 1 }

sm24tat4xbIGMPSFMInfoVLANID OBJECT-TYPE
    SYNTAX      Integer32
    MAX-ACCESS  read-only
    STATUS      current
    DESCRIPTION
        "VLAN ID"
    ::= {     sm24tat4xbIGMPSFMInfoEntry 2 }

sm24tat4xbIGMPSFMInfoGroup OBJECT-TYPE
    SYNTAX      IpAddress
    MAX-ACCESS  read-only
    STATUS      current
    DESCRIPTION
        "Group"
    ::= {     sm24tat4xbIGMPSFMInfoEntry 3 }

sm24tat4xbIGMPSFMInfoPort OBJECT-TYPE
    SYNTAX      Integer32
    MAX-ACCESS  read-only
    STATUS      current
    DESCRIPTION
        "Port"
    ::= {     sm24tat4xbIGMPSFMInfoEntry 4 }

sm24tat4xbIGMPSFMInfoMode OBJECT-TYPE
    SYNTAX      Integer32
    MAX-ACCESS  read-only
    STATUS      current
    DESCRIPTION
        "Mode
        0:Exclude.
        1:Include"
    ::= {     sm24tat4xbIGMPSFMInfoEntry 5 }

sm24tat4xbIGMPSFMInfoSourceAddress OBJECT-TYPE
    SYNTAX      DisplayString
    MAX-ACCESS  read-only
    STATUS      current
    DESCRIPTION
        "Source Adress"
    ::= {     sm24tat4xbIGMPSFMInfoEntry 6 }

sm24tat4xbIGMPSFMInfoType OBJECT-TYPE
    SYNTAX      Integer32
    MAX-ACCESS  read-only
    STATUS      current
    DESCRIPTION
        "Type
        0:Deny
        1:Allow"
    ::= {     sm24tat4xbIGMPSFMInfoEntry 7 }

sm24tat4xbIGMPSFMInfoHardwareFilterSwitch OBJECT-TYPE
    SYNTAX      Integer32
    MAX-ACCESS  read-only
    STATUS      current
    DESCRIPTION
        "Hardware Filter\Switch
        0:No
        1:Yes"
    ::= {     sm24tat4xbIGMPSFMInfoEntry 8 }

sm24tat4xbMLDSnooping    OBJECT IDENTIFIER ::= { sm24tat4xbIPMC 2 }

sm24tat4xbMLDSnoopingBasicConfigSnoopingEnabled OBJECT-TYPE
    SYNTAX      Integer32(0|1)
    MAX-ACCESS  read-write
    STATUS      current
    DESCRIPTION
        "Snooping Enabled
        0:Disable
        1:Enable"
    ::= {     sm24tat4xbMLDSnooping 2 }

sm24tat4xbMLDSnoopingUnregisteredIPMCv6FloodingEnabled OBJECT-TYPE
    SYNTAX      Integer32(0|1)
    MAX-ACCESS  read-write
    STATUS      current
    DESCRIPTION
        "Unregistered IPMCv6 Flooding Enabled
        0:Disable
        1:Enable"
    ::= {     sm24tat4xbMLDSnooping 3 }

sm24tat4xbMLDSnoopingBasicConfigMLDSSMRange OBJECT-TYPE
    SYNTAX      DisplayString
    MAX-ACCESS  read-write
    STATUS      current
    DESCRIPTION
        "MLD SSM Range
        IPv6 multicast address."
    ::= {     sm24tat4xbMLDSnooping 4 }

sm24tat4xbMLDSnoopingBasicConfigMLDSSMRangeLength OBJECT-TYPE
    SYNTAX      Integer32(8..128)
    MAX-ACCESS  read-write
    STATUS      current
    DESCRIPTION
        "MLD SSM Range prefix. "
    ::= {     sm24tat4xbMLDSnooping 5 }

sm24tat4xbMLDSnoopingBasicConfigLeaveProxyEnabled OBJECT-TYPE
    SYNTAX      Integer32(0|1)
    MAX-ACCESS  read-write
    STATUS      current
    DESCRIPTION
        "Leave Proxy Enabled
        0:Disable
        1:Enable"
    ::= {     sm24tat4xbMLDSnooping 6 }

sm24tat4xbMLDSnoopingBasicConfigProxyEnabled OBJECT-TYPE
    SYNTAX      Integer32(0|1)
    MAX-ACCESS  read-write
    STATUS      current
    DESCRIPTION
        "Proxy Enabled
        0:Disable
        1:Enable"
    ::= {     sm24tat4xbMLDSnooping 7 }



sm24tat4xbMLDSnoopingPortRelatedTable OBJECT-TYPE
    SYNTAX      SEQUENCE OF SM24TAT4XBMLDSnoopingPortRelatedEntry
    MAX-ACCESS  not-accessible
    STATUS      current
    DESCRIPTION
        " "
    ::= { sm24tat4xbMLDSnooping 8 }

sm24tat4xbMLDSnoopingPortRelatedEntry OBJECT-TYPE
    SYNTAX      SM24TAT4XBMLDSnoopingPortRelatedEntry
    MAX-ACCESS  not-accessible
    STATUS      current
    DESCRIPTION
        " "
    INDEX    { sm24tat4xbMLDSnoopingPortRelatedPort  }
    ::= { sm24tat4xbMLDSnoopingPortRelatedTable 1 }

SM24TAT4XBMLDSnoopingPortRelatedEntry ::= SEQUENCE {
    sm24tat4xbMLDSnoopingPortRelatedPort    Integer32,
    sm24tat4xbMLDSnoopingPortRouterPort    Integer32,
    sm24tat4xbMLDSnoopingPortFastLeave     Integer32,
    sm24tat4xbMLDSnoopingPortThrottling    Integer32,
    sm24tat4xbMLDSnoopingPortFilteringProfile  DisplayString
}

sm24tat4xbMLDSnoopingPortRelatedPort OBJECT-TYPE
    SYNTAX      Integer32(1..65535)
    MAX-ACCESS  not-accessible
    STATUS      current
    DESCRIPTION
        "Index"
    ::= {     sm24tat4xbMLDSnoopingPortRelatedEntry 1 }

sm24tat4xbMLDSnoopingPortRouterPort OBJECT-TYPE
    SYNTAX      Integer32(0|1)
    MAX-ACCESS  read-write
    STATUS      current
    DESCRIPTION
        "Router Port
        0:Disable
        1:Enable"
    ::= {     sm24tat4xbMLDSnoopingPortRelatedEntry 2 }

sm24tat4xbMLDSnoopingPortFastLeave OBJECT-TYPE
    SYNTAX      Integer32(0|1)
    MAX-ACCESS  read-write
    STATUS      current
    DESCRIPTION
        "Fast Leave
        0:Disable
        1:Enable"
    ::= {     sm24tat4xbMLDSnoopingPortRelatedEntry 3 }

sm24tat4xbMLDSnoopingPortThrottling OBJECT-TYPE
    SYNTAX      Integer32(0..10)
    MAX-ACCESS  read-write
    STATUS      current
    DESCRIPTION
        "Throttling.
        Range: 0:unlimited, 1-10"
    ::= {     sm24tat4xbMLDSnoopingPortRelatedEntry 4 }

sm24tat4xbMLDSnoopingPortFilteringProfile OBJECT-TYPE
    SYNTAX      DisplayString
    MAX-ACCESS  read-write
    STATUS      current
    DESCRIPTION
        "Filtering Profile"
    ::= {     sm24tat4xbMLDSnoopingPortRelatedEntry 5 }


sm24tat4xbMLDSnoopingVLANConfigTable OBJECT-TYPE
    SYNTAX      SEQUENCE OF SM24TAT4XBMLDSnoopingVLANConfigEntry
    MAX-ACCESS  not-accessible
    STATUS      current
    DESCRIPTION
        " "
    ::= { sm24tat4xbMLDSnooping 9 }

sm24tat4xbMLDSnoopingVLANConfigEntry OBJECT-TYPE
    SYNTAX      SM24TAT4XBMLDSnoopingVLANConfigEntry
    MAX-ACCESS  not-accessible
    STATUS      current
    DESCRIPTION
        " "
    INDEX    { sm24tat4xbMLDSnoopingVLANConfigIndex  }
    ::= { sm24tat4xbMLDSnoopingVLANConfigTable 1 }

SM24TAT4XBMLDSnoopingVLANConfigEntry ::= SEQUENCE {
    sm24tat4xbMLDSnoopingVLANConfigIndex        Integer32,
    sm24tat4xbMLDSnoopingVLANConfigVLANID        Integer32,
    sm24tat4xbMLDSnoopingVLANConfigSnoopingEnabled  Integer32,
    sm24tat4xbMLDSnoopingVLANConfigQuerierElection  Integer32,
    sm24tat4xbMLDSnoopingVLANConfigCompatibility    Integer32,
    sm24tat4xbMLDSnoopingVLANConfigPRI          Integer32,
    sm24tat4xbMLDSnoopingVLANConfigRV        Integer32,
    sm24tat4xbMLDSnoopingVLANConfigQI        Integer32,
    sm24tat4xbMLDSnoopingVLANConfigQRI          Integer32,
    sm24tat4xbMLDSnoopingVLANConfigLLQI         Integer32,
    sm24tat4xbMLDSnoopingVLANConfigURI          Integer32
}

sm24tat4xbMLDSnoopingVLANConfigIndex OBJECT-TYPE
    SYNTAX      Integer32(1..65535)
    MAX-ACCESS  not-accessible
    STATUS      current
    DESCRIPTION
        "Index"
    ::= {     sm24tat4xbMLDSnoopingVLANConfigEntry 1 }

sm24tat4xbMLDSnoopingVLANConfigVLANID OBJECT-TYPE
    SYNTAX      Integer32
    MAX-ACCESS  read-only
    STATUS      current
    DESCRIPTION
        "VLAN ID"
    ::= {     sm24tat4xbMLDSnoopingVLANConfigEntry 2 }

sm24tat4xbMLDSnoopingVLANConfigSnoopingEnabled OBJECT-TYPE
    SYNTAX      Integer32(0|1)
    MAX-ACCESS  read-write
    STATUS      current
    DESCRIPTION
        "IGMP Snooping Enabled
        0:Disable
        1:Enable"
    ::= {     sm24tat4xbMLDSnoopingVLANConfigEntry 3 }

sm24tat4xbMLDSnoopingVLANConfigQuerierElection OBJECT-TYPE
    SYNTAX      Integer32(0|1)
    MAX-ACCESS  read-write
    STATUS      current
    DESCRIPTION
        "Querier Election
        0:Disable
        1:Enable"
    ::= {     sm24tat4xbMLDSnoopingVLANConfigEntry 4 }

sm24tat4xbMLDSnoopingVLANConfigCompatibility OBJECT-TYPE
    SYNTAX      Integer32(0..2)
    MAX-ACCESS  read-write
    STATUS      current
    DESCRIPTION
        "Compatibility
        0:MLD-Auto
        1:Forced MLDv1
        2:Forced MLDv2"
    ::= {     sm24tat4xbMLDSnoopingVLANConfigEntry 6 }

sm24tat4xbMLDSnoopingVLANConfigPRI OBJECT-TYPE
    SYNTAX      Integer32(0..7)
    MAX-ACCESS  read-write
    STATUS      current
    DESCRIPTION
        "Priority of Interface.
    "
    ::= {     sm24tat4xbMLDSnoopingVLANConfigEntry 7 }

sm24tat4xbMLDSnoopingVLANConfigRV OBJECT-TYPE
    SYNTAX      Integer32(1..255)
    MAX-ACCESS  read-write
    STATUS      current
    DESCRIPTION
        "Robustness Variable."
    ::= {     sm24tat4xbMLDSnoopingVLANConfigEntry 8 }

sm24tat4xbMLDSnoopingVLANConfigQI OBJECT-TYPE
    SYNTAX      Integer32(1..31744)
    MAX-ACCESS  read-write
    STATUS      current
    DESCRIPTION
        "Query Interval."
    ::= {     sm24tat4xbMLDSnoopingVLANConfigEntry 9 }

sm24tat4xbMLDSnoopingVLANConfigQRI OBJECT-TYPE
    SYNTAX      Integer32(0..31744)
    MAX-ACCESS  read-write
    STATUS      current
    DESCRIPTION
        "Query Response Interval."
    ::= {     sm24tat4xbMLDSnoopingVLANConfigEntry 10 }

sm24tat4xbMLDSnoopingVLANConfigLLQI OBJECT-TYPE
    SYNTAX      Integer32(0..31744)
    MAX-ACCESS  read-write
    STATUS      current
    DESCRIPTION
        "Last Member Query Interval."
    ::= {     sm24tat4xbMLDSnoopingVLANConfigEntry 11 }

sm24tat4xbMLDSnoopingVLANConfigURI OBJECT-TYPE
    SYNTAX      Integer32(0..31744)
    MAX-ACCESS  read-write
    STATUS      current
    DESCRIPTION
        "Unsolicited Report Interval."
    ::= {     sm24tat4xbMLDSnoopingVLANConfigEntry 12 }


sm24tat4xbMLDSnoopingStatusClear OBJECT-TYPE
    SYNTAX      Integer32(0|1)
    MAX-ACCESS  read-write
    STATUS      current
    DESCRIPTION
        "Clears all Statistics counters."
    ::= { sm24tat4xbMLDSnooping 10 }


sm24tat4xbMLDSnoopingStatusTable OBJECT-TYPE
    SYNTAX      SEQUENCE OF SM24TAT4XBMLDSnoopingStatusEntry
    MAX-ACCESS  not-accessible
    STATUS      current
    DESCRIPTION
        " "
    ::= { sm24tat4xbMLDSnooping 11 }

sm24tat4xbMLDSnoopingStatusEntry OBJECT-TYPE
    SYNTAX      SM24TAT4XBMLDSnoopingStatusEntry
    MAX-ACCESS  not-accessible
    STATUS      current
    DESCRIPTION
        " "
    INDEX    { sm24tat4xbMLDSnoopingStatusIndex  }
    ::= { sm24tat4xbMLDSnoopingStatusTable 1 }

SM24TAT4XBMLDSnoopingStatusEntry ::= SEQUENCE {
    sm24tat4xbMLDSnoopingStatusIndex        Integer32,
    sm24tat4xbMLDSnoopingStatusVLANID          Integer32,
    sm24tat4xbMLDSnoopingStatusQuerierVersion      DisplayString,
    sm24tat4xbMLDSnoopingStatusHostVersion     DisplayString,
    sm24tat4xbMLDSnoopingStatusQuerierStatus    Integer32,
    sm24tat4xbMLDSnoopingStatusQueriesTransmitted  Integer32,
    sm24tat4xbMLDSnoopingStatusQueriesReceived     Integer32,
    sm24tat4xbMLDSnoopingStatusV1ReportsReceived    Integer32,
    sm24tat4xbMLDSnoopingStatusV2ReportsReceived    Integer32,
    sm24tat4xbMLDSnoopingStatusV1LeavesReceived    Integer32
}

sm24tat4xbMLDSnoopingStatusIndex OBJECT-TYPE
    SYNTAX      Integer32(1..65535)
    MAX-ACCESS  not-accessible
    STATUS      current
    DESCRIPTION
        "Index"
    ::= {     sm24tat4xbMLDSnoopingStatusEntry 1 }

sm24tat4xbMLDSnoopingStatusVLANID OBJECT-TYPE
    SYNTAX      Integer32
    MAX-ACCESS  read-only
    STATUS      current
    DESCRIPTION
        "VLAN ID"
    ::= {     sm24tat4xbMLDSnoopingStatusEntry 2 }

sm24tat4xbMLDSnoopingStatusQuerierVersion OBJECT-TYPE
    SYNTAX      DisplayString
    MAX-ACCESS  read-only
    STATUS      current
    DESCRIPTION
        "Querier Version"
    ::= {     sm24tat4xbMLDSnoopingStatusEntry 3 }

sm24tat4xbMLDSnoopingStatusHostVersion OBJECT-TYPE
    SYNTAX      DisplayString
    MAX-ACCESS  read-only
    STATUS      current
    DESCRIPTION
        "Host Version"
    ::= {     sm24tat4xbMLDSnoopingStatusEntry 4 }

sm24tat4xbMLDSnoopingStatusQuerierStatus OBJECT-TYPE
    SYNTAX      Integer32
    MAX-ACCESS  read-only
    STATUS      current
    DESCRIPTION
        "Querier Status.
        0:Init
        1:Idle
        2:Active"
    ::= {     sm24tat4xbMLDSnoopingStatusEntry 5 }

sm24tat4xbMLDSnoopingStatusQueriesTransmitted OBJECT-TYPE
    SYNTAX      Integer32
    MAX-ACCESS  read-only
    STATUS      current
    DESCRIPTION
        "Queries Transmitted."
    ::= {     sm24tat4xbMLDSnoopingStatusEntry 6 }

sm24tat4xbMLDSnoopingStatusQueriesReceived OBJECT-TYPE
    SYNTAX      Integer32
    MAX-ACCESS  read-only
    STATUS      current
    DESCRIPTION
        "Queries Received."
    ::= {     sm24tat4xbMLDSnoopingStatusEntry 7 }

sm24tat4xbMLDSnoopingStatusV1ReportsReceived OBJECT-TYPE
    SYNTAX      Integer32
    MAX-ACCESS  read-only
    STATUS      current
    DESCRIPTION
        "V1 Reports Received"
    ::= {     sm24tat4xbMLDSnoopingStatusEntry 8 }

sm24tat4xbMLDSnoopingStatusV2ReportsReceived OBJECT-TYPE
    SYNTAX      Integer32
    MAX-ACCESS  read-only
    STATUS      current
    DESCRIPTION
        "V2 Reports Received"
    ::= {     sm24tat4xbMLDSnoopingStatusEntry 9 }

sm24tat4xbMLDSnoopingStatusV1LeavesReceived OBJECT-TYPE
    SYNTAX      Integer32
    MAX-ACCESS  read-only
    STATUS      current
    DESCRIPTION
        "V1 Leaves Received"
    ::= {     sm24tat4xbMLDSnoopingStatusEntry 11 }

sm24tat4xbMLDSnoopingStatusRouterPortTable OBJECT-TYPE
    SYNTAX      SEQUENCE OF SM24TAT4XBMLDSnoopingStatusRouterPortEntry
    MAX-ACCESS  not-accessible
    STATUS      current
    DESCRIPTION
        " "
    ::= { sm24tat4xbMLDSnooping 12 }

sm24tat4xbMLDSnoopingStatusRouterPortEntry OBJECT-TYPE
    SYNTAX      SM24TAT4XBMLDSnoopingStatusRouterPortEntry
    MAX-ACCESS  not-accessible
    STATUS      current
    DESCRIPTION
        " "
    INDEX    { sm24tat4xbMLDSnoopingStatusRouterPortIndex  }
    ::= { sm24tat4xbMLDSnoopingStatusRouterPortTable 1 }

SM24TAT4XBMLDSnoopingStatusRouterPortEntry ::= SEQUENCE {
    sm24tat4xbMLDSnoopingStatusRouterPortIndex    Integer32,
    sm24tat4xbMLDSnoopingStatusRouterPortPort     Integer32
}

sm24tat4xbMLDSnoopingStatusRouterPortIndex OBJECT-TYPE
    SYNTAX      Integer32(1..65535)
    MAX-ACCESS  not-accessible
    STATUS      current
    DESCRIPTION
        "Index"
    ::= {     sm24tat4xbMLDSnoopingStatusRouterPortEntry 1 }

sm24tat4xbMLDSnoopingStatusRouterPortPort OBJECT-TYPE
    SYNTAX      Integer32
    MAX-ACCESS  read-only
    STATUS      current
    DESCRIPTION
        "Switch port number.
        0:DISABLE
        1:IDLE
        2:ACTIVE"
    ::= {     sm24tat4xbMLDSnoopingStatusRouterPortEntry 2 }


sm24tat4xbMLDSnoopingGroupInfoTable OBJECT-TYPE
    SYNTAX      SEQUENCE OF SM24TAT4XBMLDSnoopingGroupInfoEntry
    MAX-ACCESS  not-accessible
    STATUS      current
    DESCRIPTION
        " "
    ::= { sm24tat4xbMLDSnooping 13 }

sm24tat4xbMLDSnoopingGroupInfoEntry OBJECT-TYPE
    SYNTAX      SM24TAT4XBMLDSnoopingGroupInfoEntry
    MAX-ACCESS  not-accessible
    STATUS      current
    DESCRIPTION
        " "
    INDEX    { sm24tat4xbMLDSnoopingGroupInfoIndex  }
    ::= { sm24tat4xbMLDSnoopingGroupInfoTable 1 }

SM24TAT4XBMLDSnoopingGroupInfoEntry ::= SEQUENCE {
    sm24tat4xbMLDSnoopingGroupInfoIndex    Integer32,
    sm24tat4xbMLDSnoopingGroupInfoVLANID      Integer32,
    sm24tat4xbMLDSnoopingGroupInfoGroups      IpAddress,
    sm24tat4xbMLDSnoopingGroupInfoPortMembers DisplayString
}

sm24tat4xbMLDSnoopingGroupInfoIndex OBJECT-TYPE
    SYNTAX      Integer32(1..65535)
    MAX-ACCESS  not-accessible
    STATUS      current
    DESCRIPTION
        "Index"
    ::= {     sm24tat4xbMLDSnoopingGroupInfoEntry 1 }

sm24tat4xbMLDSnoopingGroupInfoVLANID OBJECT-TYPE
    SYNTAX      Integer32
    MAX-ACCESS  read-only
    STATUS      current
    DESCRIPTION
        "VLAN ID"
    ::= {     sm24tat4xbMLDSnoopingGroupInfoEntry 2 }

sm24tat4xbMLDSnoopingGroupInfoGroups OBJECT-TYPE
    SYNTAX      IpAddress
    MAX-ACCESS  read-only
    STATUS      current
    DESCRIPTION
        "Groups"
    ::= {     sm24tat4xbMLDSnoopingGroupInfoEntry 3 }

sm24tat4xbMLDSnoopingGroupInfoPortMembers OBJECT-TYPE
    SYNTAX      DisplayString
    MAX-ACCESS  read-only
    STATUS      current
    DESCRIPTION
        "Port Members"
    ::= {     sm24tat4xbMLDSnoopingGroupInfoEntry 4 }



sm24tat4xbMLDSFMInfoTable OBJECT-TYPE
    SYNTAX      SEQUENCE OF SM24TAT4XBMLDSFMInfoEntry
    MAX-ACCESS  not-accessible
    STATUS      current
    DESCRIPTION
        " "
    ::= { sm24tat4xbMLDSnooping 14 }

sm24tat4xbMLDSFMInfoEntry OBJECT-TYPE
    SYNTAX      SM24TAT4XBMLDSFMInfoEntry
    MAX-ACCESS  not-accessible
    STATUS      current
    DESCRIPTION
        " "
    INDEX    { sm24tat4xbMLDSFMInfoIndex  }
    ::= { sm24tat4xbMLDSFMInfoTable 1 }

SM24TAT4XBMLDSFMInfoEntry ::= SEQUENCE {
    sm24tat4xbMLDSFMInfoIndex        Integer32,
    sm24tat4xbMLDSFMInfoVLANID        Integer32,
    sm24tat4xbMLDSFMInfoGroup        IpAddress,
    sm24tat4xbMLDSFMInfoPort         Integer32,
    sm24tat4xbMLDSFMInfoMode         Integer32,
    sm24tat4xbMLDSFMInfoSourceAddress    DisplayString,
    sm24tat4xbMLDSFMInfoType         Integer32,
    sm24tat4xbMLDSFMInfoHardwareFilterSwitch Integer32

}

sm24tat4xbMLDSFMInfoIndex OBJECT-TYPE
    SYNTAX      Integer32(1..65535)
    MAX-ACCESS  not-accessible
    STATUS      current
    DESCRIPTION
        "Index"
    ::= {     sm24tat4xbMLDSFMInfoEntry 1 }

sm24tat4xbMLDSFMInfoVLANID OBJECT-TYPE
    SYNTAX      Integer32
    MAX-ACCESS  read-only
    STATUS      current
    DESCRIPTION
        "VLAN ID"
    ::= {     sm24tat4xbMLDSFMInfoEntry 2 }

sm24tat4xbMLDSFMInfoGroup OBJECT-TYPE
    SYNTAX      IpAddress
    MAX-ACCESS  read-only
    STATUS      current
    DESCRIPTION
        "Group"
    ::= {     sm24tat4xbMLDSFMInfoEntry 3 }

sm24tat4xbMLDSFMInfoPort OBJECT-TYPE
    SYNTAX      Integer32
    MAX-ACCESS  read-only
    STATUS      current
    DESCRIPTION
        "Port"
    ::= {     sm24tat4xbMLDSFMInfoEntry 4 }

sm24tat4xbMLDSFMInfoMode OBJECT-TYPE
    SYNTAX      Integer32
    MAX-ACCESS  read-only
    STATUS      current
    DESCRIPTION
        "Mode
        0:Exclude.
        1:Include"
    ::= {     sm24tat4xbMLDSFMInfoEntry 5 }

sm24tat4xbMLDSFMInfoSourceAddress OBJECT-TYPE
    SYNTAX      DisplayString
    MAX-ACCESS  read-only
    STATUS      current
    DESCRIPTION
        "Source Adress"
    ::= {     sm24tat4xbMLDSFMInfoEntry 6 }

sm24tat4xbMLDSFMInfoType OBJECT-TYPE
    SYNTAX      Integer32
    MAX-ACCESS  read-only
    STATUS      current
    DESCRIPTION
        "Type
        0:Deny
        1:Allow"
    ::= {     sm24tat4xbMLDSFMInfoEntry 7 }

sm24tat4xbMLDSFMInfoHardwareFilterSwitch OBJECT-TYPE
    SYNTAX      Integer32
    MAX-ACCESS  read-only
    STATUS      current
    DESCRIPTION
        "Hardware Filter\Switch
        0:No
        1:Yes"
    ::= {     sm24tat4xbMLDSFMInfoEntry 8 }

sm24tat4xbMVR    OBJECT IDENTIFIER ::= { sm24tat4xbConfiguration 33 }

sm24tat4xbMVRConfig    OBJECT IDENTIFIER ::= { sm24tat4xbMVR 1 }

sm24tat4xbMVRConfigMVRMode OBJECT-TYPE
    SYNTAX      Integer32
    MAX-ACCESS  read-write
    STATUS      current
    DESCRIPTION
        "MVR Mode
        0:Disable
        1:Enable"
    ::= { sm24tat4xbMVRConfig 2 }


sm24tat4xbVLANInterfaceSettingTable  OBJECT-TYPE
    SYNTAX      SEQUENCE OF SM24TAT4XBVLANInterfaceSettingEntry
    MAX-ACCESS  not-accessible
    STATUS      current
    DESCRIPTION
        "MVR Config table"
    ::= { sm24tat4xbMVRConfig 3 }

sm24tat4xbVLANInterfaceSettingEntry OBJECT-TYPE
    SYNTAX    SM24TAT4XBVLANInterfaceSettingEntry
    MAX-ACCESS    not-accessible
    STATUS    current
    DESCRIPTION
        "MVR Config table"
    INDEX    { sm24tat4xbVLANInterfaceSettingIndex }
    ::= { sm24tat4xbVLANInterfaceSettingTable 1 }

SM24TAT4XBVLANInterfaceSettingEntry ::=
    SEQUENCE {
    sm24tat4xbVLANInterfaceSettingIndex            Integer32,
    sm24tat4xbVLANInterfaceSettingMVRVID            Integer32,
    sm24tat4xbVLANInterfaceSettingMVRName          DisplayString,
    sm24tat4xbVLANInterfaceSettingIGMPAddress          IpAddress,
    sm24tat4xbVLANInterfaceSettingMode             Integer32,
    sm24tat4xbVLANInterfaceSettingTagging          Integer32,
    sm24tat4xbVLANInterfaceSettingPriority         Integer32,
    sm24tat4xbVLANInterfaceSettingLLQI             Integer32,
    sm24tat4xbVLANInterfaceSettingInterfaceChannelProfile  DisplayString,
    sm24tat4xbVLANInterfaceSettingRowStatus        RowStatus
    }

sm24tat4xbVLANInterfaceSettingIndex OBJECT-TYPE
    SYNTAX      Integer32(1..65535)
    MAX-ACCESS  not-accessible
    STATUS      current
    DESCRIPTION
        "MVR Config index."
    ::= {sm24tat4xbVLANInterfaceSettingEntry 1 }

sm24tat4xbVLANInterfaceSettingMVRVID OBJECT-TYPE
    SYNTAX      Integer32
    MAX-ACCESS  read-create
    STATUS      current
    DESCRIPTION
        "MVR VLAN ID"
    ::= {sm24tat4xbVLANInterfaceSettingEntry 2 }

sm24tat4xbVLANInterfaceSettingMVRName OBJECT-TYPE
    SYNTAX      DisplayString
    MAX-ACCESS  read-create
    STATUS      current
    DESCRIPTION
        "MVR Name. Length:0-16"
    ::= {sm24tat4xbVLANInterfaceSettingEntry 3 }

sm24tat4xbVLANInterfaceSettingIGMPAddress OBJECT-TYPE
    SYNTAX      IpAddress
    MAX-ACCESS  read-create
    STATUS      current
    DESCRIPTION
        "IPv4 IGMP Address"
    ::= {sm24tat4xbVLANInterfaceSettingEntry 4 }

sm24tat4xbVLANInterfaceSettingMode OBJECT-TYPE
    SYNTAX      Integer32
    MAX-ACCESS  read-create
    STATUS      current
    DESCRIPTION
      "Mode.
        0:Dynamic
        1:Compatible"
    ::= {sm24tat4xbVLANInterfaceSettingEntry 5 }

sm24tat4xbVLANInterfaceSettingTagging OBJECT-TYPE
    SYNTAX      Integer32
    MAX-ACCESS  read-create
    STATUS      current
    DESCRIPTION
      "Tagging.
        0:Untagged
        1:Tagged"
    ::= {sm24tat4xbVLANInterfaceSettingEntry 6 }

sm24tat4xbVLANInterfaceSettingPriority OBJECT-TYPE
    SYNTAX      Integer32(0..7)
    MAX-ACCESS  read-create
    STATUS      current
    DESCRIPTION
      "Priority"
    ::= {sm24tat4xbVLANInterfaceSettingEntry 7 }

sm24tat4xbVLANInterfaceSettingLLQI OBJECT-TYPE
    SYNTAX      Integer32(0..31744)
    MAX-ACCESS  read-create
    STATUS      current
    DESCRIPTION
      "LLQI"
    ::= {sm24tat4xbVLANInterfaceSettingEntry 8 }

sm24tat4xbVLANInterfaceSettingInterfaceChannelProfile OBJECT-TYPE
    SYNTAX      DisplayString
    MAX-ACCESS  read-create
    STATUS      current
    DESCRIPTION
      "Interface Channel Profile."
    ::= {sm24tat4xbVLANInterfaceSettingEntry 9 }


sm24tat4xbVLANInterfaceSettingRowStatus OBJECT-TYPE
    SYNTAX      RowStatus
    MAX-ACCESS  read-create
    STATUS      current
    DESCRIPTION
        "Row Status."
    ::= {sm24tat4xbVLANInterfaceSettingEntry 10 }

sm24tat4xbMVRVIDIndex OBJECT-TYPE
    SYNTAX      Integer32
    MAX-ACCESS  read-write
    STATUS      current
    DESCRIPTION
        "Set VIDIndex before use VLANInterfaceSettingPortRoleTable table."
    ::= { sm24tat4xbMVRConfig 4 }

sm24tat4xbVLANInterfaceSettingPortRoleTable  OBJECT-TYPE
    SYNTAX      SEQUENCE OF SM24TAT4XBVLANInterfaceSettingPortRoleEntry
    MAX-ACCESS  not-accessible
    STATUS      current
    DESCRIPTION
        "VLAN Interface Setting Port Role table"
    ::= { sm24tat4xbMVRConfig 5 }

sm24tat4xbVLANInterfaceSettingPortRoleEntry OBJECT-TYPE
    SYNTAX    SM24TAT4XBVLANInterfaceSettingPortRoleEntry
    MAX-ACCESS    not-accessible
    STATUS    current
    DESCRIPTION
        "VLAN Interface Setting Port Role table"
    INDEX    { sm24tat4xbVLANInterfaceSettingPortRoleIndex }
    ::= { sm24tat4xbVLANInterfaceSettingPortRoleTable 1 }

SM24TAT4XBVLANInterfaceSettingPortRoleEntry ::=
    SEQUENCE {
    sm24tat4xbVLANInterfaceSettingPortRoleIndex    Integer32,
    sm24tat4xbVLANInterfaceSettingPortRolePort    Integer32
    }

sm24tat4xbVLANInterfaceSettingPortRoleIndex OBJECT-TYPE
    SYNTAX      Integer32(1..65535)
    MAX-ACCESS  not-accessible
    STATUS      current
    DESCRIPTION
        "VLAN Interface Setting Port Role index."
    ::= {sm24tat4xbVLANInterfaceSettingPortRoleEntry 1 }

sm24tat4xbVLANInterfaceSettingPortRolePort OBJECT-TYPE
    SYNTAX      Integer32(0..2)
    MAX-ACCESS  read-write
    STATUS      current
    DESCRIPTION
        "Port Role.
        0:Inactive
        1:Source
        2:Receiver"
    ::= {sm24tat4xbVLANInterfaceSettingPortRoleEntry 2 }



sm24tat4xbImmediateLeaveSettingTable  OBJECT-TYPE
    SYNTAX      SEQUENCE OF SM24TAT4XBImmediateLeaveSettingEntry
    MAX-ACCESS  not-accessible
    STATUS      current
    DESCRIPTION
        "Immediate Leave Setting table"
    ::= { sm24tat4xbMVRConfig 6 }

sm24tat4xbImmediateLeaveSettingEntry OBJECT-TYPE
    SYNTAX    SM24TAT4XBImmediateLeaveSettingEntry
    MAX-ACCESS    not-accessible
    STATUS    current
    DESCRIPTION
        "Immediate Leave Setting table"
    INDEX    { sm24tat4xbImmediateLeaveSettingPort }
    ::= { sm24tat4xbImmediateLeaveSettingTable 1 }

SM24TAT4XBImmediateLeaveSettingEntry ::=
    SEQUENCE {
    sm24tat4xbImmediateLeaveSettingPort        Integer32,
    sm24tat4xbImmediateLeaveSettingImmediateLeave  Integer32
    }

sm24tat4xbImmediateLeaveSettingPort OBJECT-TYPE
    SYNTAX      Integer32(1..65535)
    MAX-ACCESS  not-accessible
    STATUS      current
    DESCRIPTION
        "Immediate Leave Setting index."
    ::= {sm24tat4xbImmediateLeaveSettingEntry 1 }

sm24tat4xbImmediateLeaveSettingImmediateLeave OBJECT-TYPE
    SYNTAX      Integer32(0|1)
    MAX-ACCESS  read-write
    STATUS      current
    DESCRIPTION
      "Immediate Leave
        0:Disable
        1:Enable"
    ::= {sm24tat4xbImmediateLeaveSettingEntry 2 }


sm24tat4xbStatistics    OBJECT IDENTIFIER ::= { sm24tat4xbMVR 2 }

sm24tat4xbMVRStatisticsClear OBJECT-TYPE
    SYNTAX      Integer32
    MAX-ACCESS  read-write
    STATUS      current
    DESCRIPTION
        "Statistics Clear.
        1:Clear"
    ::= { sm24tat4xbStatistics 2 }

sm24tat4xbMVRStatisticsTable OBJECT-TYPE
    SYNTAX      SEQUENCE OF SM24TAT4XBMVRStatisticsEntry
    MAX-ACCESS  not-accessible
    STATUS      current
    DESCRIPTION
        " "
    ::= { sm24tat4xbStatistics 3 }

sm24tat4xbMVRStatisticsEntry OBJECT-TYPE
    SYNTAX      SM24TAT4XBMVRStatisticsEntry
    MAX-ACCESS  not-accessible
    STATUS      current
    DESCRIPTION
        " "
    INDEX    { sm24tat4xbMVRStatisticsIndex  }
    ::= { sm24tat4xbMVRStatisticsTable 1 }

SM24TAT4XBMVRStatisticsEntry ::= SEQUENCE {
    sm24tat4xbMVRStatisticsIndex            Integer32,
    sm24tat4xbMVRStatisticsVLANID              Integer32,
    sm24tat4xbMVRStatisticsIGMPMLDQueriesReceived      DisplayString,
    sm24tat4xbMVRStatisticsIGMPMLDQueriesTransmitted    DisplayString,
    sm24tat4xbMVRStatisticsIGMPv1JoinsReceived     DisplayString,
    sm24tat4xbMVRStatisticsIGMPv2MLDv1ReportsReceived  DisplayString,
    sm24tat4xbMVRStatisticsIGMPv3MLDv2ReportsReceived  DisplayString,
    sm24tat4xbMVRStatisticsIGMPv2MLDv1LeavesReceived    DisplayString
}

sm24tat4xbMVRStatisticsIndex OBJECT-TYPE
    SYNTAX      Integer32(1..65535)
    MAX-ACCESS  not-accessible
    STATUS      current
    DESCRIPTION
        "Index"
    ::= {     sm24tat4xbMVRStatisticsEntry 1 }

sm24tat4xbMVRStatisticsVLANID OBJECT-TYPE
    SYNTAX      Integer32
    MAX-ACCESS  read-only
    STATUS      current
    DESCRIPTION
        "VLAN ID"
    ::= {     sm24tat4xbMVRStatisticsEntry 2 }

sm24tat4xbMVRStatisticsIGMPMLDQueriesReceived OBJECT-TYPE
    SYNTAX      DisplayString
    MAX-ACCESS  read-only
    STATUS      current
    DESCRIPTION
        "IGMP/MLD Queries Received"
    ::= {     sm24tat4xbMVRStatisticsEntry 3 }

sm24tat4xbMVRStatisticsIGMPMLDQueriesTransmitted OBJECT-TYPE
    SYNTAX      DisplayString
    MAX-ACCESS  read-only
    STATUS      current
    DESCRIPTION
        "IGMP/MLD Queries Transmitted"
    ::= {     sm24tat4xbMVRStatisticsEntry 4 }

sm24tat4xbMVRStatisticsIGMPv1JoinsReceived OBJECT-TYPE
    SYNTAX      DisplayString
    MAX-ACCESS  read-only
    STATUS      current
    DESCRIPTION
        "IGMPv1 Joins Received"
    ::= {     sm24tat4xbMVRStatisticsEntry 5 }

sm24tat4xbMVRStatisticsIGMPv2MLDv1ReportsReceived OBJECT-TYPE
    SYNTAX      DisplayString
    MAX-ACCESS  read-only
    STATUS      current
    DESCRIPTION
        "IGMPv2/MLDv1 Reports Received"
    ::= {     sm24tat4xbMVRStatisticsEntry 6 }

sm24tat4xbMVRStatisticsIGMPv3MLDv2ReportsReceived OBJECT-TYPE
    SYNTAX      DisplayString
    MAX-ACCESS  read-only
    STATUS      current
    DESCRIPTION
        "IGMPv3/MLDv2 Reports Received"
    ::= {     sm24tat4xbMVRStatisticsEntry 7 }

sm24tat4xbMVRStatisticsIGMPv2MLDv1LeavesReceived OBJECT-TYPE
    SYNTAX      DisplayString
    MAX-ACCESS  read-only
    STATUS      current
    DESCRIPTION
        "IGMPv2/MLDv1 Leaves Received"
    ::= {     sm24tat4xbMVRStatisticsEntry 8 }


sm24tat4xbGroupInformation  OBJECT IDENTIFIER ::= { sm24tat4xbMVR 3 }

sm24tat4xbMVRGroupInfoTable OBJECT-TYPE
    SYNTAX      SEQUENCE OF SM24TAT4XBMVRGroupInfoEntry
    MAX-ACCESS  not-accessible
    STATUS      current
    DESCRIPTION
        " "
    ::= { sm24tat4xbGroupInformation 1 }

sm24tat4xbMVRGroupInfoEntry OBJECT-TYPE
    SYNTAX      SM24TAT4XBMVRGroupInfoEntry
    MAX-ACCESS  not-accessible
    STATUS      current
    DESCRIPTION
        " "
    INDEX    { sm24tat4xbMVRGroupInfoIndex  }
    ::= { sm24tat4xbMVRGroupInfoTable 1 }

SM24TAT4XBMVRGroupInfoEntry ::= SEQUENCE {
    sm24tat4xbMVRGroupInfoIndex    Integer32,
    sm24tat4xbMVRGroupInfoVLANID      Integer32,
    sm24tat4xbMVRGroupInfoGroups      DisplayString,
    sm24tat4xbMVRGroupInfoPortMembers DisplayString
}

sm24tat4xbMVRGroupInfoIndex OBJECT-TYPE
    SYNTAX      Integer32(1..65535)
    MAX-ACCESS  not-accessible
    STATUS      current
    DESCRIPTION
        "Index"
    ::= {     sm24tat4xbMVRGroupInfoEntry 1 }

sm24tat4xbMVRGroupInfoVLANID OBJECT-TYPE
    SYNTAX      Integer32
    MAX-ACCESS  read-only
    STATUS      current
    DESCRIPTION
        "VLAN ID"
    ::= {     sm24tat4xbMVRGroupInfoEntry 2 }

sm24tat4xbMVRGroupInfoGroups OBJECT-TYPE
    SYNTAX      DisplayString
    MAX-ACCESS  read-only
    STATUS      current
    DESCRIPTION
        "Groups"
    ::= {     sm24tat4xbMVRGroupInfoEntry 3 }

sm24tat4xbMVRGroupInfoPortMembers OBJECT-TYPE
    SYNTAX      DisplayString
    MAX-ACCESS  read-only
    STATUS      current
    DESCRIPTION
        "Port Members"
    ::= {     sm24tat4xbMVRGroupInfoEntry 4 }

sm24tat4xbMVRSFMInformation  OBJECT IDENTIFIER ::= { sm24tat4xbMVR 4 }

sm24tat4xbMVRSFMInfoTable OBJECT-TYPE
    SYNTAX      SEQUENCE OF SM24TAT4XBMVRSFMInfoEntry
    MAX-ACCESS  not-accessible
    STATUS      current
    DESCRIPTION
        " "
    ::= { sm24tat4xbMVRSFMInformation 2 }

sm24tat4xbMVRSFMInfoEntry OBJECT-TYPE
    SYNTAX      SM24TAT4XBMVRSFMInfoEntry
    MAX-ACCESS  not-accessible
    STATUS      current
    DESCRIPTION
        " "
    INDEX    { sm24tat4xbMVRSFMInfoIndex  }
    ::= { sm24tat4xbMVRSFMInfoTable 1 }

SM24TAT4XBMVRSFMInfoEntry ::= SEQUENCE {
    sm24tat4xbMVRSFMInfoIndex        Integer32,
    sm24tat4xbMVRSFMInfoVLANID        Integer32,
    sm24tat4xbMVRSFMInfoGroup        DisplayString,
    sm24tat4xbMVRSFMInfoPort         Integer32,
    sm24tat4xbMVRSFMInfoMode         Integer32,
    sm24tat4xbMVRSFMInfoSourceAddress    DisplayString,
    sm24tat4xbMVRSFMInfoType         Integer32,
    sm24tat4xbMVRSFMInfoHardwareFilterSwitch Integer32

}

sm24tat4xbMVRSFMInfoIndex OBJECT-TYPE
    SYNTAX      Integer32(1..65535)
    MAX-ACCESS  not-accessible
    STATUS      current
    DESCRIPTION
        "Index"
    ::= {     sm24tat4xbMVRSFMInfoEntry 1 }

sm24tat4xbMVRSFMInfoVLANID OBJECT-TYPE
    SYNTAX      Integer32
    MAX-ACCESS  read-only
    STATUS      current
    DESCRIPTION
        "VLAN ID"
    ::= {     sm24tat4xbMVRSFMInfoEntry 2 }

sm24tat4xbMVRSFMInfoGroup OBJECT-TYPE
    SYNTAX      DisplayString
    MAX-ACCESS  read-only
    STATUS      current
    DESCRIPTION
        "Group"
    ::= {     sm24tat4xbMVRSFMInfoEntry 3 }

sm24tat4xbMVRSFMInfoPort OBJECT-TYPE
    SYNTAX      Integer32
    MAX-ACCESS  read-only
    STATUS      current
    DESCRIPTION
        "Port"
    ::= {     sm24tat4xbMVRSFMInfoEntry 4 }

sm24tat4xbMVRSFMInfoMode OBJECT-TYPE
    SYNTAX      Integer32
    MAX-ACCESS  read-only
    STATUS      current
    DESCRIPTION
        "Mode
        0:Exclude.
        1:Include"
    ::= {     sm24tat4xbMVRSFMInfoEntry 5 }

sm24tat4xbMVRSFMInfoSourceAddress OBJECT-TYPE
    SYNTAX      DisplayString
    MAX-ACCESS  read-only
    STATUS      current
    DESCRIPTION
        "Source Adress"
    ::= {     sm24tat4xbMVRSFMInfoEntry 6 }

sm24tat4xbMVRSFMInfoType OBJECT-TYPE
    SYNTAX      Integer32
    MAX-ACCESS  read-only
    STATUS      current
    DESCRIPTION
        "Type
        0:Deny
        1:Allow"
    ::= {     sm24tat4xbMVRSFMInfoEntry 7 }

sm24tat4xbMVRSFMInfoHardwareFilterSwitch OBJECT-TYPE
    SYNTAX      Integer32
    MAX-ACCESS  read-only
    STATUS      current
    DESCRIPTION
        "Hardware Filter\Switch
        0:No
        1:Yes"
    ::= {     sm24tat4xbMVRSFMInfoEntry 8 }


sm24tat4xbIPMCLIB    OBJECT IDENTIFIER ::= { sm24tat4xbConfiguration 34 }

sm24tat4xbMulticastFilteringProfileMode OBJECT-TYPE
    SYNTAX      Integer32
    MAX-ACCESS  read-write
    STATUS      current
    DESCRIPTION
        "Multicast Filtering Profile Mode.
        0:Disable
        1:Enable"
    ::= {     sm24tat4xbIPMCLIB 1 }


sm24tat4xbMulticastFilteringProfileSettingTable  OBJECT-TYPE
    SYNTAX      SEQUENCE OF SM24TAT4XBMulticastFilteringProfileSettingEntry
    MAX-ACCESS  not-accessible
    STATUS      current
    DESCRIPTION
        "Multicast Filtering Profile Setting table"
    ::= { sm24tat4xbIPMCLIB 2 }

sm24tat4xbMulticastFilteringProfileSettingEntry OBJECT-TYPE
    SYNTAX    SM24TAT4XBMulticastFilteringProfileSettingEntry
    MAX-ACCESS    not-accessible
    STATUS    current
    DESCRIPTION
        "Multicast Filtering Profile Setting table."
    INDEX    { sm24tat4xbMulticastFilteringProfileSettingIndex }
    ::= { sm24tat4xbMulticastFilteringProfileSettingTable 1 }

SM24TAT4XBMulticastFilteringProfileSettingEntry ::=
    SEQUENCE {
    sm24tat4xbMulticastFilteringProfileSettingIndex        Integer32,
    sm24tat4xbMulticastFilteringProfileSettingProfileName     DisplayString,
    sm24tat4xbMulticastFilteringProfileSettingProfileDescription  DisplayString,
    sm24tat4xbMulticastFilteringProfileSettingRowStatus        RowStatus
    }

sm24tat4xbMulticastFilteringProfileSettingIndex OBJECT-TYPE
    SYNTAX      Integer32(1..65535)
    MAX-ACCESS  not-accessible
    STATUS      current
    DESCRIPTION
        "Multicast Filtering Profile Setting index."
    ::= {sm24tat4xbMulticastFilteringProfileSettingEntry 1 }


sm24tat4xbMulticastFilteringProfileSettingProfileName OBJECT-TYPE
    SYNTAX      DisplayString
    MAX-ACCESS  read-create
    STATUS      current
    DESCRIPTION
        "Profile Name. Length:1-16"
    ::= {sm24tat4xbMulticastFilteringProfileSettingEntry 2 }

sm24tat4xbMulticastFilteringProfileSettingProfileDescription OBJECT-TYPE
    SYNTAX      DisplayString
    MAX-ACCESS  read-create
    STATUS      current
    DESCRIPTION
        "Profile Description. Length:0-64"
    ::= {sm24tat4xbMulticastFilteringProfileSettingEntry 3 }

sm24tat4xbMulticastFilteringProfileSettingRowStatus OBJECT-TYPE
    SYNTAX      RowStatus
    MAX-ACCESS  read-create
    STATUS      current
    DESCRIPTION
        "Row Status."
    ::= {sm24tat4xbMulticastFilteringProfileSettingEntry 4 }



sm24tat4xbMulticastFilterProfRuleSettingsProfileNameIndex OBJECT-TYPE
    SYNTAX      DisplayString
    MAX-ACCESS  read-write
    STATUS      current
    DESCRIPTION
        "Set this Profile Name value before use MulticastFilteringProfileRuleSettingsTable table"
    ::= {     sm24tat4xbIPMCLIB 3 }



sm24tat4xbMulticastFilteringProfileRuleSettingsTable  OBJECT-TYPE
    SYNTAX      SEQUENCE OF SM24TAT4XBMulticastFilteringProfileRuleSettingsEntry
    MAX-ACCESS  not-accessible
    STATUS      current
    DESCRIPTION
        "Multicast Filtering Profile Rule Setting table"
    ::= { sm24tat4xbIPMCLIB 4 }

sm24tat4xbMulticastFilteringProfileRuleSettingsEntry OBJECT-TYPE
    SYNTAX    SM24TAT4XBMulticastFilteringProfileRuleSettingsEntry
    MAX-ACCESS    not-accessible
    STATUS    current
    DESCRIPTION
        "Multicast Filtering Profile Rule Setting table."
    INDEX    { sm24tat4xbMulticastFilteringProfileRuleSettingsIndex }
    ::= { sm24tat4xbMulticastFilteringProfileRuleSettingsTable 1 }

SM24TAT4XBMulticastFilteringProfileRuleSettingsEntry ::=
    SEQUENCE {
    sm24tat4xbMulticastFilteringProfileRuleSettingsTableIndex      Integer32,
    sm24tat4xbMulticastFilteringProfileRuleSettingsProfileName     DisplayString,
    sm24tat4xbMulticastFilteringProfileRuleSettingsIndex        Integer32,
    sm24tat4xbMulticastFilteringProfileRuleSettingsEntryName        DisplayString,
    sm24tat4xbMulticastFilteringProfileRuleSettingsAddressRange    DisplayString,
    sm24tat4xbMulticastFilteringProfileRuleSettingsAction          Integer32,
    sm24tat4xbMulticastFilteringProfileRuleSettingsLog         Integer32,
    sm24tat4xbMulticastFilteringProfileRuleSettingsRowStatus        RowStatus
    }

sm24tat4xbMulticastFilteringProfileRuleSettingsTableIndex OBJECT-TYPE
    SYNTAX      Integer32
    MAX-ACCESS  not-accessible
    STATUS      current
    DESCRIPTION
        "Multicast Filtering Profile Rule Setting index."
    ::= {sm24tat4xbMulticastFilteringProfileRuleSettingsEntry 1 }


sm24tat4xbMulticastFilteringProfileRuleSettingsProfileName OBJECT-TYPE
    SYNTAX      DisplayString
    MAX-ACCESS  read-only
    STATUS      current
    DESCRIPTION
        "Profile Name"
    ::= {sm24tat4xbMulticastFilteringProfileRuleSettingsEntry 2 }

sm24tat4xbMulticastFilteringProfileRuleSettingsIndex OBJECT-TYPE
    SYNTAX      Integer32(1..65535)
    MAX-ACCESS  read-only
    STATUS      current
    DESCRIPTION
        "Index"
    ::= {sm24tat4xbMulticastFilteringProfileRuleSettingsEntry 3 }

sm24tat4xbMulticastFilteringProfileRuleSettingsEntryName OBJECT-TYPE
    SYNTAX      DisplayString
    MAX-ACCESS  read-create
    STATUS      current
    DESCRIPTION
        "Entry Name, Length: 1-16"
    ::= {sm24tat4xbMulticastFilteringProfileRuleSettingsEntry 4 }

sm24tat4xbMulticastFilteringProfileRuleSettingsAddressRange OBJECT-TYPE
    SYNTAX      DisplayString
    MAX-ACCESS  read-only
    STATUS      current
    DESCRIPTION
        "Address Range"
    ::= {sm24tat4xbMulticastFilteringProfileRuleSettingsEntry 5 }


sm24tat4xbMulticastFilteringProfileRuleSettingsAction OBJECT-TYPE
    SYNTAX      Integer32
    MAX-ACCESS  read-create
    STATUS      current
    DESCRIPTION
        "0:Deny
        1:Permit"
    ::= {sm24tat4xbMulticastFilteringProfileRuleSettingsEntry 6 }

sm24tat4xbMulticastFilteringProfileRuleSettingsLog OBJECT-TYPE
    SYNTAX      Integer32
    MAX-ACCESS  read-create
    STATUS      current
    DESCRIPTION
        "0:Disable
        1:Enable"
    ::= {sm24tat4xbMulticastFilteringProfileRuleSettingsEntry 7 }


sm24tat4xbMulticastFilteringProfileRuleSettingsRowStatus OBJECT-TYPE
    SYNTAX      RowStatus
    MAX-ACCESS  read-create
    STATUS      current
    DESCRIPTION
        "Row Status."
    ::= {sm24tat4xbMulticastFilteringProfileRuleSettingsEntry 8 }


sm24tat4xbMulticastFilteringProfileAddressConfigTable  OBJECT-TYPE
    SYNTAX      SEQUENCE OF SM24TAT4XBMulticastFilteringProfileAddressConfigEntry
    MAX-ACCESS  not-accessible
    STATUS      current
    DESCRIPTION
        "Multicast Filtering Profile Address Config table"
    ::= { sm24tat4xbIPMCLIB 5 }

sm24tat4xbMulticastFilteringProfileAddressConfigEntry OBJECT-TYPE
    SYNTAX    SM24TAT4XBMulticastFilteringProfileAddressConfigEntry
    MAX-ACCESS    not-accessible
    STATUS    current
    DESCRIPTION
        "Multicast Filtering Profile Address Config table."
    INDEX    { sm24tat4xbMulticastFilteringProfileAddressConfigTableIndex }
    ::= { sm24tat4xbMulticastFilteringProfileAddressConfigTable 1 }

SM24TAT4XBMulticastFilteringProfileAddressConfigEntry ::=
    SEQUENCE {
    sm24tat4xbMulticastFilteringProfileAddressConfigTableIndex     Integer32,
    sm24tat4xbMulticastFilteringProfileAddressConfigEntryName      DisplayString,
    sm24tat4xbMulticastFilteringProfileAddressConfigStartAddress    DisplayString,
    sm24tat4xbMulticastFilteringProfileAddressConfigEndAddress     DisplayString,
    sm24tat4xbMulticastFilteringProfileAddressConfigRowStatus      RowStatus
    }

sm24tat4xbMulticastFilteringProfileAddressConfigTableIndex OBJECT-TYPE
    SYNTAX      Integer32(1..65535)
    MAX-ACCESS  not-accessible
    STATUS      current
    DESCRIPTION
        "Multicast Filtering Profile Address Config index."
    ::= {sm24tat4xbMulticastFilteringProfileAddressConfigEntry 1 }


sm24tat4xbMulticastFilteringProfileAddressConfigEntryName OBJECT-TYPE
    SYNTAX      DisplayString
    MAX-ACCESS  read-create
    STATUS      current
    DESCRIPTION
        "Entry Name, Length: 1-16"
    ::= {sm24tat4xbMulticastFilteringProfileAddressConfigEntry 2 }

sm24tat4xbMulticastFilteringProfileAddressConfigStartAddress OBJECT-TYPE
    SYNTAX      DisplayString
    MAX-ACCESS  read-create
    STATUS      current
    DESCRIPTION
        "IPv4/IPv6 Multicast Group Address"
    ::= {sm24tat4xbMulticastFilteringProfileAddressConfigEntry 3 }

sm24tat4xbMulticastFilteringProfileAddressConfigEndAddress OBJECT-TYPE
    SYNTAX      DisplayString
    MAX-ACCESS  read-create
    STATUS      current
    DESCRIPTION
        "IPv4/IPv6 Multicast Group Address"
    ::= {sm24tat4xbMulticastFilteringProfileAddressConfigEntry 4 }

sm24tat4xbMulticastFilteringProfileAddressConfigRowStatus OBJECT-TYPE
    SYNTAX      RowStatus
    MAX-ACCESS  read-create
    STATUS      current
    DESCRIPTION
        "Row Status."
    ::= {sm24tat4xbMulticastFilteringProfileAddressConfigEntry 5 }

sm24tat4xbEEE    OBJECT IDENTIFIER ::= { sm24tat4xbConfiguration 35 }

sm24tat4xbPortPowerSavings    OBJECT IDENTIFIER ::= { sm24tat4xbEEE 1 }

sm24tat4xbEnergyEfficientEthernetConfigTable OBJECT-TYPE
    SYNTAX      SEQUENCE OF SM24TAT4XBEnergyEfficientEthernetConfigEntry
    MAX-ACCESS  not-accessible
    STATUS      current
    DESCRIPTION
        " "
    ::= { sm24tat4xbPortPowerSavings 2 }

sm24tat4xbEnergyEfficientEthernetConfigEntry OBJECT-TYPE
    SYNTAX      SM24TAT4XBEnergyEfficientEthernetConfigEntry
    MAX-ACCESS  not-accessible
    STATUS      current
    DESCRIPTION
        " "
    INDEX    { sm24tat4xbEnergyEfficientEthernetConfigPort  }
    ::= { sm24tat4xbEnergyEfficientEthernetConfigTable 1 }

SM24TAT4XBEnergyEfficientEthernetConfigEntry ::= SEQUENCE {
    sm24tat4xbEnergyEfficientEthernetConfigPort        Integer32,
    sm24tat4xbEnergyEfficientEthernetConfigPortConfig     Integer32
}

sm24tat4xbEnergyEfficientEthernetConfigPort OBJECT-TYPE
    SYNTAX      Integer32(1..65535)
    MAX-ACCESS  not-accessible
    STATUS      current
    DESCRIPTION
        "Index"
    ::= { sm24tat4xbEnergyEfficientEthernetConfigEntry 1 }

sm24tat4xbEnergyEfficientEthernetConfigPortConfig OBJECT-TYPE
    SYNTAX      Integer32
    MAX-ACCESS  read-write
    STATUS      current
    DESCRIPTION
        "Controls whether EEE is enabled for this port.
        0:Disable
        1:Enable"
    ::= { sm24tat4xbEnergyEfficientEthernetConfigEntry 2 }

-- =======================================================================================================================

sm24tat4xbAggregation    OBJECT IDENTIFIER ::= { sm24tat4xbConfiguration 36 }

sm24tat4xbAggregationStatic    OBJECT IDENTIFIER ::= { sm24tat4xbAggregation 1 }

sm24tat4xbAggrSourceMACAddress    OBJECT-TYPE
        SYNTAX      Integer32 (0|1)
        MAX-ACCESS  read-write
        STATUS      current
        DESCRIPTION
            "Source MAC Address"
        ::= { sm24tat4xbAggregationStatic 2 }

sm24tat4xbAggrDestinationMACAddress    OBJECT-TYPE
        SYNTAX      Integer32 (0|1)
        MAX-ACCESS  read-write
        STATUS      current
        DESCRIPTION
            "Destination MAC Address"
        ::= { sm24tat4xbAggregationStatic 3 }

sm24tat4xbAggrIPAddress    OBJECT-TYPE
        SYNTAX      Integer32 (0|1)
        MAX-ACCESS  read-write
        STATUS      current
        DESCRIPTION
            "IP Address"
        ::= { sm24tat4xbAggregationStatic 4 }

sm24tat4xbAggrTCPUDPPortNumber    OBJECT-TYPE
        SYNTAX      Integer32 (0|1)
        MAX-ACCESS  read-write
        STATUS      current
        DESCRIPTION
            "TCP/UDP Port Number"
        ::= { sm24tat4xbAggregationStatic 5 }


sm24tat4xbAggrGroupConfigTable OBJECT-TYPE
    SYNTAX      SEQUENCE OF SM24TAT4XBAggrGroupConfigEntry
    MAX-ACCESS  not-accessible
    STATUS      current
    DESCRIPTION
        " "
    ::= { sm24tat4xbAggregationStatic 6 }

sm24tat4xbAggrGroupConfigEntry OBJECT-TYPE
    SYNTAX      SM24TAT4XBAggrGroupConfigEntry
    MAX-ACCESS  not-accessible
    STATUS      current
    DESCRIPTION
        " "
    INDEX    { sm24tat4xbAggrGroupConfigPort  }
    ::= { sm24tat4xbAggrGroupConfigTable 1 }

SM24TAT4XBAggrGroupConfigEntry ::= SEQUENCE {
    sm24tat4xbAggrGroupConfigPort         Integer32,
    sm24tat4xbAggrGroupConfigGroup        Integer32,
    sm24tat4xbAggrGroupConfig             Integer32
}

sm24tat4xbAggrGroupConfigPort OBJECT-TYPE
    SYNTAX      Integer32(1..65535)
    MAX-ACCESS  not-accessible
    STATUS      current
    DESCRIPTION
        "port index"
    ::= { sm24tat4xbAggrGroupConfigEntry 1 }

sm24tat4xbAggrGroupConfigGroup OBJECT-TYPE
    SYNTAX      Integer32
    MAX-ACCESS  not-accessible
    STATUS      current
    DESCRIPTION
        "group index"
    ::= { sm24tat4xbAggrGroupConfigEntry 2 }

sm24tat4xbAggrGroupConfig OBJECT-TYPE
    SYNTAX      Integer32 (0|1)
    MAX-ACCESS  read-write
    STATUS      current
    DESCRIPTION
        "Aggregation Group Configuration"
    ::= { sm24tat4xbAggrGroupConfigEntry 3 }

sm24tat4xbLACPConfiguration    OBJECT IDENTIFIER ::= { sm24tat4xbAggregation 2 }

sm24tat4xbLACPPortConfigTable OBJECT-TYPE
    SYNTAX      SEQUENCE OF SM24TAT4XBLACPPortConfigEntry
    MAX-ACCESS  not-accessible
    STATUS      current
    DESCRIPTION
        " "
    ::= { sm24tat4xbLACPConfiguration 1 }

sm24tat4xbLACPPortConfigEntry OBJECT-TYPE
    SYNTAX      SM24TAT4XBLACPPortConfigEntry
    MAX-ACCESS  not-accessible
    STATUS      current
    DESCRIPTION
        " "
    INDEX    { sm24tat4xbLACPPortConfigPort  }
    ::= { sm24tat4xbLACPPortConfigTable 1 }

SM24TAT4XBLACPPortConfigEntry ::= SEQUENCE {
    sm24tat4xbLACPPortConfigPort          Integer32,
    sm24tat4xbLACPPortConfigEnabled        Integer32,
    sm24tat4xbLACPPortConfigKey            Integer32,
    sm24tat4xbLACPPortConfigRole          Integer32,
    sm24tat4xbLACPPortConfigTimeout        Integer32,
    sm24tat4xbLACPPortConfigPrio          Integer32
}

sm24tat4xbLACPPortConfigPort OBJECT-TYPE
    SYNTAX      Integer32(1..65535)
    MAX-ACCESS  not-accessible
    STATUS      current
    DESCRIPTION
        "port index"
    ::= { sm24tat4xbLACPPortConfigEntry 1 }

sm24tat4xbLACPPortConfigEnabled OBJECT-TYPE
    SYNTAX      Integer32 (0|1)
    MAX-ACCESS  read-write
    STATUS      current
    DESCRIPTION
        "Controls whether LACP is enabled on this switch port.
        0:Disable
        1:Enable"
    ::= { sm24tat4xbLACPPortConfigEntry 2 }

sm24tat4xbLACPPortConfigKey OBJECT-TYPE
    SYNTAX      Integer32
    MAX-ACCESS  read-write
    STATUS      current
    DESCRIPTION
        "The Key value incurred by the port, range 1-Number of link aggregations.
        0:autokey."
    ::= { sm24tat4xbLACPPortConfigEntry 3 }

sm24tat4xbLACPPortConfigRole OBJECT-TYPE
    SYNTAX      Integer32 (0|1)
    MAX-ACCESS  read-write
    STATUS      current
    DESCRIPTION
        "The Role shows the LACP activity status.
        0:Passive
        1:Active"
    ::= { sm24tat4xbLACPPortConfigEntry 4 }

sm24tat4xbLACPPortConfigTimeout OBJECT-TYPE
    SYNTAX      Integer32 (0|1)
    MAX-ACCESS  read-write
    STATUS      current
    DESCRIPTION
        "The Timeout controls the period between BPDU transmissions.
        0:Slow
        1:Fast"
    ::= { sm24tat4xbLACPPortConfigEntry 5 }

sm24tat4xbLACPPortConfigPrio OBJECT-TYPE
    SYNTAX      Integer32 (1..65535)
    MAX-ACCESS  read-write
    STATUS      current
    DESCRIPTION
        "The Prio controls the priority of the port."
    ::= { sm24tat4xbLACPPortConfigEntry 6 }


sm24tat4xbLacpSystemStatus    OBJECT IDENTIFIER ::= { sm24tat4xbAggregation 3 }

sm24tat4xbLacpSystemStatusTable OBJECT-TYPE
    SYNTAX      SEQUENCE OF SM24TAT4XBLacpSystemStatusEntry
    MAX-ACCESS  not-accessible
    STATUS      current
    DESCRIPTION
        " "
    ::= { sm24tat4xbLacpSystemStatus 1 }

sm24tat4xbLacpSystemStatusEntry OBJECT-TYPE
    SYNTAX      SM24TAT4XBLacpSystemStatusEntry
    MAX-ACCESS  not-accessible
    STATUS      current
    DESCRIPTION
        " "
    INDEX    { sm24tat4xbLacpSystemStatusIndex  }
    ::= { sm24tat4xbLacpSystemStatusTable 1 }

SM24TAT4XBLacpSystemStatusEntry ::= SEQUENCE {
    sm24tat4xbLacpSystemStatusIndex          Integer32,
    sm24tat4xbLacpSystemStatusAggrID         DisplayString,
    sm24tat4xbLacpSystemStatusPartnerSystemID    DisplayString,
    sm24tat4xbLacpSystemStatusPartnerKey     DisplayString,
    sm24tat4xbLacpSystemStatusPartnerPrio    DisplayString,
    sm24tat4xbLacpSystemStatusLastChanged    DisplayString,
    sm24tat4xbLacpSystemStatusLocalPorts     DisplayString
}

sm24tat4xbLacpSystemStatusIndex OBJECT-TYPE
    SYNTAX      Integer32(1..65535)
    MAX-ACCESS  not-accessible
    STATUS      current
    DESCRIPTION
        "index"
    ::= { sm24tat4xbLacpSystemStatusEntry 1 }

sm24tat4xbLacpSystemStatusAggrID OBJECT-TYPE
    SYNTAX      DisplayString
    MAX-ACCESS  read-only
    STATUS      current
    DESCRIPTION
        "The Aggregation ID associated with this aggregation instance."
    ::= { sm24tat4xbLacpSystemStatusEntry 2 }

sm24tat4xbLacpSystemStatusPartnerSystemID OBJECT-TYPE
    SYNTAX      DisplayString
    MAX-ACCESS  read-only
    STATUS      current
    DESCRIPTION
        "The system ID (MAC address) of the aggregation partner."
    ::= { sm24tat4xbLacpSystemStatusEntry 3 }

sm24tat4xbLacpSystemStatusPartnerKey OBJECT-TYPE
    SYNTAX      DisplayString
    MAX-ACCESS  read-only
    STATUS      current
    DESCRIPTION
        "The Key that the partner has assigned to this aggregation ID."
    ::= { sm24tat4xbLacpSystemStatusEntry 4 }

sm24tat4xbLacpSystemStatusPartnerPrio OBJECT-TYPE
    SYNTAX      DisplayString
    MAX-ACCESS  read-only
    STATUS      current
    DESCRIPTION
        "The priority that the partner has assigned to this aggregation ID."
    ::= { sm24tat4xbLacpSystemStatusEntry 5 }

sm24tat4xbLacpSystemStatusLastChanged OBJECT-TYPE
    SYNTAX      DisplayString
    MAX-ACCESS  read-only
    STATUS      current
    DESCRIPTION
        "The time since this aggregation changed."
    ::= { sm24tat4xbLacpSystemStatusEntry 6 }

sm24tat4xbLacpSystemStatusLocalPorts OBJECT-TYPE
    SYNTAX      DisplayString
    MAX-ACCESS  read-only
    STATUS      current
    DESCRIPTION
        "Shows which ports are a part of this aggregation for this switch."
    ::= { sm24tat4xbLacpSystemStatusEntry 7 }

sm24tat4xbLACPInternalPortStatus    OBJECT IDENTIFIER ::= { sm24tat4xbAggregation 4 }

sm24tat4xbLACPInternalPortStatusTable OBJECT-TYPE
    SYNTAX      SEQUENCE OF SM24TAT4XBLACPInternalPortStatusEntry
    MAX-ACCESS  not-accessible
    STATUS      current
    DESCRIPTION
        " "
    ::= { sm24tat4xbLACPInternalPortStatus 1 }

sm24tat4xbLACPInternalPortStatusEntry OBJECT-TYPE
    SYNTAX      SM24TAT4XBLACPInternalPortStatusEntry
    MAX-ACCESS  not-accessible
    STATUS      current
    DESCRIPTION
        " "
    INDEX    { sm24tat4xbLACPInternalPortStatusIndex  }
    ::= { sm24tat4xbLACPInternalPortStatusTable 1 }

SM24TAT4XBLACPInternalPortStatusEntry ::= SEQUENCE {
    sm24tat4xbLACPInternalPortStatusIndex          Integer32,
    sm24tat4xbLACPInternalPortStatusPort        DisplayString,
    sm24tat4xbLACPInternalPortStatusState          DisplayString,
    sm24tat4xbLACPInternalPortStatusKey        DisplayString,
    sm24tat4xbLACPInternalPortStatusPriority        DisplayString,
    sm24tat4xbLACPInternalPortStatusActivity        DisplayString,
    sm24tat4xbLACPInternalPortStatusTimeout        DisplayString,
    sm24tat4xbLACPInternalPortStatusAggregation    DisplayString,
    sm24tat4xbLACPInternalPortStatusSynchronization    DisplayString,
    sm24tat4xbLACPInternalPortStatusCollecting     DisplayString,
    sm24tat4xbLACPInternalPortStatusDistributing    DisplayString,
    sm24tat4xbLACPInternalPortStatusDefaulted      DisplayString,
    sm24tat4xbLACPInternalPortStatusExpired        DisplayString
}

sm24tat4xbLACPInternalPortStatusIndex OBJECT-TYPE
    SYNTAX      Integer32(1..65535)
    MAX-ACCESS  not-accessible
    STATUS      current
    DESCRIPTION
        "index"
    ::= { sm24tat4xbLACPInternalPortStatusEntry 1 }

sm24tat4xbLACPInternalPortStatusPort OBJECT-TYPE
    SYNTAX      DisplayString
    MAX-ACCESS  read-only
    STATUS      current
    DESCRIPTION
        "The switch port number."
    ::= { sm24tat4xbLACPInternalPortStatusEntry 2 }

sm24tat4xbLACPInternalPortStatusState OBJECT-TYPE
    SYNTAX      DisplayString
    MAX-ACCESS  read-only
    STATUS      current
    DESCRIPTION
        "The current port state:
        Down: The port is not active.
        Active: The port is in active state.
        Standby: The port is in standby state."
    ::= { sm24tat4xbLACPInternalPortStatusEntry 3 }

sm24tat4xbLACPInternalPortStatusKey OBJECT-TYPE
    SYNTAX      DisplayString
    MAX-ACCESS  read-only
    STATUS      current
    DESCRIPTION
        "The key assigned to this port. Only ports with the same key can aggregate together."
    ::= { sm24tat4xbLACPInternalPortStatusEntry 4 }

sm24tat4xbLACPInternalPortStatusPriority OBJECT-TYPE
    SYNTAX      DisplayString
    MAX-ACCESS  read-only
    STATUS      current
    DESCRIPTION
        "The priority assigned to this aggregation group."
    ::= { sm24tat4xbLACPInternalPortStatusEntry 5 }

sm24tat4xbLACPInternalPortStatusActivity OBJECT-TYPE
    SYNTAX      DisplayString
    MAX-ACCESS  read-only
    STATUS      current
    DESCRIPTION
        "The LACP mode of the group (Active or Passive)."
    ::= { sm24tat4xbLACPInternalPortStatusEntry 6 }

sm24tat4xbLACPInternalPortStatusTimeout OBJECT-TYPE
    SYNTAX      DisplayString
    MAX-ACCESS  read-only
    STATUS      current
    DESCRIPTION
        "The timeout mode configured for the port (Fast or Slow)."
    ::= { sm24tat4xbLACPInternalPortStatusEntry 7 }

sm24tat4xbLACPInternalPortStatusAggregation OBJECT-TYPE
    SYNTAX      DisplayString
    MAX-ACCESS  read-only
    STATUS      current
    DESCRIPTION
        "Show whether the system considers this link to be aggregateable. i.e., a potential candidate for aggregation."
    ::= { sm24tat4xbLACPInternalPortStatusEntry 8 }

sm24tat4xbLACPInternalPortStatusSynchronization OBJECT-TYPE
    SYNTAX      DisplayString
    MAX-ACCESS  read-only
    STATUS      current
    DESCRIPTION
        "Show whether the system considers this link to be IN_SYNC."
    ::= { sm24tat4xbLACPInternalPortStatusEntry 9 }

sm24tat4xbLACPInternalPortStatusCollecting OBJECT-TYPE
    SYNTAX      DisplayString
    MAX-ACCESS  read-only
    STATUS      current
    DESCRIPTION
        "Show if collection of incoming frames on this link is enabled."
    ::= { sm24tat4xbLACPInternalPortStatusEntry 10 }

sm24tat4xbLACPInternalPortStatusDistributing OBJECT-TYPE
    SYNTAX      DisplayString
    MAX-ACCESS  read-only
    STATUS      current
    DESCRIPTION
        "Show if distribution of outgoing frames on this link is enabled."
    ::= { sm24tat4xbLACPInternalPortStatusEntry 11 }

sm24tat4xbLACPInternalPortStatusDefaulted OBJECT-TYPE
    SYNTAX      DisplayString
    MAX-ACCESS  read-only
    STATUS      current
    DESCRIPTION
        "Show if the Actor's Receive machine is using Defaulted operational Partner information."
    ::= { sm24tat4xbLACPInternalPortStatusEntry 12 }

sm24tat4xbLACPInternalPortStatusExpired OBJECT-TYPE
    SYNTAX      DisplayString
    MAX-ACCESS  read-only
    STATUS      current
    DESCRIPTION
        "Show if that the Actor's Receive machine is in the EXPIRED state."
    ::= { sm24tat4xbLACPInternalPortStatusEntry 13 }


sm24tat4xbLACPNeighborPortStatus    OBJECT IDENTIFIER ::= { sm24tat4xbAggregation 5 }

sm24tat4xbLACPNeighborPortStatusTable OBJECT-TYPE
    SYNTAX      SEQUENCE OF SM24TAT4XBLACPNeighborPortStatusEntry
    MAX-ACCESS  not-accessible
    STATUS      current
    DESCRIPTION
        " "
    ::= { sm24tat4xbLACPNeighborPortStatus 1 }

sm24tat4xbLACPNeighborPortStatusEntry OBJECT-TYPE
    SYNTAX      SM24TAT4XBLACPNeighborPortStatusEntry
    MAX-ACCESS  not-accessible
    STATUS      current
    DESCRIPTION
        " "
    INDEX    { sm24tat4xbLACPNeighborPortStatusIndex  }
    ::= { sm24tat4xbLACPNeighborPortStatusTable 1 }

SM24TAT4XBLACPNeighborPortStatusEntry ::= SEQUENCE {
    sm24tat4xbLACPNeighborPortStatusIndex          Integer32,
    sm24tat4xbLACPNeighborPortStatusPort        DisplayString,
    sm24tat4xbLACPNeighborPortStatusState          DisplayString,
    sm24tat4xbLACPNeighborPortStatusAggrID         DisplayString,
    sm24tat4xbLACPNeighborPortStatusPartnerKey     DisplayString,
    sm24tat4xbLACPNeighborPortStatusPartnerPort    DisplayString,
    sm24tat4xbLACPNeighborPortStatusPartnerPortPrio    DisplayString,
    sm24tat4xbLACPNeighborPortStatusActivity        DisplayString,
    sm24tat4xbLACPNeighborPortStatusTimeout        DisplayString,
    sm24tat4xbLACPNeighborPortStatusAggregation    DisplayString,
    sm24tat4xbLACPNeighborPortStatusSynchronization    DisplayString,
    sm24tat4xbLACPNeighborPortStatusCollecting     DisplayString,
    sm24tat4xbLACPNeighborPortStatusDistributing    DisplayString,
    sm24tat4xbLACPNeighborPortStatusDefaulted      DisplayString,
    sm24tat4xbLACPNeighborPortStatusExpired        DisplayString
}

sm24tat4xbLACPNeighborPortStatusIndex OBJECT-TYPE
    SYNTAX      Integer32(1..65535)
    MAX-ACCESS  not-accessible
    STATUS      current
    DESCRIPTION
        "index"
    ::= { sm24tat4xbLACPNeighborPortStatusEntry 1 }

sm24tat4xbLACPNeighborPortStatusPort OBJECT-TYPE
    SYNTAX      DisplayString
    MAX-ACCESS  read-only
    STATUS      current
    DESCRIPTION
        "The switch port number."
    ::= { sm24tat4xbLACPNeighborPortStatusEntry 2 }

sm24tat4xbLACPNeighborPortStatusState OBJECT-TYPE
    SYNTAX      DisplayString
    MAX-ACCESS  read-only
    STATUS      current
    DESCRIPTION
        "The current port state:
        Down: The port is not active.
        Active: The port is in active state.
        Standby: The port is in standby state."
    ::= { sm24tat4xbLACPNeighborPortStatusEntry 3 }

sm24tat4xbLACPNeighborPortStatusAggrID OBJECT-TYPE
    SYNTAX      DisplayString
    MAX-ACCESS  read-only
    STATUS      current
    DESCRIPTION
        "The aggregation group ID which the port is assigned to."
    ::= { sm24tat4xbLACPNeighborPortStatusEntry 4 }

sm24tat4xbLACPNeighborPortStatusPartnerKey OBJECT-TYPE
    SYNTAX      DisplayString
    MAX-ACCESS  read-only
    STATUS      current
    DESCRIPTION
        "The key assigned to this port by the partner."
    ::= { sm24tat4xbLACPNeighborPortStatusEntry 5 }

sm24tat4xbLACPNeighborPortStatusPartnerPort OBJECT-TYPE
    SYNTAX      DisplayString
    MAX-ACCESS  read-only
    STATUS      current
    DESCRIPTION
        "The partner port number associated with this link."
    ::= { sm24tat4xbLACPNeighborPortStatusEntry 6 }

sm24tat4xbLACPNeighborPortStatusPartnerPortPrio OBJECT-TYPE
    SYNTAX      DisplayString
    MAX-ACCESS  read-only
    STATUS      current
    DESCRIPTION
        "The priority assigned to this partner port ."
    ::= { sm24tat4xbLACPNeighborPortStatusEntry 7 }

sm24tat4xbLACPNeighborPortStatusActivity OBJECT-TYPE
    SYNTAX      DisplayString
    MAX-ACCESS  read-only
    STATUS      current
    DESCRIPTION
        "The LACP mode of the group (Active or Passive)."
    ::= { sm24tat4xbLACPNeighborPortStatusEntry 8 }

sm24tat4xbLACPNeighborPortStatusTimeout OBJECT-TYPE
    SYNTAX      DisplayString
    MAX-ACCESS  read-only
    STATUS      current
    DESCRIPTION
        "The timeout mode configured for the partner port (Fast or Slow)."
    ::= { sm24tat4xbLACPNeighborPortStatusEntry 9 }

sm24tat4xbLACPNeighborPortStatusAggregation OBJECT-TYPE
    SYNTAX      DisplayString
    MAX-ACCESS  read-only
    STATUS      current
    DESCRIPTION
        "Show whether the partner considers this link to be aggregateable."
    ::= { sm24tat4xbLACPNeighborPortStatusEntry 10 }

sm24tat4xbLACPNeighborPortStatusSynchronization OBJECT-TYPE
    SYNTAX      DisplayString
    MAX-ACCESS  read-only
    STATUS      current
    DESCRIPTION
        "Show whether the partner considers this link to be IN_SYNC"
    ::= { sm24tat4xbLACPNeighborPortStatusEntry 11 }

sm24tat4xbLACPNeighborPortStatusCollecting OBJECT-TYPE
    SYNTAX      DisplayString
    MAX-ACCESS  read-only
    STATUS      current
    DESCRIPTION
        "Show if collection of incoming frames on this link is enabled."
    ::= { sm24tat4xbLACPNeighborPortStatusEntry 12 }

sm24tat4xbLACPNeighborPortStatusDistributing OBJECT-TYPE
    SYNTAX      DisplayString
    MAX-ACCESS  read-only
    STATUS      current
    DESCRIPTION
        "Show if distribution of outgoing frames on this link is enabled."
    ::= { sm24tat4xbLACPNeighborPortStatusEntry 13 }

sm24tat4xbLACPNeighborPortStatusDefaulted OBJECT-TYPE
    SYNTAX      DisplayString
    MAX-ACCESS  read-only
    STATUS      current
    DESCRIPTION
        "Show if the partners Receive machine is using Defaulted operational Partner information."
    ::= { sm24tat4xbLACPNeighborPortStatusEntry 14 }

sm24tat4xbLACPNeighborPortStatusExpired OBJECT-TYPE
    SYNTAX      DisplayString
    MAX-ACCESS  read-only
    STATUS      current
    DESCRIPTION
        "Show if that the partners Receive machine is in the EXPIRED state."
    ::= { sm24tat4xbLACPNeighborPortStatusEntry 15 }


sm24tat4xbLACPStatus    OBJECT IDENTIFIER ::= { sm24tat4xbAggregation 6 }

sm24tat4xbLACPStatusTable OBJECT-TYPE
    SYNTAX      SEQUENCE OF SM24TAT4XBLACPStatusEntry
    MAX-ACCESS  not-accessible
    STATUS      current
    DESCRIPTION
        " "
    ::= { sm24tat4xbLACPStatus 1 }

sm24tat4xbLACPStatusEntry OBJECT-TYPE
    SYNTAX      SM24TAT4XBLACPStatusEntry
    MAX-ACCESS  not-accessible
    STATUS      current
    DESCRIPTION
        " "
    INDEX    { sm24tat4xbLACPStatusPort  }
    ::= { sm24tat4xbLACPStatusTable 1 }

SM24TAT4XBLACPStatusEntry ::= SEQUENCE {
    sm24tat4xbLACPStatusPort        Integer32,
    sm24tat4xbLACPStatusLACP        DisplayString,
    sm24tat4xbLACPStatusKey        DisplayString,
    sm24tat4xbLACPStatusAggrID         DisplayString,
    sm24tat4xbLACPStatusPartnerSystemID    DisplayString,
    sm24tat4xbLACPStatusPartnerPort    DisplayString,
    sm24tat4xbLACPStatusPartnerPrio    DisplayString
}

sm24tat4xbLACPStatusPort OBJECT-TYPE
    SYNTAX      Integer32(1..65535)
    MAX-ACCESS  not-accessible
    STATUS      current
    DESCRIPTION
        "index"
    ::= { sm24tat4xbLACPStatusEntry 1 }

sm24tat4xbLACPStatusLACP OBJECT-TYPE
    SYNTAX      DisplayString
    MAX-ACCESS  read-only
    STATUS      current
    DESCRIPTION
        "Yes: means that LACP is enabled and the port link is up.
        No: means that LACP is not enabled or that the port link is down.
        Backup: means that the port could not join the aggregation group but will join if other port leaves. Meanwhile it's LACP status is disabled."
    ::= { sm24tat4xbLACPStatusEntry 2 }

sm24tat4xbLACPStatusKey OBJECT-TYPE
    SYNTAX      DisplayString
    MAX-ACCESS  read-only
    STATUS      current
    DESCRIPTION
        "The key assigned to this port. Only ports with the same key can aggregate together."
    ::= { sm24tat4xbLACPStatusEntry 3 }

sm24tat4xbLACPStatusAggrID OBJECT-TYPE
    SYNTAX      DisplayString
    MAX-ACCESS  read-only
    STATUS      current
    DESCRIPTION
        "The Aggregation ID assigned to this aggregation group."
    ::= { sm24tat4xbLACPStatusEntry 4 }

sm24tat4xbLACPStatusPartnerSystemID OBJECT-TYPE
    SYNTAX      DisplayString
    MAX-ACCESS  read-only
    STATUS      current
    DESCRIPTION
        "The partner's System ID (MAC address)."
    ::= { sm24tat4xbLACPStatusEntry 5 }

sm24tat4xbLACPStatusPartnerPort OBJECT-TYPE
    SYNTAX      DisplayString
    MAX-ACCESS  read-only
    STATUS      current
    DESCRIPTION
        "The partner's port number connected to this port."
    ::= { sm24tat4xbLACPStatusEntry 6 }

sm24tat4xbLACPStatusPartnerPrio OBJECT-TYPE
    SYNTAX      DisplayString
    MAX-ACCESS  read-only
    STATUS      current
    DESCRIPTION
        "The partner's port priority."
    ::= { sm24tat4xbLACPStatusEntry 7 }

sm24tat4xbAggrGroupStateTable OBJECT-TYPE
    SYNTAX      SEQUENCE OF SM24TAT4XBAggrGroupStateEntry
    MAX-ACCESS  not-accessible
    STATUS      current
    DESCRIPTION
        " "
    ::= { sm24tat4xbAggregation 7 }

sm24tat4xbAggrGroupStateEntry OBJECT-TYPE
    SYNTAX      SM24TAT4XBAggrGroupStateEntry
    MAX-ACCESS  not-accessible
    STATUS      current
    DESCRIPTION
        " "
    INDEX    { sm24tat4xbAggrGroupStateIndex  }
    ::= { sm24tat4xbAggrGroupStateTable 1 }

SM24TAT4XBAggrGroupStateEntry ::= SEQUENCE {
    sm24tat4xbAggrGroupStateIndex         Integer32,
    sm24tat4xbAggrGroupStateAggrID        DisplayString,
    sm24tat4xbAggrGroupStateName          DisplayString,
    sm24tat4xbAggrGroupStateType          DisplayString,
    sm24tat4xbAggrGroupStateSpeed         DisplayString,
    sm24tat4xbAggrGroupStateConfiguredPorts    DisplayString,
    sm24tat4xbAggrGroupStateAggregatedPorts    DisplayString,
    sm24tat4xbAggrGroupStateAggregatedBandwidth    DisplayString
}

sm24tat4xbAggrGroupStateIndex OBJECT-TYPE
    SYNTAX      Integer32(1..65535)
    MAX-ACCESS  not-accessible
    STATUS      current
    DESCRIPTION
        "index"
    ::= { sm24tat4xbAggrGroupStateEntry 1 }

sm24tat4xbAggrGroupStateAggrID OBJECT-TYPE
    SYNTAX      DisplayString
    MAX-ACCESS  read-only
    STATUS      current
    DESCRIPTION
        "AggrID"
    ::= { sm24tat4xbAggrGroupStateEntry 2 }

sm24tat4xbAggrGroupStateName OBJECT-TYPE
    SYNTAX      DisplayString
    MAX-ACCESS  read-only
    STATUS      current
    DESCRIPTION
        "Name"
    ::= { sm24tat4xbAggrGroupStateEntry 3 }

sm24tat4xbAggrGroupStateType OBJECT-TYPE
    SYNTAX      DisplayString
    MAX-ACCESS  read-only
    STATUS      current
    DESCRIPTION
        "Type"
    ::= { sm24tat4xbAggrGroupStateEntry 4 }

sm24tat4xbAggrGroupStateSpeed OBJECT-TYPE
    SYNTAX      DisplayString
    MAX-ACCESS  read-only
    STATUS      current
    DESCRIPTION
        "Speed"
    ::= { sm24tat4xbAggrGroupStateEntry 5 }

sm24tat4xbAggrGroupStateConfiguredPorts OBJECT-TYPE
    SYNTAX      DisplayString
    MAX-ACCESS  read-only
    STATUS      current
    DESCRIPTION
        "Configured Ports"
    ::= { sm24tat4xbAggrGroupStateEntry 6 }

sm24tat4xbAggrGroupStateAggregatedPorts OBJECT-TYPE
    SYNTAX      DisplayString
    MAX-ACCESS  read-only
    STATUS      current
    DESCRIPTION
        "Aggregated Ports"
    ::= { sm24tat4xbAggrGroupStateEntry 7 }

sm24tat4xbAggrGroupStateAggregatedBandwidth OBJECT-TYPE
    SYNTAX      DisplayString
    MAX-ACCESS  read-only
    STATUS      current
    DESCRIPTION
        "Aggregated Bandwidth"
    ::= { sm24tat4xbAggrGroupStateEntry 8 }

-- =======================================================================================================================
sm24tat4xbSecurity                          OBJECT IDENTIFIER ::= { sm24tat4xbProductId 3 }

sm24tat4xbIPSourceGuard                     OBJECT IDENTIFIER ::= { sm24tat4xbSecurity 1 }

sm24tat4xbIPSourceGuardConf                     OBJECT IDENTIFIER ::= { sm24tat4xbIPSourceGuard 1 }

-- RowStatus Info:  createAndGo, notReady not supported.
-- =======================================================================================================================
-- Textual Conventions for the SM24TAT4XB IP Source Guard Mib
-- =======================================================================================================================
--
--    sm24tat4xbIPSourceGuard    OBJECT IDENTIFIER  ::= { sm24tat4xbIPSourceGuardMIB 1 }
--    sm24tat4xbIPSourceGuardConf    OBJECT IDENTIFIER  ::= { sm24tat4xbIPSourceGuard 1 }

--
-- =======================================================================================================================
-- Start sm24tat4xbIPSourceGuard group
-- =======================================================================================================================
--sm24tat4xbIPSourceGuardConf

    sm24tat4xbIPSourceGuardMode OBJECT-TYPE
        SYNTAX      AdminMode
        MAX-ACCESS  read-write
        STATUS      current
        DESCRIPTION
            "Enable the Global IP Source Guard or disable the
            Global IP Source Guard."
        ::= {     sm24tat4xbIPSourceGuardConf 1 }

    sm24tat4xbIPSourceGuardDynamicToStaticCmd OBJECT-TYPE
        SYNTAX      ActivateCmd
        MAX-ACCESS  read-write
        STATUS      current
        DESCRIPTION
            "Translate all dynamic entries to static entries."
        DEFVAL  { noAction }
        ::= {     sm24tat4xbIPSourceGuardConf 2 }

--sm24tat4xbIPSourceGuardPortConfigTable

    sm24tat4xbIPSourceGuardPortConfigTable OBJECT-TYPE
        SYNTAX      SEQUENCE OF     SM24TAT4XBIPSourceGuardPortConfigEntry
        MAX-ACCESS  not-accessible
        STATUS      current
        DESCRIPTION
            "The IP Source Guard Port Configuration Table.
            INDEX for this table is ifIndex which is
            equivalent to the panel port number."
        ::= {     sm24tat4xbIPSourceGuardConf 3 }

    sm24tat4xbIPSourceGuardPortConfigEntry OBJECT-TYPE
        SYNTAX      SM24TAT4XBIPSourceGuardPortConfigEntry
        MAX-ACCESS  not-accessible
        STATUS      current
        DESCRIPTION
            "The IP Source Guard Port Configuration Entry."
        INDEX    {    ifIndex  }
        ::= {     sm24tat4xbIPSourceGuardPortConfigTable 1 }

    SM24TAT4XBIPSourceGuardPortConfigEntry         ::= SEQUENCE {
         sm24tat4xbIPSourceGuardPortConfigMode        AdminMode,
         sm24tat4xbIPSourceGuardPortMaxDynamicClients     Integer32
         }

    sm24tat4xbIPSourceGuardPortConfigMode OBJECT-TYPE
        SYNTAX      AdminMode
        MAX-ACCESS  read-write
        STATUS      current
        DESCRIPTION
            "Specify IP Source Guard is enabled on which ports."
        ::= {     sm24tat4xbIPSourceGuardPortConfigEntry 2 }

    sm24tat4xbIPSourceGuardPortMaxDynamicClients OBJECT-TYPE
        SYNTAX      Integer32(0..2|99)
        MAX-ACCESS  read-write
        STATUS      current
        DESCRIPTION
            "Specify the maximum number of dynamic clients that can
            be learned on given port.
            default: 99
            0~2: Max Dynamic clients
            99:Unlimited "
        ::= {     sm24tat4xbIPSourceGuardPortConfigEntry 3 }

--sm24tat4xbIPSourceGuardStaticTable

    sm24tat4xbIPSourceGuardStaticTable OBJECT-TYPE
        SYNTAX      SEQUENCE OF     SM24TAT4XBIPSourceGuardStaticEntry
        MAX-ACCESS  not-accessible
        STATUS      current
        DESCRIPTION
            "The IP Source Guard Static Table."
        ::= {     sm24tat4xbIPSourceGuard 2 }

    sm24tat4xbIPSourceGuardStaticEntry OBJECT-TYPE
        SYNTAX      SM24TAT4XBIPSourceGuardStaticEntry
        MAX-ACCESS  not-accessible
        STATUS      current
        DESCRIPTION
            "The IP Source Guard Static Entry."
        INDEX    {    sm24tat4xbIPSourceGuardStaticIndex  }
        ::= {     sm24tat4xbIPSourceGuardStaticTable 1 }

    SM24TAT4XBIPSourceGuardStaticEntry         ::= SEQUENCE {
         sm24tat4xbIPSourceGuardStaticSwitchIndex    Integer32,
         sm24tat4xbIPSourceGuardStaticIndex     Integer32,
         sm24tat4xbIPSourceGuardStaticPort      Integer32,
         sm24tat4xbIPSourceGuardStaticVLANId    Integer32,
         sm24tat4xbIPSourceGuardStaticIPAddress     IpAddress,
--         sm24tat4xbIPSourceGuardStaticIPMask    IpAddress,
         sm24tat4xbIPSourceGuardStaticMACAddress    DisplayString,
         sm24tat4xbIPSourceGuardStaticRowStatus     RowStatus
         }

    sm24tat4xbIPSourceGuardStaticSwitchIndex OBJECT-TYPE
        SYNTAX      Integer32(1..16)
        MAX-ACCESS  not-accessible
        STATUS      current
        DESCRIPTION
            "Switch Index."
        ::= {     sm24tat4xbIPSourceGuardStaticEntry 1 }

    sm24tat4xbIPSourceGuardStaticIndex OBJECT-TYPE
        SYNTAX      Integer32(1..28)
        MAX-ACCESS  not-accessible
        STATUS      current
        DESCRIPTION
            "The entry of table."
        ::= {     sm24tat4xbIPSourceGuardStaticEntry 2 }

    sm24tat4xbIPSourceGuardStaticPort OBJECT-TYPE
        SYNTAX      Integer32(1..255)
        MAX-ACCESS  read-create
        STATUS      current
        DESCRIPTION
            "The port number of table.
            range: 1 - port number."
        ::= {     sm24tat4xbIPSourceGuardStaticEntry 3 }

    sm24tat4xbIPSourceGuardStaticVLANId OBJECT-TYPE
        SYNTAX      Integer32(1..4095)
        MAX-ACCESS  read-create
        STATUS      current
        DESCRIPTION
            "VLAN ID, range: 1 - 4095."
        ::= {     sm24tat4xbIPSourceGuardStaticEntry 4 }

    sm24tat4xbIPSourceGuardStaticIPAddress OBJECT-TYPE
        SYNTAX      IpAddress
        MAX-ACCESS  read-create
        STATUS      current
        DESCRIPTION
            "IP address allowed for doing IP source guard."
        ::= {     sm24tat4xbIPSourceGuardStaticEntry 5 }

--    sm24tat4xbIPSourceGuardStaticIPMask OBJECT-TYPE
--        SYNTAX      IpAddress
--        MAX-ACCESS  read-create
--        STATUS      current
--        DESCRIPTION
--            "IP Mask allowed for doing IP source guard."
--        ::= {     sm24tat4xbIPSourceGuardStaticEntry 6 }

    sm24tat4xbIPSourceGuardStaticMACAddress OBJECT-TYPE
        SYNTAX      DisplayString
        MAX-ACCESS  read-create
        STATUS      current
        DESCRIPTION
            "Allowed Source MAC address, format: 0a 1b 2c 3d 4e 5f."
        ::= {     sm24tat4xbIPSourceGuardStaticEntry 7 }

    sm24tat4xbIPSourceGuardStaticRowStatus OBJECT-TYPE
        SYNTAX      RowStatus
        MAX-ACCESS  read-create
        STATUS      current
        DESCRIPTION
            "This object indicates the status of this entry, and is
            used to create/delete entries.  Any object in an entry of
            this table may be modified while the value of the
            corresponding instance of this object is active(1).
            createAndGo, notReady not supported."
        ::= {     sm24tat4xbIPSourceGuardStaticEntry 8 }

--sm24tat4xbIPSourceGuardDynamicTable

    sm24tat4xbIPSourceGuardDynamicTable OBJECT-TYPE
        SYNTAX      SEQUENCE OF     SM24TAT4XBIPSourceGuardDynamicEntry
        MAX-ACCESS  not-accessible
        STATUS      current
        DESCRIPTION
            "The IP Source Guard Dynamic Table."
        ::= {     sm24tat4xbIPSourceGuard 3 }

    sm24tat4xbIPSourceGuardDynamicEntry OBJECT-TYPE
        SYNTAX      SM24TAT4XBIPSourceGuardDynamicEntry
        MAX-ACCESS  not-accessible
        STATUS      current
        DESCRIPTION
            "The IP Source Guard Dynamic Entry."
        INDEX    {    sm24tat4xbIPSourceGuardDynamicIndex  }
        ::= {     sm24tat4xbIPSourceGuardDynamicTable 1 }

    SM24TAT4XBIPSourceGuardDynamicEntry         ::= SEQUENCE {
         sm24tat4xbIPSourceGuardDynamicSwitchIndex    Integer32,
         sm24tat4xbIPSourceGuardDynamicIndex      Integer32,
         sm24tat4xbIPSourceGuardDynamicPort        Integer32,
         sm24tat4xbIPSourceGuardDynamicVLANId     Integer32,
         sm24tat4xbIPSourceGuardDynamicIPAddress      IpAddress,
         sm24tat4xbIPSourceGuardDynamicMACAddress     DisplayString
         }

    sm24tat4xbIPSourceGuardDynamicSwitchIndex OBJECT-TYPE
        SYNTAX      Integer32(1..16)
        MAX-ACCESS  not-accessible
        STATUS      current
        DESCRIPTION
            "Switch Index."
        ::= {     sm24tat4xbIPSourceGuardDynamicEntry 1 }

    sm24tat4xbIPSourceGuardDynamicIndex OBJECT-TYPE
        SYNTAX      Integer32(1..4095)
        MAX-ACCESS  not-accessible
        STATUS      current
        DESCRIPTION
            "The entry of table."
        ::= {     sm24tat4xbIPSourceGuardDynamicEntry 2 }

    sm24tat4xbIPSourceGuardDynamicPort OBJECT-TYPE
        SYNTAX      Integer32(1..255)
        MAX-ACCESS  read-only
        STATUS      current
        DESCRIPTION
            "The logical port for the settings."
        ::= {     sm24tat4xbIPSourceGuardDynamicEntry 3 }

    sm24tat4xbIPSourceGuardDynamicVLANId OBJECT-TYPE
        SYNTAX      Integer32(1..4094)
        MAX-ACCESS  read-only
        STATUS      current
        DESCRIPTION
            "The vlan id for the settings."
        ::= {     sm24tat4xbIPSourceGuardDynamicEntry 4 }

    sm24tat4xbIPSourceGuardDynamicIPAddress OBJECT-TYPE
        SYNTAX      IpAddress
        MAX-ACCESS  read-only
        STATUS      current
        DESCRIPTION
            "Allowed Source IP address."
        ::= {     sm24tat4xbIPSourceGuardDynamicEntry 5 }

    sm24tat4xbIPSourceGuardDynamicMACAddress OBJECT-TYPE
        SYNTAX      DisplayString
        MAX-ACCESS  read-only
        STATUS      current
        DESCRIPTION
            "Allowed Source MAC address."
        ::= {     sm24tat4xbIPSourceGuardDynamicEntry 6 }
-- =======================================================================================================================
sm24tat4xbARPInspection                      OBJECT IDENTIFIER ::= { sm24tat4xbSecurity 2 }
-- RowStatus Info:  createAndGo, notReady not supported.
-- =======================================================================================================================
-- Textual Conventions for the sm24tat4xb Arp Mib
-- =======================================================================================================================
--
    sm24tat4xbARP          OBJECT IDENTIFIER  ::= { sm24tat4xbARPInspection 1 }
    sm24tat4xbARPConfig        OBJECT IDENTIFIER  ::= { sm24tat4xbARP 1 }

--
-- =======================================================================================================================
-- Start sm24tat4xbARP group
-- =======================================================================================================================
--sm24tat4xbARPConfig

    sm24tat4xbARPConfMode OBJECT-TYPE
        SYNTAX      AdminMode
        MAX-ACCESS  read-write
        STATUS      current
        DESCRIPTION
            "Enable the Global ARP Inspection or disable the Global
            ARP Inspection."
        ::= {     sm24tat4xbARPConfig 1 }

--sm24tat4xbARPPortConfTable

    sm24tat4xbARPPortConfTable OBJECT-TYPE
        SYNTAX      SEQUENCE OF     SM24TAT4XBARPPortConfEntry
        MAX-ACCESS  not-accessible
        STATUS      current
        DESCRIPTION
            "The ARP Port Configuration Table."
        ::= {     sm24tat4xbARPConfig 3 }

    sm24tat4xbARPPortConfEntry OBJECT-TYPE
        SYNTAX      SM24TAT4XBARPPortConfEntry
        MAX-ACCESS  not-accessible
        STATUS      current
        DESCRIPTION
            "The ARP Port Configuration Entry."
        INDEX    {    sm24tat4xbARPPortConfPort  }
        ::= {     sm24tat4xbARPPortConfTable 1 }

    SM24TAT4XBARPPortConfEntry         ::= SEQUENCE {
         sm24tat4xbARPPortConfPort        Integer32,
         sm24tat4xbARPPortConfMode        AdminMode,
         sm24tat4xbARPPortConfCheckVLAN    AdminMode,
         sm24tat4xbARPPortConfLogType     INTEGER
         }

    sm24tat4xbARPPortConfPort OBJECT-TYPE
        SYNTAX      Integer32(1..255)
        MAX-ACCESS  not-accessible
        STATUS      current
        DESCRIPTION
            "The port number for which the configuration below applies.
            range: 1 - port number."
        ::= {     sm24tat4xbARPPortConfEntry 1 }

    sm24tat4xbARPPortConfMode OBJECT-TYPE
        SYNTAX      AdminMode
        MAX-ACCESS  read-write
        STATUS      current
        DESCRIPTION
            "Specify ARP Inspection is enabled on which ports."
        ::= {     sm24tat4xbARPPortConfEntry 2 }

    sm24tat4xbARPPortConfCheckVLAN OBJECT-TYPE
        SYNTAX      AdminMode
        MAX-ACCESS  read-write
        STATUS      current
        DESCRIPTION
            "When the setting of 'Check VLAN' is disabled, the log
            type of ARP Inspection will refer to the port setting.
            And the setting of 'Check VLAN' is enabled, the log type
            of ARP Inspection will refer to the VLAN setting."
        ::= {     sm24tat4xbARPPortConfEntry 3 }

    sm24tat4xbARPPortConfLogType OBJECT-TYPE
        SYNTAX      INTEGER{none(0),deny(1),permit(2),all(3)}
        MAX-ACCESS  read-write
        STATUS      current
        DESCRIPTION
            "The log type of ARP Inspection will refer to the
            port setting.
            0: none,
            1: deny,
            2: permit,
            3: all,
            range: 0-3."
        ::= {     sm24tat4xbARPPortConfEntry 4 }

--sm24tat4xbARPVlanConfig

    sm24tat4xbARPVlanConfigTable OBJECT-TYPE
        SYNTAX      SEQUENCE OF     SM24TAT4XBARPVlanConfigEntry
        MAX-ACCESS  not-accessible
        STATUS      current
        DESCRIPTION
            "The ARP Vlan Configuration Table."
        ::= {     sm24tat4xbARP 2 }

    sm24tat4xbARPVlanConfigEntry OBJECT-TYPE
        SYNTAX      SM24TAT4XBARPVlanConfigEntry
        MAX-ACCESS  not-accessible
        STATUS      current
        DESCRIPTION
            "The ARP Vlan Configuration Entry."
        INDEX    {    sm24tat4xbARPVlanConfigVlan  }
        ::= {     sm24tat4xbARPVlanConfigTable 1 }

    SM24TAT4XBARPVlanConfigEntry         ::= SEQUENCE {
         sm24tat4xbARPPortConfigIndex      Integer32,
         sm24tat4xbARPVlanConfigVlan    Integer32,
         sm24tat4xbARPVlanConfigLogType    INTEGER,
         sm24tat4xbARPVlanConfigRowStatus  RowStatus
         }

    sm24tat4xbARPPortConfigIndex OBJECT-TYPE
        SYNTAX      Integer32(1..4095)
        MAX-ACCESS  not-accessible
        STATUS      current
        DESCRIPTION
            "The Index of Vlan config Table"
        ::= {     sm24tat4xbARPVlanConfigEntry 1 }

    sm24tat4xbARPVlanConfigVlan OBJECT-TYPE
        SYNTAX      Integer32(1..4095)
        MAX-ACCESS  read-create
        STATUS      current
        DESCRIPTION
            "Specify ARP Inspection is enabled on which VLANs.
            range: 1 - 4095."
        ::= {     sm24tat4xbARPVlanConfigEntry 2 }

    sm24tat4xbARPVlanConfigLogType OBJECT-TYPE
        SYNTAX      INTEGER{none(0),deny(1),permit(2),all(3)}
        MAX-ACCESS  read-create
        STATUS      current
        DESCRIPTION
            "The log type also can be configured on per VLAN setting.
            0: none,
            1: deny,
            2: permit,
            3: all,
            range: 0-3."
        ::= {     sm24tat4xbARPVlanConfigEntry 3 }

    sm24tat4xbARPVlanConfigRowStatus OBJECT-TYPE
        SYNTAX      RowStatus
        MAX-ACCESS  read-create
        STATUS      current
        DESCRIPTION
            "This object indicates the status of this entry, and is
            used to create/delete entries.  Any object in an entry of
            this table may be modified while the value of the
            corresponding instance of this object is active(1).
            createAndGo, notReady not supported."
        ::= {     sm24tat4xbARPVlanConfigEntry 4 }

--sm24tat4xbARPStaticTable

    sm24tat4xbARPStaticTable OBJECT-TYPE
        SYNTAX      SEQUENCE OF     SM24TAT4XBARPStaticEntry
        MAX-ACCESS  not-accessible
        STATUS      current
        DESCRIPTION
            "The ARP Static Table."
        ::= {     sm24tat4xbARP 3 }

    sm24tat4xbARPStaticEntry OBJECT-TYPE
        SYNTAX      SM24TAT4XBARPStaticEntry
        MAX-ACCESS  not-accessible
        STATUS      current
        DESCRIPTION
            "The ARP Static Entry."
        INDEX    {    sm24tat4xbARPStaticIndex  }
        ::= {     sm24tat4xbARPStaticTable 1 }

    SM24TAT4XBARPStaticEntry         ::= SEQUENCE {
         sm24tat4xbARPStaticSwitchIndex    Integer32,
         sm24tat4xbARPStaticIndex     Integer32,
         sm24tat4xbARPStaticPort      Integer32,
         sm24tat4xbARPStaticVlanID    Integer32,
         sm24tat4xbARPStaticMACAddress    DisplayString,
         sm24tat4xbARPStaticIPAddress     IpAddress,
         sm24tat4xbARPStaticRowStatus     RowStatus
         }


    sm24tat4xbARPStaticSwitchIndex OBJECT-TYPE
        SYNTAX      Integer32(1..16)
        MAX-ACCESS  not-accessible
        STATUS      current
        DESCRIPTION
            "Switch Index."
        ::= {     sm24tat4xbARPStaticEntry 1 }

    sm24tat4xbARPStaticIndex OBJECT-TYPE
        SYNTAX      Integer32(1..255)
        MAX-ACCESS  not-accessible
        STATUS      current
        DESCRIPTION
            "The entry of table."
        ::= {     sm24tat4xbARPStaticEntry 2 }

    sm24tat4xbARPStaticPort OBJECT-TYPE
        SYNTAX      Integer32(1..255)
        MAX-ACCESS  read-create
        STATUS      current
        DESCRIPTION
            "The logical port for the settings.
            range: 1 - port number."
        ::= {     sm24tat4xbARPStaticEntry 3 }

    sm24tat4xbARPStaticVlanID OBJECT-TYPE
        SYNTAX      Integer32(1..4095)
        MAX-ACCESS  read-create
        STATUS      current
        DESCRIPTION
            "The vlan id for the settings.
            range: 1-4095."
        ::= {     sm24tat4xbARPStaticEntry 4 }

    sm24tat4xbARPStaticMACAddress OBJECT-TYPE
        SYNTAX      DisplayString
        MAX-ACCESS  read-create
        STATUS      current
        DESCRIPTION
            "Allowed Source MAC address in ARP request packets."
        ::= {     sm24tat4xbARPStaticEntry 5 }

    sm24tat4xbARPStaticIPAddress OBJECT-TYPE
        SYNTAX      IpAddress
        MAX-ACCESS  read-create
        STATUS      current
        DESCRIPTION
            "Allowed Source IP address in ARP request packets."
        ::= {     sm24tat4xbARPStaticEntry 6 }

    sm24tat4xbARPStaticRowStatus OBJECT-TYPE
        SYNTAX      RowStatus
        MAX-ACCESS  read-create
        STATUS      current
        DESCRIPTION
            "This object indicates the status of this entry, and is
            used to create/delete entries.  Any object in an entry of
            this table may be modified while the value of the
            corresponding instance of this object is active(1).
            createAndGo, notReady not supported."
        ::= {     sm24tat4xbARPStaticEntry 7 }

--sm24tat4xbARPDynamicTable

    sm24tat4xbARPDynamicTable OBJECT-TYPE
        SYNTAX      SEQUENCE OF     SM24TAT4XBARPDynamicEntry
        MAX-ACCESS  not-accessible
        STATUS      current
        DESCRIPTION
            "The ARP Dynamic Table."
        ::= {    sm24tat4xbARP 4 }

    sm24tat4xbARPDynamicEntry OBJECT-TYPE
        SYNTAX      SM24TAT4XBARPDynamicEntry
        MAX-ACCESS  not-accessible
        STATUS      current
        DESCRIPTION
            "The ARP Dynamic Entry."
        INDEX    {    sm24tat4xbARPDynamicIndex  }
        ::= {    sm24tat4xbARPDynamicTable 1 }

    SM24TAT4XBARPDynamicEntry         ::= SEQUENCE {
         sm24tat4xbARPDynamicIndex      Integer32,
         sm24tat4xbARPDynamicPort        Integer32,
         sm24tat4xbARPDynamicVLANId     Integer32,
         sm24tat4xbARPDynamicMACAddress     MacAddress,
         sm24tat4xbARPDynamicIPAddress      IpAddress,
         sm24tat4xbARPDynamicToStaticCmd    INTEGER
         }

    sm24tat4xbARPDynamicIndex OBJECT-TYPE
        SYNTAX      Integer32(1..4095)
        MAX-ACCESS  not-accessible
        STATUS      current
        DESCRIPTION
            "The entry of table."
        ::= {    sm24tat4xbARPDynamicEntry 1 }

    sm24tat4xbARPDynamicPort OBJECT-TYPE
        SYNTAX      Integer32(1..255)
        MAX-ACCESS  read-only
        STATUS      current
        DESCRIPTION
            "Switch Port Number for which the entries are displayed."
        ::= {    sm24tat4xbARPDynamicEntry 2 }

    sm24tat4xbARPDynamicVLANId OBJECT-TYPE
        SYNTAX      Integer32(1..4095)
        MAX-ACCESS  read-only
        STATUS      current
        DESCRIPTION
            "VLAN-ID in which the ARP traffic is permitted."
        ::= {    sm24tat4xbARPDynamicEntry 3 }

    sm24tat4xbARPDynamicMACAddress OBJECT-TYPE
        SYNTAX      MacAddress
        MAX-ACCESS  read-only
        STATUS      current
        DESCRIPTION
            "User MAC address of the entry."
        ::= {    sm24tat4xbARPDynamicEntry 4 }

    sm24tat4xbARPDynamicIPAddress OBJECT-TYPE
        SYNTAX      IpAddress
        MAX-ACCESS  read-only
        STATUS      current
        DESCRIPTION
            "User IP address of the entry."
        ::= {    sm24tat4xbARPDynamicEntry 5 }

    sm24tat4xbARPDynamicToStaticCmd OBJECT-TYPE
        SYNTAX      ActivateCmd
        MAX-ACCESS  read-write
        STATUS      current
        DESCRIPTION
            "Enable the Global ARP Inspection or disable the Global
            ARP Inspection."
        ::= {     sm24tat4xbARPDynamicEntry 6 }


-- =======================================================================================================================
-- sm24tat4xbARPConformance
-- =======================================================================================================================
sm24tat4xbARPConformance OBJECT IDENTIFIER ::= { sm24tat4xbARPInspection 200 }

sm24tat4xbARPCompliances OBJECT IDENTIFIER ::= { sm24tat4xbARPConformance 1 }

sm24tat4xbARPGroups      OBJECT IDENTIFIER ::= { sm24tat4xbARPConformance 2 }

sm24tat4xbARPGroup OBJECT-GROUP
    OBJECTS {
        -- sm24tat4xbARPConfig
        sm24tat4xbARPConfMode,

        --sm24tat4xbARPPortConfTable
        sm24tat4xbARPPortConfMode,
        sm24tat4xbARPPortConfCheckVLAN,
        sm24tat4xbARPPortConfLogType,

        --sm24tat4xbARPVlanConfig
        sm24tat4xbARPVlanConfigLogType,
        sm24tat4xbARPVlanConfigRowStatus,

        --sm24tat4xbARPStaticTable
        sm24tat4xbARPStaticPort,
        sm24tat4xbARPStaticVlanID,
        sm24tat4xbARPStaticMACAddress,
        sm24tat4xbARPStaticIPAddress,
        sm24tat4xbARPStaticRowStatus,

        --sm24tat4xbARPDynamicTable
        sm24tat4xbARPDynamicPort,
        sm24tat4xbARPDynamicVLANId,
        sm24tat4xbARPDynamicMACAddress,
        sm24tat4xbARPDynamicIPAddress,
        sm24tat4xbARPDynamicToStaticCmd
        }
     STATUS  current
     DESCRIPTION
        "The collection of objects which are used to indicate
        sm24tat4xb ARP information."
    ::= { sm24tat4xbARPGroups 1 }

-- =======================================================================================================================
sm24tat4xbDHCPSnooping                      OBJECT IDENTIFIER ::= { sm24tat4xbSecurity 3 }

sm24tat4xbDHCPSnoopingConf                      OBJECT IDENTIFIER ::= { sm24tat4xbDHCPSnooping 1 }

sm24tat4xbDHCPSnoopingMode OBJECT-TYPE
    SYNTAX      Integer32(0|1)
    MAX-ACCESS  read-write
    STATUS      current
    DESCRIPTION
        "default: 0
        0: disable
        1: enable"
    ::= { sm24tat4xbDHCPSnoopingConf 1 }

sm24tat4xbDHCPSnoopingPortModeConfigurationTable OBJECT-TYPE
    SYNTAX      SEQUENCE OF SM24TAT4XBDHCPSnoopingPortModeConfigurationEntry
    MAX-ACCESS  not-accessible
    STATUS      current
    DESCRIPTION
        " "
    ::= { sm24tat4xbDHCPSnoopingConf 2 }

sm24tat4xbDHCPSnoopingPortModeConfigurationEntry OBJECT-TYPE
    SYNTAX      SM24TAT4XBDHCPSnoopingPortModeConfigurationEntry
    MAX-ACCESS  not-accessible
    STATUS      current
    DESCRIPTION
        " "
    INDEX    { sm24tat4xbDHCPSnoopingPortModeConfigurationPort  }
    ::= { sm24tat4xbDHCPSnoopingPortModeConfigurationTable 1 }

SM24TAT4XBDHCPSnoopingPortModeConfigurationEntry ::= SEQUENCE {
    sm24tat4xbDHCPSnoopingPortModeConfigurationPort	Integer32,
    sm24tat4xbDHCPSnoopingPortModeConfigurationMode	Integer32
}

sm24tat4xbDHCPSnoopingPortModeConfigurationPort OBJECT-TYPE
    SYNTAX      Integer32(1..4095)
    MAX-ACCESS  not-accessible
    STATUS      current
    DESCRIPTION
        " "
    ::= { sm24tat4xbDHCPSnoopingPortModeConfigurationEntry 1 }

sm24tat4xbDHCPSnoopingPortModeConfigurationMode OBJECT-TYPE
    SYNTAX      Integer32 (0|1)
    MAX-ACCESS  read-write
    STATUS      current
    DESCRIPTION
        "default: 1
        0: trust port mode
        1: untrust port mode"
    ::= { sm24tat4xbDHCPSnoopingPortModeConfigurationEntry 2 }

sm24tat4xbDHCPSnoopingStatisticsTable OBJECT-TYPE
    SYNTAX      SEQUENCE OF SM24TAT4XBDHCPSnoopingStatisticsEntry
    MAX-ACCESS  not-accessible
    STATUS      current
    DESCRIPTION
        " "
    ::= { sm24tat4xbDHCPSnooping 2 }

sm24tat4xbDHCPSnoopingStatisticsEntry OBJECT-TYPE
    SYNTAX      SM24TAT4XBDHCPSnoopingStatisticsEntry
    MAX-ACCESS  not-accessible
    STATUS      current
    DESCRIPTION
        " "
    INDEX    { sm24tat4xbDHCPSnoopingStatisticsPort  }
    ::= { sm24tat4xbDHCPSnoopingStatisticsTable 1 }

SM24TAT4XBDHCPSnoopingStatisticsEntry ::= SEQUENCE {
    sm24tat4xbDHCPSnoopingStatisticsPort     Integer32,
    sm24tat4xbDHCPSnoopingStatisticsClear    Integer32,
    sm24tat4xbDHCPSnoopingRxDiscover         Counter32,
    sm24tat4xbDHCPSnoopingRxOffer        Counter32,
    sm24tat4xbDHCPSnoopingRxRequest          Counter32,
    sm24tat4xbDHCPSnoopingRxDecline          Counter32,
    sm24tat4xbDHCPSnoopingRxACK          Counter32,
    sm24tat4xbDHCPSnoopingRxNAK          Counter32,
    sm24tat4xbDHCPSnoopingRxRelease          Counter32,
    sm24tat4xbDHCPSnoopingRxInform        Counter32,
    sm24tat4xbDHCPSnoopingRxLeaseQuery        Counter32,
    sm24tat4xbDHCPSnoopingRxLeaseUnassigned      Counter32,
    sm24tat4xbDHCPSnoopingRxLeaseUnknown     Counter32,
    sm24tat4xbDHCPSnoopingRxLeaseActive      Counter32,
    sm24tat4xbDHCPSnoopingTxDiscover         Counter32,
    sm24tat4xbDHCPSnoopingTxOffer        Counter32,
    sm24tat4xbDHCPSnoopingTxRequest          Counter32,
    sm24tat4xbDHCPSnoopingTxDecline          Counter32,
    sm24tat4xbDHCPSnoopingTxACK          Counter32,
    sm24tat4xbDHCPSnoopingTxNAK          Counter32,
    sm24tat4xbDHCPSnoopingTxRelease          Counter32,
    sm24tat4xbDHCPSnoopingTxInform        Counter32,
    sm24tat4xbDHCPSnoopingTxLeaseQuery        Counter32,
    sm24tat4xbDHCPSnoopingTxLeaseUnassigned      Counter32,
    sm24tat4xbDHCPSnoopingTxLeaseUnknown     Counter32,
    sm24tat4xbDHCPSnoopingTxLeaseActive      Counter32,
    sm24tat4xbDHCPSnoopingRxDiscardedChecksumError  Counter32,
    sm24tat4xbDHCPSnoopingRxDiscardedFromUntrusted  Counter32
}

sm24tat4xbDHCPSnoopingStatisticsPort OBJECT-TYPE
    SYNTAX      Integer32(1..4095)
    MAX-ACCESS  not-accessible
    STATUS      current
    DESCRIPTION
        " "
    ::= { sm24tat4xbDHCPSnoopingStatisticsEntry 1 }

sm24tat4xbDHCPSnoopingStatisticsClear OBJECT-TYPE
    SYNTAX      Integer32 (0|1)
    MAX-ACCESS  read-write
    STATUS      current
    DESCRIPTION
        "default: 0
        0: none
        1: clear"
    ::= { sm24tat4xbDHCPSnoopingStatisticsEntry 2 }

sm24tat4xbDHCPSnoopingRxDiscover OBJECT-TYPE
    SYNTAX      Counter32
    MAX-ACCESS  read-only
    STATUS      current
    DESCRIPTION
        " "
    ::= { sm24tat4xbDHCPSnoopingStatisticsEntry 3 }

sm24tat4xbDHCPSnoopingRxOffer OBJECT-TYPE
    SYNTAX      Counter32
    MAX-ACCESS  read-only
    STATUS      current
    DESCRIPTION
        " "
    ::= { sm24tat4xbDHCPSnoopingStatisticsEntry 4 }

sm24tat4xbDHCPSnoopingRxRequest OBJECT-TYPE
    SYNTAX      Counter32
    MAX-ACCESS  read-only
    STATUS      current
    DESCRIPTION
        " "
    ::= { sm24tat4xbDHCPSnoopingStatisticsEntry 5 }

sm24tat4xbDHCPSnoopingRxDecline OBJECT-TYPE
    SYNTAX      Counter32
    MAX-ACCESS  read-only
    STATUS      current
    DESCRIPTION
        " "
    ::= { sm24tat4xbDHCPSnoopingStatisticsEntry 6 }

sm24tat4xbDHCPSnoopingRxACK OBJECT-TYPE
    SYNTAX      Counter32
    MAX-ACCESS  read-only
    STATUS      current
    DESCRIPTION
        " "
    ::= { sm24tat4xbDHCPSnoopingStatisticsEntry 7 }

sm24tat4xbDHCPSnoopingRxNAK OBJECT-TYPE
    SYNTAX      Counter32
    MAX-ACCESS  read-only
    STATUS      current
    DESCRIPTION
        " "
    ::= { sm24tat4xbDHCPSnoopingStatisticsEntry 8 }

sm24tat4xbDHCPSnoopingRxRelease OBJECT-TYPE
    SYNTAX      Counter32
    MAX-ACCESS  read-only
    STATUS      current
    DESCRIPTION
        " "
    ::= { sm24tat4xbDHCPSnoopingStatisticsEntry 9 }

sm24tat4xbDHCPSnoopingRxInform OBJECT-TYPE
    SYNTAX      Counter32
    MAX-ACCESS  read-only
    STATUS      current
    DESCRIPTION
        " "
    ::= { sm24tat4xbDHCPSnoopingStatisticsEntry 10 }

sm24tat4xbDHCPSnoopingRxLeaseQuery OBJECT-TYPE
    SYNTAX      Counter32
    MAX-ACCESS  read-only
    STATUS      current
    DESCRIPTION
        " "
    ::= { sm24tat4xbDHCPSnoopingStatisticsEntry 11 }

sm24tat4xbDHCPSnoopingRxLeaseUnassigned OBJECT-TYPE
    SYNTAX      Counter32
    MAX-ACCESS  read-only
    STATUS      current
    DESCRIPTION
        " "
    ::= { sm24tat4xbDHCPSnoopingStatisticsEntry 12 }

sm24tat4xbDHCPSnoopingRxLeaseUnknown OBJECT-TYPE
    SYNTAX      Counter32
    MAX-ACCESS  read-only
    STATUS      current
    DESCRIPTION
        " "
    ::= { sm24tat4xbDHCPSnoopingStatisticsEntry 13 }

sm24tat4xbDHCPSnoopingRxLeaseActive OBJECT-TYPE
    SYNTAX      Counter32
    MAX-ACCESS  read-only
    STATUS      current
    DESCRIPTION
        " "
    ::= { sm24tat4xbDHCPSnoopingStatisticsEntry 14 }

sm24tat4xbDHCPSnoopingTxDiscover OBJECT-TYPE
    SYNTAX      Counter32
    MAX-ACCESS  read-only
    STATUS      current
    DESCRIPTION
        " "
    ::= { sm24tat4xbDHCPSnoopingStatisticsEntry 15 }

sm24tat4xbDHCPSnoopingTxOffer OBJECT-TYPE
    SYNTAX      Counter32
    MAX-ACCESS  read-only
    STATUS      current
    DESCRIPTION
        " "
    ::= { sm24tat4xbDHCPSnoopingStatisticsEntry 16 }

sm24tat4xbDHCPSnoopingTxRequest OBJECT-TYPE
    SYNTAX      Counter32
    MAX-ACCESS  read-only
    STATUS      current
    DESCRIPTION
        " "
    ::= { sm24tat4xbDHCPSnoopingStatisticsEntry 17 }

sm24tat4xbDHCPSnoopingTxDecline OBJECT-TYPE
    SYNTAX      Counter32
    MAX-ACCESS  read-only
    STATUS      current
    DESCRIPTION
        " "
    ::= { sm24tat4xbDHCPSnoopingStatisticsEntry 18 }

sm24tat4xbDHCPSnoopingTxACK OBJECT-TYPE
    SYNTAX      Counter32
    MAX-ACCESS  read-only
    STATUS      current
    DESCRIPTION
        " "
    ::= { sm24tat4xbDHCPSnoopingStatisticsEntry 19 }

sm24tat4xbDHCPSnoopingTxNAK OBJECT-TYPE
    SYNTAX      Counter32
    MAX-ACCESS  read-only
    STATUS      current
    DESCRIPTION
        " "
    ::= { sm24tat4xbDHCPSnoopingStatisticsEntry 20 }

sm24tat4xbDHCPSnoopingTxRelease OBJECT-TYPE
    SYNTAX      Counter32
    MAX-ACCESS  read-only
    STATUS      current
    DESCRIPTION
        " "
    ::= { sm24tat4xbDHCPSnoopingStatisticsEntry 21 }

sm24tat4xbDHCPSnoopingTxInform OBJECT-TYPE
    SYNTAX      Counter32
    MAX-ACCESS  read-only
    STATUS      current
    DESCRIPTION
        " "
    ::= { sm24tat4xbDHCPSnoopingStatisticsEntry 22 }

sm24tat4xbDHCPSnoopingTxLeaseQuery OBJECT-TYPE
    SYNTAX      Counter32
    MAX-ACCESS  read-only
    STATUS      current
    DESCRIPTION
        " "
    ::= { sm24tat4xbDHCPSnoopingStatisticsEntry 23 }

sm24tat4xbDHCPSnoopingTxLeaseUnassigned OBJECT-TYPE
    SYNTAX      Counter32
    MAX-ACCESS  read-only
    STATUS      current
    DESCRIPTION
        " "
    ::= { sm24tat4xbDHCPSnoopingStatisticsEntry 24 }

sm24tat4xbDHCPSnoopingTxLeaseUnknown OBJECT-TYPE
    SYNTAX      Counter32
    MAX-ACCESS  read-only
    STATUS      current
    DESCRIPTION
        " "
    ::= { sm24tat4xbDHCPSnoopingStatisticsEntry 25 }

sm24tat4xbDHCPSnoopingTxLeaseActive OBJECT-TYPE
    SYNTAX      Counter32
    MAX-ACCESS  read-only
    STATUS      current
    DESCRIPTION
        " "
    ::= { sm24tat4xbDHCPSnoopingStatisticsEntry 26 }

sm24tat4xbDHCPSnoopingRxDiscardedChecksumError OBJECT-TYPE
    SYNTAX      Counter32
    MAX-ACCESS  read-only
    STATUS      current
    DESCRIPTION
        " "
    ::= { sm24tat4xbDHCPSnoopingStatisticsEntry 27 }

sm24tat4xbDHCPSnoopingRxDiscardedFromUntrusted OBJECT-TYPE
    SYNTAX      Counter32
    MAX-ACCESS  read-only
    STATUS      current
    DESCRIPTION
        " "
    ::= { sm24tat4xbDHCPSnoopingStatisticsEntry 28 }

sm24tat4xbDHCPRelay                         OBJECT IDENTIFIER ::= { sm24tat4xbSecurity 4 }

sm24tat4xbDHCPRelayConfiguration                     OBJECT IDENTIFIER ::= { sm24tat4xbDHCPRelay 1 }

sm24tat4xbDHCPRelayMode OBJECT-TYPE
    SYNTAX      Integer32(0|1)
    MAX-ACCESS  read-write
    STATUS      current
    DESCRIPTION
        "default: 0
        0: disable
        1: enable
        We need at least one server"
    ::= { sm24tat4xbDHCPRelayConfiguration 1 }

sm24tat4xbDHCPRelayServer OBJECT-TYPE
    SYNTAX      IpAddress
    MAX-ACCESS  read-write
    STATUS      current
    DESCRIPTION
        " "
    ::= { sm24tat4xbDHCPRelayConfiguration 2 }

sm24tat4xbDHCPRelayInformationMode OBJECT-TYPE
    SYNTAX      Integer32(0|1)
    MAX-ACCESS  read-write
    STATUS      current
    DESCRIPTION
        "default: 0
        0: disable
        1: enable "
    ::= { sm24tat4xbDHCPRelayConfiguration 3 }

sm24tat4xbDHCPRelayInformationPolicy OBJECT-TYPE
    SYNTAX      Integer32(0..2)
    MAX-ACCESS  read-write
    STATUS      current
    DESCRIPTION
        "default: 0
        0: replace
        1: keep
        2: drop "
    ::= { sm24tat4xbDHCPRelayConfiguration 4 }

sm24tat4xbDHCPRelayStatistics                    OBJECT IDENTIFIER ::= { sm24tat4xbDHCPRelay 2 }

sm24tat4xbDHCPRelayServerStatistics                    OBJECT IDENTIFIER ::= { sm24tat4xbDHCPRelayStatistics 1 }

sm24tat4xbServerStatTransmitToServer OBJECT-TYPE
    SYNTAX      Counter32
    MAX-ACCESS  read-only
    STATUS      current
    DESCRIPTION
        " "
    ::= { sm24tat4xbDHCPRelayServerStatistics 1 }

sm24tat4xbServerStatTransmitError OBJECT-TYPE
    SYNTAX      Counter32
    MAX-ACCESS  read-only
    STATUS      current
    DESCRIPTION
        " "
    ::= { sm24tat4xbDHCPRelayServerStatistics 2 }

sm24tat4xbServerStatReceiveFromServer OBJECT-TYPE
    SYNTAX      Counter32
    MAX-ACCESS  read-only
    STATUS      current
    DESCRIPTION
        " "
    ::= { sm24tat4xbDHCPRelayServerStatistics 3 }

sm24tat4xbServerStatReceiveMissingAgentOption OBJECT-TYPE
    SYNTAX      Counter32
    MAX-ACCESS  read-only
    STATUS      current
    DESCRIPTION
        " "
    ::= { sm24tat4xbDHCPRelayServerStatistics 4 }

sm24tat4xbServerStatReceiveMissingCircuitID OBJECT-TYPE
    SYNTAX      Counter32
    MAX-ACCESS  read-only
    STATUS      current
    DESCRIPTION
        " "
    ::= { sm24tat4xbDHCPRelayServerStatistics 5 }

sm24tat4xbServerStatReceiveMissingRemoteID OBJECT-TYPE
    SYNTAX      Counter32
    MAX-ACCESS  read-only
    STATUS      current
    DESCRIPTION
        " "
    ::= { sm24tat4xbDHCPRelayServerStatistics 6 }

sm24tat4xbServerStatReceiveBadCircuitID OBJECT-TYPE
    SYNTAX      Counter32
    MAX-ACCESS  read-only
    STATUS      current
    DESCRIPTION
        " "
    ::= { sm24tat4xbDHCPRelayServerStatistics 7 }

sm24tat4xbServerStatReceiveBadRemoteID OBJECT-TYPE
    SYNTAX      Counter32
    MAX-ACCESS  read-only
    STATUS      current
    DESCRIPTION
        " "
    ::= { sm24tat4xbDHCPRelayServerStatistics 8 }

sm24tat4xbDHCPRelayClientStatistics                    OBJECT IDENTIFIER ::= { sm24tat4xbDHCPRelayStatistics 2 }

sm24tat4xbClientStatTransmitToClient OBJECT-TYPE
    SYNTAX      Counter32
    MAX-ACCESS  read-only
    STATUS      current
    DESCRIPTION
        " "
    ::= { sm24tat4xbDHCPRelayClientStatistics 1 }

sm24tat4xbClientStatTransmitError OBJECT-TYPE
    SYNTAX      Counter32
    MAX-ACCESS  read-only
    STATUS      current
    DESCRIPTION
        " "
    ::= { sm24tat4xbDHCPRelayClientStatistics 2 }

sm24tat4xbClientStatReceivefromClient OBJECT-TYPE
    SYNTAX      Counter32
    MAX-ACCESS  read-only
    STATUS      current
    DESCRIPTION
        " "
    ::= { sm24tat4xbDHCPRelayClientStatistics 3 }

sm24tat4xbClientStatReceiveAgentOption OBJECT-TYPE
    SYNTAX      Counter32
    MAX-ACCESS  read-only
    STATUS      current
    DESCRIPTION
        " "
    ::= { sm24tat4xbDHCPRelayClientStatistics 4 }

sm24tat4xbClientStatReplaceAgentOption OBJECT-TYPE
    SYNTAX      Counter32
    MAX-ACCESS  read-only
    STATUS      current
    DESCRIPTION
        " "
    ::= { sm24tat4xbDHCPRelayClientStatistics 5 }

sm24tat4xbClientStatKeepAgentOption OBJECT-TYPE
    SYNTAX      Counter32
    MAX-ACCESS  read-only
    STATUS      current
    DESCRIPTION
        " "
    ::= { sm24tat4xbDHCPRelayClientStatistics 6 }

sm24tat4xbClientStatDropAgentOption OBJECT-TYPE
    SYNTAX      Counter32
    MAX-ACCESS  read-only
    STATUS      current
    DESCRIPTION
        " "
    ::= { sm24tat4xbDHCPRelayClientStatistics 7 }

sm24tat4xbPortSecurity                      OBJECT IDENTIFIER ::= { sm24tat4xbSecurity 5 }

sm24tat4xbPortSecLimitCtrl                      OBJECT IDENTIFIER ::= { sm24tat4xbPortSecurity 1 }

sm24tat4xbPortSecLimitCtrlSystemConf                      OBJECT IDENTIFIER ::= { sm24tat4xbPortSecLimitCtrl 1 }

-- sm24tat4xbPortSecurityMode OBJECT-TYPE
--    SYNTAX      Integer32(0|1)
--    MAX-ACCESS  read-write
--    STATUS      current
--    DESCRIPTION
--    "default: 0
--    0: disable
--    1: enable "
--    ::= { sm24tat4xbPortSecLimitCtrlSystemConf 1 }

sm24tat4xbPortSecurityAging OBJECT-TYPE
    SYNTAX      Integer32(0|1)
    MAX-ACCESS  read-write
    STATUS      current
    DESCRIPTION
        "default: 0
        0: disable
        1: enable "
    ::= { sm24tat4xbPortSecLimitCtrlSystemConf 1 }

sm24tat4xbPortSecurityAgingPeriod OBJECT-TYPE
    SYNTAX      Integer32(10..10000000)
    MAX-ACCESS  read-write
    STATUS      current
    DESCRIPTION
        "default: 3600, range: 10-10000000 "
    ::= { sm24tat4xbPortSecLimitCtrlSystemConf 2 }

sm24tat4xbPortSecurityHoldTime OBJECT-TYPE
    SYNTAX      Integer32(10..10000000)
    MAX-ACCESS  read-write
    STATUS      current
    DESCRIPTION
        "default: 300, range: 10-10000000 "
    ::= { sm24tat4xbPortSecLimitCtrlSystemConf 3 }

sm24tat4xbPortSecLimitCtrlTable OBJECT-TYPE
    SYNTAX      SEQUENCE OF SM24TAT4XBPortSecLimitCtrlEntry
    MAX-ACCESS  not-accessible
    STATUS      current
    DESCRIPTION
        " "
    ::= { sm24tat4xbPortSecLimitCtrl 2 }

sm24tat4xbPortSecLimitCtrlEntry OBJECT-TYPE
    SYNTAX      SM24TAT4XBPortSecLimitCtrlEntry
    MAX-ACCESS  not-accessible
    STATUS      current
    DESCRIPTION
        " "
    INDEX    { sm24tat4xbPortSecLimitCtrlPort  }
    ::= { sm24tat4xbPortSecLimitCtrlTable 1 }

SM24TAT4XBPortSecLimitCtrlEntry ::= SEQUENCE {
    sm24tat4xbPortSecLimitCtrlPort        Integer32,
    sm24tat4xbPortSecLimitCtrlPortMode        Integer32,
    sm24tat4xbPortSecLimitCtrlPortLimit        Integer32,
    sm24tat4xbPortSecLimitCtrlPortViolationmMode  Integer32,
    sm24tat4xbPortSecLimitCtrlPortViolationmLimit Integer32,
    sm24tat4xbPortSecLimitCtrlPortState        DisplayString,
    sm24tat4xbPortSecLimitCtrlPortReOpen      Integer32,
    sm24tat4xbPortSecLimitCtrlPortSticky      Integer32,
    sm24tat4xbPortSecLimitCtrlPortClear        Integer32
}

sm24tat4xbPortSecLimitCtrlPort OBJECT-TYPE
    SYNTAX      Integer32(1..65535)
    MAX-ACCESS  not-accessible
    STATUS      current
    DESCRIPTION
        " "
    ::= { sm24tat4xbPortSecLimitCtrlEntry 1 }

sm24tat4xbPortSecLimitCtrlPortMode OBJECT-TYPE
    SYNTAX      Integer32 (0|1)
    MAX-ACCESS  read-write
    STATUS      current
    DESCRIPTION
        "default: 0
        0: disable
        1: enable"
    ::= { sm24tat4xbPortSecLimitCtrlEntry 2 }

sm24tat4xbPortSecLimitCtrlPortLimit OBJECT-TYPE
    SYNTAX      Integer32(1..1024)
    MAX-ACCESS  read-write
    STATUS      current
    DESCRIPTION
        "default: 4, range: 1-1024"
    ::= { sm24tat4xbPortSecLimitCtrlEntry 3 }

sm24tat4xbPortSecLimitCtrlPortViolationmMode OBJECT-TYPE
    SYNTAX      Integer32(0..2)
    MAX-ACCESS  read-write
    STATUS      current
    DESCRIPTION
        "default: 0
        0: Protect
        1: Restrict
        2: Shutdown"
    ::= { sm24tat4xbPortSecLimitCtrlEntry 4 }

sm24tat4xbPortSecLimitCtrlPortViolationmLimit OBJECT-TYPE
    SYNTAX      Integer32(1..1024)
    MAX-ACCESS  read-write
    STATUS      current
    DESCRIPTION
        "default: 4, range: 1-1024"
    ::= { sm24tat4xbPortSecLimitCtrlEntry 5 }


sm24tat4xbPortSecLimitCtrlPortState OBJECT-TYPE
    SYNTAX      DisplayString
    MAX-ACCESS  read-only
    STATUS      current
    DESCRIPTION
        " "
    ::= { sm24tat4xbPortSecLimitCtrlEntry 6 }

sm24tat4xbPortSecLimitCtrlPortReOpen OBJECT-TYPE
    SYNTAX      Integer32 (0|1)
    MAX-ACCESS  read-write
    STATUS      current
    DESCRIPTION
        "default: 0
        0: none
        1: reopen"
    ::= { sm24tat4xbPortSecLimitCtrlEntry 7 }

sm24tat4xbPortSecLimitCtrlPortSticky OBJECT-TYPE
    SYNTAX      Integer32 (0|1)
    MAX-ACCESS  read-write
    STATUS      current
    DESCRIPTION
        "default: 0
        0: disable
        1: enable"
    ::= { sm24tat4xbPortSecLimitCtrlEntry 8 }

sm24tat4xbPortSecLimitCtrlPortClear OBJECT-TYPE
    SYNTAX      Integer32 (0|1)
    MAX-ACCESS  read-write
    STATUS      current
    DESCRIPTION
        "default: 0
        1: clear"
    ::= { sm24tat4xbPortSecLimitCtrlEntry 9 }


sm24tat4xbPortSecSwitchStatusTable OBJECT-TYPE
    SYNTAX      SEQUENCE OF SM24TAT4XBPortSecSwitchStatusEntry
    MAX-ACCESS  not-accessible
    STATUS      current
    DESCRIPTION
        " "
    ::= { sm24tat4xbPortSecurity 2 }

sm24tat4xbPortSecSwitchStatusEntry OBJECT-TYPE
    SYNTAX      SM24TAT4XBPortSecSwitchStatusEntry
    MAX-ACCESS  not-accessible
    STATUS      current
    DESCRIPTION
        " "
    INDEX    { sm24tat4xbPortSecSwitchStatusPort  }
    ::= { sm24tat4xbPortSecSwitchStatusTable 1 }

SM24TAT4XBPortSecSwitchStatusEntry ::= SEQUENCE {
    sm24tat4xbPortSecSwitchStatusPort        Integer32,
--    sm24tat4xbPortSecSwitchStatusUsers        DisplayString,
    sm24tat4xbPortSecSwitchStatusViolationmMode      DisplayString,
    sm24tat4xbPortSecSwitchStatusState        DisplayString,
    sm24tat4xbPortSecSwitchStatusMACCountCurrent     Integer32,
    sm24tat4xbPortSecSwitchStatusMACCountViolating    Integer32,
    sm24tat4xbPortSecSwitchStatusMACCountLimit    Integer32,
    sm24tat4xbPortSecSwitchStatusClear        Integer32
}

sm24tat4xbPortSecSwitchStatusPort OBJECT-TYPE
    SYNTAX      Integer32(1..65535)
    MAX-ACCESS  not-accessible
    STATUS      current
    DESCRIPTION
        " "
    ::= { sm24tat4xbPortSecSwitchStatusEntry 1 }

-- sm24tat4xbPortSecSwitchStatusUsers OBJECT-TYPE
--    SYNTAX      DisplayString
--    MAX-ACCESS  read-only
--    STATUS      current
--    DESCRIPTION
--    " Users Abbr: L = Limit Control, 8 = 802.1X, D = DHCP Snooping, V = Voice VLAN,
--     '-' means that the corresponding user module is not enabled. "
--    ::= { sm24tat4xbPortSecSwitchStatusEntry 2 }

sm24tat4xbPortSecSwitchStatusViolationmMode OBJECT-TYPE
    SYNTAX      DisplayString
    MAX-ACCESS  read-only
    STATUS      current
    DESCRIPTION
        "Shows the configured Violation Mode of the port."
    ::= { sm24tat4xbPortSecSwitchStatusEntry 3 }

sm24tat4xbPortSecSwitchStatusState OBJECT-TYPE
    SYNTAX      DisplayString
    MAX-ACCESS  read-only
    STATUS      current
    DESCRIPTION
        " Shows the current state of the port : Disabled, Ready, Limit Reached, Shutdown. "
    ::= { sm24tat4xbPortSecSwitchStatusEntry 4 }

sm24tat4xbPortSecSwitchStatusMACCountCurrent OBJECT-TYPE
    SYNTAX      Integer32
    MAX-ACCESS  read-only
    STATUS      current
    DESCRIPTION
        " "
    ::= { sm24tat4xbPortSecSwitchStatusEntry 5 }

sm24tat4xbPortSecSwitchStatusMACCountViolating OBJECT-TYPE
    SYNTAX      Integer32
    MAX-ACCESS  read-only
    STATUS      current
    DESCRIPTION
        " "
    ::= { sm24tat4xbPortSecSwitchStatusEntry 6 }

sm24tat4xbPortSecSwitchStatusMACCountLimit OBJECT-TYPE
    SYNTAX      Integer32
    MAX-ACCESS  read-only
    STATUS      current
    DESCRIPTION
        " "
    ::= { sm24tat4xbPortSecSwitchStatusEntry 7 }

sm24tat4xbPortSecSwitchStatusClear OBJECT-TYPE
    SYNTAX      Integer32 (0|1)
    MAX-ACCESS  read-write
    STATUS      current
    DESCRIPTION
        "Remove all MAC addresses on all VLANs on this port."
    ::= { sm24tat4xbPortSecSwitchStatusEntry 8 }

sm24tat4xbPortSecPortStatus                      OBJECT IDENTIFIER ::= { sm24tat4xbPortSecurity 3 }

sm24tat4xbPortSecPortStatusPort OBJECT-TYPE
    SYNTAX    Integer32
    MAX-ACCESS    read-write
    STATUS    current
    DESCRIPTION
        "port number
        default: 1
        range: 1 - port number."
    ::= { sm24tat4xbPortSecPortStatus 1 }

sm24tat4xbPortSecPortStatusTable OBJECT-TYPE
    SYNTAX      SEQUENCE OF SM24TAT4XBPortSecPortStatusEntry
    MAX-ACCESS  not-accessible
    STATUS      current
    DESCRIPTION
          " "
    ::= { sm24tat4xbPortSecPortStatus 2 }

sm24tat4xbPortSecPortStatusEntry OBJECT-TYPE
    SYNTAX      SM24TAT4XBPortSecPortStatusEntry
    MAX-ACCESS  not-accessible
    STATUS      current
    DESCRIPTION
        " "
    INDEX    { sm24tat4xbPortSecPortStatusIndex  }
    ::= { sm24tat4xbPortSecPortStatusTable 1 }

SM24TAT4XBPortSecPortStatusEntry ::= SEQUENCE {
    sm24tat4xbPortSecPortStatusIndex          Integer32,
    sm24tat4xbPortSecPortStatusMACAddress     DisplayString,
    sm24tat4xbPortSecPortStatusVLANId         Integer32,
    sm24tat4xbPortSecPortStatusState          DisplayString,
    sm24tat4xbPortSecPortStatusAgeAndHold     DisplayString,
    sm24tat4xbPortSecPortStatusClear          Integer32
}

sm24tat4xbPortSecPortStatusIndex OBJECT-TYPE
    SYNTAX      Integer32(1..65535)
    MAX-ACCESS  not-accessible
    STATUS      current
    DESCRIPTION
        " "
    ::= { sm24tat4xbPortSecPortStatusEntry 1 }

sm24tat4xbPortSecPortStatusMACAddress OBJECT-TYPE
    SYNTAX      DisplayString
    MAX-ACCESS  read-only
    STATUS      current
    DESCRIPTION
        "MAC address that is seen on this port."
    ::= { sm24tat4xbPortSecPortStatusEntry 2 }

sm24tat4xbPortSecPortStatusVLANId OBJECT-TYPE
    SYNTAX      Integer32(1..4094)
    MAX-ACCESS  read-only
    STATUS      current
    DESCRIPTION
        "VLAN ID that is seen on this port"
    ::= { sm24tat4xbPortSecPortStatusEntry 3 }

sm24tat4xbPortSecPortStatusState OBJECT-TYPE
    SYNTAX      DisplayString
    MAX-ACCESS  read-only
    STATUS      current
    DESCRIPTION
        "Indicates whether the corresponding MAC address is violating
	    (administrative user has configured the interface in Restrict mode and the MAC address is blocked),
	    blocked, or forwarding."
    ::= { sm24tat4xbPortSecPortStatusEntry 4 }

sm24tat4xbPortSecPortStatusAgeAndHold OBJECT-TYPE
    SYNTAX      DisplayString
    MAX-ACCESS  read-only
    STATUS      current
    DESCRIPTION
        " "
    ::= { sm24tat4xbPortSecPortStatusEntry 5 }

sm24tat4xbPortSecPortStatusClear OBJECT-TYPE
    SYNTAX      Integer32(0|1)
    MAX-ACCESS  read-write
    STATUS      current
    DESCRIPTION
        "Remove particular MAC addresses from MAC table
	    1:clear"
    ::= { sm24tat4xbPortSecPortStatusEntry 6 }

sm24tat4xbAccessManagement                      OBJECT IDENTIFIER ::= { sm24tat4xbSecurity 6 }

sm24tat4xbAccessMgmtConf                     OBJECT IDENTIFIER ::= { sm24tat4xbAccessManagement 1 }

sm24tat4xbAccessMgmtStatistics                    OBJECT IDENTIFIER ::= { sm24tat4xbAccessManagement 2 }
--
-- =======================================================================================================================
-- Start sm24tat4xbAccessManagement group
-- =======================================================================================================================
--sm24tat4xbAccessMgmtConf

    sm24tat4xbAccessMgmtConfMode OBJECT-TYPE
        SYNTAX      AdminMode
        MAX-ACCESS  read-write
        STATUS      current
        DESCRIPTION
            "Indicates the access management mode operation."
        DEFVAL  { disable }
        ::= {     sm24tat4xbAccessMgmtConf 1 }

--sm24tat4xbAccessMgmtConfTable

    sm24tat4xbAccessMgmtConfTable OBJECT-TYPE
        SYNTAX      SEQUENCE OF     SM24TAT4XBAccessMgmtConfEntry
        MAX-ACCESS  not-accessible
        STATUS      current
        DESCRIPTION
            "The Access Mgmt Conf Table. "
        ::= {     sm24tat4xbAccessMgmtConf 2 }

    sm24tat4xbAccessMgmtConfEntry OBJECT-TYPE
        SYNTAX      SM24TAT4XBAccessMgmtConfEntry
        MAX-ACCESS  not-accessible
        STATUS      current
        DESCRIPTION
            "The Access Mgmt Conf Entry "
        INDEX    {    sm24tat4xbAccessMgmtIndex  }
        ::= {     sm24tat4xbAccessMgmtConfTable 1 }

    SM24TAT4XBAccessMgmtConfEntry         ::= SEQUENCE {
         sm24tat4xbAccessMgmtIndex        Integer32,
         sm24tat4xbAccessMgmtVlanID        Integer32,
         sm24tat4xbAccessMgmtStartIpAddress    IpAddress,
         sm24tat4xbAccessMgmtEndIpAddress     IpAddress,
         sm24tat4xbAccessMgmtHttpHttps    AdminMode,
         sm24tat4xbAccessMgmtSNMP         AdminMode,
         sm24tat4xbAccessMgmtTelnetSSH    AdminMode,
         sm24tat4xbAccessMgmtRowStatus    RowStatus
         }

    sm24tat4xbAccessMgmtIndex OBJECT-TYPE
        SYNTAX      Integer32(1..16)
        MAX-ACCESS  not-accessible
        STATUS      current
        DESCRIPTION
            "The Access Management config index.
            range : 1-16."
        ::= {     sm24tat4xbAccessMgmtConfEntry 1 }

    sm24tat4xbAccessMgmtVlanID OBJECT-TYPE
        SYNTAX      Integer32 (1..4095)
        MAX-ACCESS  read-create
        STATUS      current
        DESCRIPTION
            "The VLAN ID for the access management entry.
            range: 1-4095."
        ::= {     sm24tat4xbAccessMgmtConfEntry 2 }

    sm24tat4xbAccessMgmtStartIpAddress OBJECT-TYPE
        SYNTAX      IpAddress
        MAX-ACCESS  read-create
        STATUS      current
        DESCRIPTION
            "The start IP address for the access management
            entry."
        ::= {     sm24tat4xbAccessMgmtConfEntry 3 }

    sm24tat4xbAccessMgmtEndIpAddress OBJECT-TYPE
        SYNTAX      IpAddress
        MAX-ACCESS  read-create
        STATUS      current
        DESCRIPTION
            "The end IP address for the access management
            entry. "
        ::= {     sm24tat4xbAccessMgmtConfEntry 4 }

    sm24tat4xbAccessMgmtHttpHttps OBJECT-TYPE
        SYNTAX      AdminMode
        MAX-ACCESS  read-create
        STATUS      current
        DESCRIPTION
            "Indicates that the host can access the switch from
            HTTP/HTTPS interface if the host IP address matches the IP
            address range provided in the entry."
        DEFVAL  { disable }
        ::= {     sm24tat4xbAccessMgmtConfEntry 5 }

    sm24tat4xbAccessMgmtSNMP OBJECT-TYPE
        SYNTAX      AdminMode
        MAX-ACCESS  read-create
        STATUS      current
        DESCRIPTION
            "Indicates that the host can access the switch from SNMP
            interface if the host IP address matches the IP address
            range provided in the entry."
        DEFVAL  { disable }
        ::= {     sm24tat4xbAccessMgmtConfEntry 6 }

    sm24tat4xbAccessMgmtTelnetSSH OBJECT-TYPE
        SYNTAX      AdminMode
        MAX-ACCESS  read-create
        STATUS      current
        DESCRIPTION
            "Indicates that the host can access the switch from
            TELNET/SSH interface if the host IP address matches
            the IP address range provided in the entry."
        DEFVAL  { disable }
        ::= {     sm24tat4xbAccessMgmtConfEntry 7 }

    sm24tat4xbAccessMgmtRowStatus OBJECT-TYPE
        SYNTAX      RowStatus
        MAX-ACCESS  read-create
        STATUS      current
        DESCRIPTION
            "This object indicates the status of this entry, and is used
            to create/delete entries.  Any object in an entry of this
            table may be modified while the value of the corresponding
            instance of this object is active(1).
            createAndGo, notReady not supported."
        ::= {     sm24tat4xbAccessMgmtConfEntry 8 }

--sm24tat4xbAccessMgmtStatistics

    sm24tat4xbAccessMgmtStatisticsClear OBJECT-TYPE
        SYNTAX      ActivateCmd
        MAX-ACCESS  read-write
        STATUS      current
        DESCRIPTION
            "Clear all statistics."
        ::= {     sm24tat4xbAccessMgmtStatistics 1 }

--sm24tat4xbAccessMgmtStatisticsTable

    sm24tat4xbAccessMgmtStatisticsTable OBJECT-TYPE
        SYNTAX      SEQUENCE OF     SM24TAT4XBAccessMgmtStatisticsEntry
        MAX-ACCESS  not-accessible
        STATUS      current
        DESCRIPTION
            "The Access Mgmt Statistics Table. "
        ::= {     sm24tat4xbAccessMgmtStatistics 2 }

    sm24tat4xbAccessMgmtStatisticsEntry OBJECT-TYPE
        SYNTAX      SM24TAT4XBAccessMgmtStatisticsEntry
        MAX-ACCESS  not-accessible
        STATUS      current
        DESCRIPTION
            "The Access Mgmt Statistics Entry. "
        INDEX    {    sm24tat4xbAccessMgmtStatisticsInterface  }
        ::= {     sm24tat4xbAccessMgmtStatisticsTable 1 }

    SM24TAT4XBAccessMgmtStatisticsEntry ::= SEQUENCE {
         sm24tat4xbAccessMgmtStatisticsInterface     INTEGER,
         sm24tat4xbAccessMgmtStatisticsReceivedPackets    Integer32,
         sm24tat4xbAccessMgmtStatisticsAllowedPackets    Integer32,
         sm24tat4xbAccessMgmtStatisticsDiscardedPackets  Integer32
         }

    sm24tat4xbAccessMgmtStatisticsInterface OBJECT-TYPE
        SYNTAX      INTEGER { http(1), https(2), snmp(3), telnet(4), ssh (5) }
        MAX-ACCESS  not-accessible
        STATUS      current
        DESCRIPTION
            "The interface type through which the remote host can
            access the switch.
            1: HTTP,
            2: HTTPs,
            3: SNMP,
            4: TELNET,
            5: SSH"
        ::= {     sm24tat4xbAccessMgmtStatisticsEntry 1 }

    sm24tat4xbAccessMgmtStatisticsReceivedPackets OBJECT-TYPE
        SYNTAX      Integer32(1..10000000)
        MAX-ACCESS  read-only
        STATUS      current
        DESCRIPTION
            "Number of received packets from the interface when
            access management mode is enabled. "
        ::= {     sm24tat4xbAccessMgmtStatisticsEntry 2 }

    sm24tat4xbAccessMgmtStatisticsAllowedPackets OBJECT-TYPE
        SYNTAX      Integer32(1..10000000)
        MAX-ACCESS  read-only
        STATUS      current
        DESCRIPTION
            "Number of allowed packets from the interface when
            access management mode is enabled. "
        ::= {     sm24tat4xbAccessMgmtStatisticsEntry 3 }

    sm24tat4xbAccessMgmtStatisticsDiscardedPackets OBJECT-TYPE
        SYNTAX      Integer32(1..10000000)
        MAX-ACCESS  read-only
        STATUS      current
        DESCRIPTION
            "Number of discarded packets from the interface when
            access management mode is enabled. "
        ::= {     sm24tat4xbAccessMgmtStatisticsEntry 4 }

-- =======================================================================================================================

--sm24tat4xbSSH                            OBJECT IDENTIFIER ::= { sm24tat4xbSecurity 7 }
--
--sm24tat4xbSSHMode OBJECT-TYPE
--    SYNTAX      Integer32(0|1)
--    MAX-ACCESS  read-write
--    STATUS      current
--    DESCRIPTION
--    "default: 1
--    0: disable
--    1: enable"
--    ::= { sm24tat4xbSSH 1 }

--sm24tat4xbSSHPort OBJECT-TYPE
--    SYNTAX      Integer32(1..65535)
--    MAX-ACCESS  read-write
--    STATUS      current
--    DESCRIPTION
--    "SSH service port number.
--    range : 1-65535, default : 22."
--    ::= { sm24tat4xbSSH 2 }

sm24tat4xbHTTPS                         OBJECT IDENTIFIER ::= { sm24tat4xbSecurity 8 }
--
--sm24tat4xbHTTPSMode OBJECT-TYPE
--    SYNTAX      Integer32(0|1)
--    MAX-ACCESS  read-write
--    STATUS      current
--    DESCRIPTION
--    "default: 1
--    0: disable
--    1: enable"
--    ::= { sm24tat4xbHTTPS 1 }
--
--sm24tat4xbHTTPSAutoRedirect OBJECT-TYPE
--    SYNTAX      Integer32(0|1)
--    MAX-ACCESS  read-write
--    STATUS      current
--    DESCRIPTION
--    "default: 0
--    0: disable
--    1: enable"
--    ::= { sm24tat4xbHTTPS 2 }
--
--sm24tat4xbHTTPSPort OBJECT-TYPE
--    SYNTAX      Integer32(1..65535)
--    MAX-ACCESS  read-write
--    STATUS      current
--    DESCRIPTION
--    "HTTPS service port number.
--    range : 1-65535, default : 443."
--    ::= { sm24tat4xbHTTPS 3 }
--
sm24tat4xbHTTPSCertificateMaintain OBJECT-TYPE
    SYNTAX      Integer32(2..3)
    MAX-ACCESS  read-write
    STATUS      current
    DESCRIPTION
        "2: Upload
		3: Generate"
    ::= { sm24tat4xbHTTPS 4 }

sm24tat4xbHTTPSCertificatePassPhrase OBJECT-TYPE
    SYNTAX      DisplayString
    MAX-ACCESS  read-write
    STATUS      current
    DESCRIPTION
        "Enter the pass phrase in this field if your uploading certificate is protected by a specific passphrase."
    ::= { sm24tat4xbHTTPS 5 }

sm24tat4xbHTTPSCertificateUpload OBJECT-TYPE
    SYNTAX      Integer32(0|1)
    MAX-ACCESS  read-write
    STATUS      current
    DESCRIPTION
        "default: 0
        0: TFTP
        1: URL"
    ::= { sm24tat4xbHTTPS 6 }

sm24tat4xbHTTPSFileUploadFileURL OBJECT-TYPE
    SYNTAX      DisplayString
    MAX-ACCESS  read-write
    STATUS      current
    DESCRIPTION
        "TFTP: filename
	    URL: URL"
    ::= { sm24tat4xbHTTPS 7 }

sm24tat4xbHTTPSFileUploadTFTPServer OBJECT-TYPE
    SYNTAX    IpAddress
    MAX-ACCESS    read-write
    STATUS    current
    DESCRIPTION
		"TFTP server IP address"
    ::= { sm24tat4xbHTTPS 8 }

sm24tat4xbHTTPSApply OBJECT-TYPE
    SYNTAX      Integer32(0|1)
    MAX-ACCESS  read-write
    STATUS      current
    DESCRIPTION
        "1: apply the above https settings"
    ::= { sm24tat4xbHTTPS 9 }

sm24tat4xbHTTPSCertificateStatus OBJECT-TYPE
    SYNTAX      DisplayString
    MAX-ACCESS  read-only
    STATUS      current
    DESCRIPTION
        "Display the current status of certificate on the switch."
    ::= { sm24tat4xbHTTPS 10 }

sm24tat4xbAuthMethod                        OBJECT IDENTIFIER ::= { sm24tat4xbSecurity 9 }

--
-- =======================================================================================================================
-- Start sm24tat4xbAuthMethodConfig group
-- =======================================================================================================================
--sm24tat4xbAuthMethodConfigTable

    sm24tat4xbAuthMethodConfigTable OBJECT-TYPE
        SYNTAX      SEQUENCE OF     SM24TAT4XBAuthMethodConfigEntry
        MAX-ACCESS  not-accessible
        STATUS      current
        DESCRIPTION
            "The Auth Method Config Table."
        ::= {     sm24tat4xbAuthMethod 1 }

    sm24tat4xbAuthMethodConfigEntry OBJECT-TYPE
        SYNTAX      SM24TAT4XBAuthMethodConfigEntry
        MAX-ACCESS  not-accessible
        STATUS      current
        DESCRIPTION
            "The Auth Method Config Entry."
        INDEX    {    sm24tat4xbAuthMethodConfigClient  }
        ::= {     sm24tat4xbAuthMethodConfigTable 1 }

    SM24TAT4XBAuthMethodConfigEntry         ::= SEQUENCE {
         sm24tat4xbAuthMethodConfigClient    INTEGER,
         sm24tat4xbAuthMethodConfigMethod1    INTEGER,
         sm24tat4xbAuthMethodConfigMethod2    INTEGER,
         sm24tat4xbAuthMethodConfigMethod3    INTEGER,
         sm24tat4xbAuthMethodConfigMethod4    INTEGER,
         sm24tat4xbAuthMethodConfigServicePort    Integer32
         }

    sm24tat4xbAuthMethodConfigClient OBJECT-TYPE
        SYNTAX      INTEGER  {  console ( 1 ),
                    telnet ( 2 ),
                    ssh ( 3 ),
                    http ( 4 ),
                    https ( 5 )
                    }
        MAX-ACCESS  not-accessible
        STATUS      current
        DESCRIPTION
            "1: console.
            2: telnet.
            3: ssh.
            4: http.
            5: https. "
        ::= {     sm24tat4xbAuthMethodConfigEntry 1 }

    sm24tat4xbAuthMethodConfigMethod1 OBJECT-TYPE
        SYNTAX      INTEGER {no(0) ,redirect(1) ,local(2) ,radius(3) ,tacacs(4)}
        MAX-ACCESS  read-write
        STATUS      current
        DESCRIPTION
            "Methods that involves remote servers are timed out if the
            remote servers are offline.Each method is tried from left to
            right and continues until a method either approves or
            rejects a user.
            0: no, Authentication is disabled and login is not possible.
            1: redirect, When HTTPS is enabled, enable HTTPS automatic redirect on the switch.
            2: local, Use the local user database on the switch for
            authentication.
            3: radius, Use remote RADIUS server(s) for authentication.
            4: tacacs+, Use remote TACACS+ server(s) for authentication."
        ::= {     sm24tat4xbAuthMethodConfigEntry 2 }

    sm24tat4xbAuthMethodConfigMethod2 OBJECT-TYPE
        SYNTAX      INTEGER {no(0) ,redirect(1) ,local(2) ,radius(3) ,tacacs(4)}
        MAX-ACCESS  read-write
        STATUS      current
        DESCRIPTION
            "Methods that involves remote servers are timed out if the
            remote servers are offline.Each method is tried from left to
            right and continues until a method either approves or
            rejects a user.
            0: no, Authentication is disabled and login is not possible.
            1: redirect, When HTTPS is enabled, enable HTTPS automatic redirect on the switch.
            2: local, Use the local user database on the switch for
            authentication.
            3: radius, Use remote RADIUS server(s) for authentication.
            4: tacacs+, Use remote TACACS+ server(s) for authentication."
        ::= {     sm24tat4xbAuthMethodConfigEntry 3 }

    sm24tat4xbAuthMethodConfigMethod3 OBJECT-TYPE
        SYNTAX      INTEGER {no(0) ,redirect(1) ,local(2) ,radius(3) ,tacacs(4)}
        MAX-ACCESS  read-write
        STATUS      current
        DESCRIPTION
            "Methods that involves remote servers are timed out if the
            remote servers are offline.Each method is tried from left to
            right and continues until a method either approves or
            rejects a user.
            0: no, Authentication is disabled and login is not possible.
            1: redirect, When HTTPS is enabled, enable HTTPS automatic redirect on the switch.
            2: local, Use the local user database on the switch for
            authentication.
            3: radius, Use remote RADIUS server(s) for authentication.
            4: tacacs+, Use remote TACACS+ server(s) for authentication."
        ::= {     sm24tat4xbAuthMethodConfigEntry 4 }

    sm24tat4xbAuthMethodConfigMethod4 OBJECT-TYPE
        SYNTAX      INTEGER {no(0) ,redirect(1) ,local(2) ,radius(3) ,tacacs(4)}
        MAX-ACCESS  read-write
        STATUS      current
        DESCRIPTION
            "Methods that involves remote servers are timed out if the
            remote servers are offline.Each method is tried from left to
            right and continues until a method either approves or
            rejects a user.
            0: no, Authentication is disabled and login is not possible.
            1: redirect, When HTTPS is enabled, enable HTTPS automatic redirect on the switch.
            2: local, Use the local user database on the switch for
            authentication.
            3: radius, Use remote RADIUS server(s) for authentication.
            4: tacacs+, Use remote TACACS+ server(s) for authentication."
        ::= {     sm24tat4xbAuthMethodConfigEntry 5 }

    sm24tat4xbAuthMethodConfigServicePort OBJECT-TYPE
        SYNTAX      Integer32 (1..65535)
        MAX-ACCESS  read-write
        STATUS      current
        DESCRIPTION
            "The network port number this client bound to provide service."
        ::= {     sm24tat4xbAuthMethodConfigEntry 6 }

    sm24tat4xbCommandAuthorizationMethodTable OBJECT-TYPE
        SYNTAX      SEQUENCE OF     SM24TAT4XBCommandAuthorizationMethodEntry
        MAX-ACCESS  not-accessible
        STATUS      current
        DESCRIPTION
            "The Command Authorized Method Config Table."
        ::= {     sm24tat4xbAuthMethod 2 }

    sm24tat4xbCommandAuthorizationMethodEntry OBJECT-TYPE
        SYNTAX      SM24TAT4XBCommandAuthorizationMethodEntry
        MAX-ACCESS  not-accessible
        STATUS      current
        DESCRIPTION
            "The Command Authorized Method Config Entry."
        INDEX    {    sm24tat4xbCommandAuthorizationMethodClient  }
        ::= {     sm24tat4xbCommandAuthorizationMethodTable 1 }

    SM24TAT4XBCommandAuthorizationMethodEntry         ::= SEQUENCE {
         sm24tat4xbCommandAuthorizationMethodClient    INTEGER,
         sm24tat4xbCommandAuthorizationMethodMethod    Integer32,
         sm24tat4xbCommandAuthorizationMethodCmdLvl    Integer32,
         sm24tat4xbCommandAuthorizationMethodCfgCmd    Integer32
         }

    sm24tat4xbCommandAuthorizationMethodClient OBJECT-TYPE
        SYNTAX      INTEGER  {  console ( 1 ),
                    telnet ( 2 ),
                    ssh ( 3 ),
                    http ( 4 ),
                    https ( 5 )
                    }
        MAX-ACCESS  not-accessible
        STATUS      current
        DESCRIPTION
            "1: console.
            2: telnet.
            3: ssh.
            4: http.
            5: https. "
        ::= {     sm24tat4xbCommandAuthorizationMethodEntry 1 }

    sm24tat4xbCommandAuthorizationMethodMethod OBJECT-TYPE
        SYNTAX      Integer32
        MAX-ACCESS  read-write
        STATUS      current
        DESCRIPTION
            "Method can be set to one of the following values:
            0:no: Command authorization is disabled.
					  User is granted access to CLI commands according to his privilege level.
            4:tacacs: Use remote TACACS+ server(s) for command authorization.
					  If all remote servers are offline, the user is granted access to CLI commands
					  according to his privilege level."
        ::= {     sm24tat4xbCommandAuthorizationMethodEntry 2 }

    sm24tat4xbCommandAuthorizationMethodCmdLvl OBJECT-TYPE
        SYNTAX      Integer32
        MAX-ACCESS  read-write
        STATUS      current
        DESCRIPTION
            "Authorize all commands with a privilege level higher than or equal to this level.
            Valid values are in the range 0 to 15."
        ::= {     sm24tat4xbCommandAuthorizationMethodEntry 3 }

    sm24tat4xbCommandAuthorizationMethodCfgCmd OBJECT-TYPE
        SYNTAX      Integer32
        MAX-ACCESS  read-write
        STATUS      current
        DESCRIPTION
            "Also authorize configuration commands.
				    0:Disable
				    1:Enable"
        ::= {     sm24tat4xbCommandAuthorizationMethodEntry 4 }


    sm24tat4xbAccountingMethodTable OBJECT-TYPE
        SYNTAX      SEQUENCE OF     SM24TAT4XBAccountingMethodEntry
        MAX-ACCESS  not-accessible
        STATUS      current
        DESCRIPTION
            "The Accounting Method Config Table."
        ::= {     sm24tat4xbAuthMethod 3 }

    sm24tat4xbAccountingMethodEntry OBJECT-TYPE
        SYNTAX      SM24TAT4XBAccountingMethodEntry
        MAX-ACCESS  not-accessible
        STATUS      current
        DESCRIPTION
            "The Accounting Method Config Entry."
        INDEX    {    sm24tat4xbAccountingMethodClient  }
        ::= {     sm24tat4xbAccountingMethodTable 1 }

    SM24TAT4XBAccountingMethodEntry         ::= SEQUENCE {
         sm24tat4xbAccountingMethodClient    INTEGER,
         sm24tat4xbAccountingMethodMethod    Integer32,
         sm24tat4xbAccountingMethodCmdLvl    Integer32,
         sm24tat4xbAccountingMethodCfgCmd    Integer32
         }

    sm24tat4xbAccountingMethodClient OBJECT-TYPE
        SYNTAX      INTEGER  {  console ( 1 ),
                    telnet ( 2 ),
                    ssh ( 3 ),
                    http ( 4 ),
                    https ( 5 )
                    }
        MAX-ACCESS  not-accessible
        STATUS      current
        DESCRIPTION
            "1: console.
            2: telnet.
            3: ssh.
            4: http.
            5: https. "
        ::= {     sm24tat4xbAccountingMethodEntry 1 }

    sm24tat4xbAccountingMethodMethod OBJECT-TYPE
        SYNTAX      Integer32
        MAX-ACCESS  read-write
        STATUS      current
        DESCRIPTION
            "Method can be set to one of the following values:
            0:no: Accounting is disabled.
            4:tacacs: Use remote TACACS+ server(s) for accounting."
        ::= {     sm24tat4xbAccountingMethodEntry 2 }

    sm24tat4xbAccountingMethodCmdLvl OBJECT-TYPE
        SYNTAX      Integer32
        MAX-ACCESS  read-write
        STATUS      current
        DESCRIPTION
            "Enable accounting of all commands with a privilege level higher than or equal to this level.
            Valid values are in the range 0 to 15. Leave the field empty to disable command accounting."
        ::= {     sm24tat4xbAccountingMethodEntry 3 }

    sm24tat4xbAccountingMethodCfgCmd OBJECT-TYPE
        SYNTAX      Integer32
        MAX-ACCESS  read-write
        STATUS      current
        DESCRIPTION
            "Enable exec (login) accounting.
				    0:Disable
				    1:Enable"
        ::= {     sm24tat4xbAccountingMethodEntry 4 }

-- sm24tat4xbTELNET                         OBJECT IDENTIFIER ::= { sm24tat4xbSecurity 10 }

-- sm24tat4xbTELNETPort OBJECT-TYPE
--    SYNTAX      Integer32(1..65535)
--    MAX-ACCESS  read-write
--    STATUS      current
--    DESCRIPTION
--    "TELNET service port number.
--    range : 1-65535, default : 23."
--    ::= { sm24tat4xbTELNET 1 }

-- =======================================================================================================================
sm24tat4xbMaintenance                        OBJECT IDENTIFIER ::= { sm24tat4xbProductId 4 }

sm24tat4xbSoftware              OBJECT IDENTIFIER    ::= {  sm24tat4xbMaintenance 3 }
sm24tat4xbConfig            OBJECT IDENTIFIER    ::= {  sm24tat4xbMaintenance 4 }

--
-- =======================================================================================================================
-- Objects in the sm24tat4xbMaintenance Group
-- =======================================================================================================================
    sm24tat4xbRestartDevice OBJECT-TYPE
        SYNTAX      ActivateCmd
        MAX-ACCESS  read-write
        STATUS      current
        DESCRIPTION
            "Command to restart the device."
        DEFVAL  { noAction }
        ::= {     sm24tat4xbMaintenance 1 }

    sm24tat4xbFactoryDefaults OBJECT-TYPE
        SYNTAX      ActivateCmd
        MAX-ACCESS  read-write
        STATUS      current
        DESCRIPTION
            "Reset the configuration to Factory Defaults keep-ip."
        DEFVAL  { noAction }
        ::= {     sm24tat4xbMaintenance 2 }

--sm24tat4xbSoftware

    sm24tat4xbSoftwareUsername OBJECT-TYPE
        SYNTAX    DisplayString
        MAX-ACCESS    read-write
        STATUS    current
        DESCRIPTION
            "Get/Set the username for 'tftp' firmware upgrading."
        ::= {     sm24tat4xbSoftware 1 }

    sm24tat4xbSoftwarePassword OBJECT-TYPE
        SYNTAX    DisplayString
        MAX-ACCESS    read-write
        STATUS    current
        DESCRIPTION
            "Get/Set the password for 'tftp' firmware upgrading."
        ::= {     sm24tat4xbSoftware 2 }

    sm24tat4xbSoftwareIpAddress OBJECT-TYPE
        SYNTAX    IpAddress
        MAX-ACCESS    read-write
        STATUS    current
        DESCRIPTION
            "Get/Set the firmware tftp server."
        ::= {     sm24tat4xbSoftware 3 }

    sm24tat4xbSoftwareFileName OBJECT-TYPE
        SYNTAX    DisplayString
        MAX-ACCESS    read-write
        STATUS    current
        DESCRIPTION
            "Get/Set the path and filename for firmware upgrading."
        ::= {     sm24tat4xbSoftware 4 }

    sm24tat4xbSoftwareUpgradeCmd OBJECT-TYPE
        SYNTAX    INTEGER  {  noAction ( 0 ),
                    tftpUpgrade ( 1 ),
                    ftpUpgrade ( 2 )
                     }
        MAX-ACCESS    read-write
        STATUS    current
        DESCRIPTION
            "Firmware upgrade command.
             noAction(0 )- do nothing    (read only).
             tftpUpgrade (1) - activate 'tftp' firmware upgrade"

        DEFVAL  { noAction }
        ::= {     sm24tat4xbSoftware 5 }

    sm24tat4xbSoftwareImageSelectionCmd OBJECT-TYPE
        SYNTAX    ActivateCmd
        MAX-ACCESS    read-write
        STATUS    current
        DESCRIPTION
            "Activate firmware image selection.
             noAction(0) - do nothing - returned upon get.
             activate(1) - activate firmware image selection."
        DEFVAL  { noAction }
        ::= {     sm24tat4xbSoftware 6 }

    sm24tat4xbSaveStartCmd OBJECT-TYPE
        SYNTAX      ActivateCmd
        MAX-ACCESS  read-write
        STATUS      current
        DESCRIPTION
            "This copies running-config to startup-config,
            thereby ensuring that the currently active
            configuration will be used at the next reboot. "
        DEFVAL  { noAction }
        ::= {     sm24tat4xbConfig 1 }

    sm24tat4xbConfigUsername OBJECT-TYPE
        SYNTAX    DisplayString
        MAX-ACCESS    read-write
        STATUS    current
        DESCRIPTION
            "Get/Set the username for 'tftp' 'upload config' or 'download config'."
        ::= {     sm24tat4xbConfig 2 }

    sm24tat4xbConfigPassword OBJECT-TYPE
        SYNTAX    DisplayString
        MAX-ACCESS    read-write
        STATUS    current
        DESCRIPTION
            "Get/Set the password for 'tftp' 'upload config' or 'download config'."
        ::= {     sm24tat4xbConfig 3 }

    sm24tat4xbConfigIpAddress OBJECT-TYPE
        SYNTAX    IpAddress
        MAX-ACCESS    read-write
        STATUS    current
        DESCRIPTION
            "Get/Set the IP address for 'tftp' 'upload config'
            or 'download config'."
        ::= {     sm24tat4xbConfig 4 }

    sm24tat4xbConfigFilename OBJECT-TYPE
        SYNTAX    DisplayString
        MAX-ACCESS    read-write
        STATUS    current
        DESCRIPTION
            "Get/Set the filename in switch for 'tftp'
            'upload config' or 'download config'."
        ::= {     sm24tat4xbConfig 5 }

    sm24tat4xbConfigFileTable OBJECT-TYPE
        SYNTAX      SEQUENCE OF     SM24TAT4XBConfigFileEntry
        MAX-ACCESS  not-accessible
        STATUS      current
        DESCRIPTION
            "The config file tabe."
        ::= {     sm24tat4xbConfig 6 }

    sm24tat4xbConfigFileEntry OBJECT-TYPE
        SYNTAX      SM24TAT4XBConfigFileEntry
        MAX-ACCESS  not-accessible
        STATUS      current
        DESCRIPTION
            "an entry in the config file tabe."
        INDEX    {     sm24tat4xbConfigFileIndex }
        ::= {     sm24tat4xbConfigFileTable 1 }

    SM24TAT4XBConfigFileEntry         ::= SEQUENCE {
        sm24tat4xbConfigFileIndex     Integer32,
        sm24tat4xbShowConfigFileName      DisplayString,
        sm24tat4xbActivateConfigCmd    ActivateCmd,
        sm24tat4xbDeleteConfigCmd     ActivateCmd,
        sm24tat4xbUploadConfigCmd     INTEGER,
        sm24tat4xbDownloadConfigCmd    INTEGER
        }

    sm24tat4xbConfigFileIndex OBJECT-TYPE
        SYNTAX      Integer32(1..255)
        MAX-ACCESS  not-accessible
        STATUS      current
        DESCRIPTION
            "The config file index."
        ::= {     sm24tat4xbConfigFileEntry 1 }

    sm24tat4xbShowConfigFileName OBJECT-TYPE
        SYNTAX      DisplayString
        MAX-ACCESS  read-write
        STATUS      current
        DESCRIPTION
            "Shows the config file name. Without config filename:'NewConfig'
            is temp file when 'activate download
            config' can 'create new file' and 'change create filename'."
        ::= {     sm24tat4xbConfigFileEntry 2 }

    sm24tat4xbActivateConfigCmd OBJECT-TYPE
        SYNTAX    ActivateCmd
        MAX-ACCESS    read-write
        STATUS    current
        DESCRIPTION
            "Activate config command.
             noAction(0) : do nothing  (read only).
             activate(1) : activate the config"
        DEFVAL  { noAction }
        ::= {     sm24tat4xbConfigFileEntry 3 }

    sm24tat4xbDeleteConfigCmd OBJECT-TYPE
        SYNTAX    ActivateCmd
        MAX-ACCESS    read-write
        STATUS    current
        DESCRIPTION
            "Delete config command.
             noAction(0) : do nothing  (read only).
             activate(1) : delete the config"
        DEFVAL  { noAction }
        ::= {     sm24tat4xbConfigFileEntry 4 }

    sm24tat4xbDownloadConfigCmd OBJECT-TYPE
        SYNTAX    INTEGER  {  noAction ( 0 ),
                    tftpUpload ( 1 )
                    --ftpUpload ( 2 )
                     }
        MAX-ACCESS    read-write
        STATUS    current
        DESCRIPTION
            "Download config command.
             noAction    (0) - do nothing    (read only).
             tftpUpload (1) - activate 'tftp' config download."
        DEFVAL  { noAction }
        ::= {     sm24tat4xbConfigFileEntry 5 }

    sm24tat4xbUploadConfigCmd OBJECT-TYPE
        SYNTAX    INTEGER  {  noAction ( 0 ),
                    tftpDownload ( 1 )
                    --ftpDownload ( 2 )
                     }
        MAX-ACCESS    read-write
        STATUS    current
        DESCRIPTION
            "Upload config command.
             noAction    (0) - do nothing    (read only).
             tftpDownload (1) - activate 'tftp' config upload.
					 For merge/replace running-config:
					 1:merge
					 3:replace"
        DEFVAL  { noAction }
        ::= {     sm24tat4xbConfigFileEntry 6 }

-- =======================================================================================================================
sm24tat4xbDiagnostics                        OBJECT IDENTIFIER ::= { sm24tat4xbMaintenance 5 }

sm24tat4xbPingIpAddress OBJECT-TYPE
    SYNTAX      IpAddress
    MAX-ACCESS  read-write
    STATUS      current
    DESCRIPTION
        " The destination IP Address. "
    ::= { sm24tat4xbDiagnostics 1 }

sm24tat4xbPingSize OBJECT-TYPE
    SYNTAX      Integer32(60..1400)
    MAX-ACCESS  read-write
    STATUS      current
    DESCRIPTION
        " Size of ICMP echo packet.
     range : 60-1400, default : 64. "
    ::= { sm24tat4xbDiagnostics 2 }

sm24tat4xbDoPingConfig OBJECT-TYPE
    SYNTAX      Integer32(1)
    MAX-ACCESS  read-write
    STATUS      current
    DESCRIPTION
        "Do ping-config.
        Get this OID always return zero.
        1 - ping. Uses the ICMP protocol's mandatory ECHO_REQUEST datagram
        to elicit an ICMP ECHO_RESPONSE from a host or gateway. "
    ::= { sm24tat4xbDiagnostics 3 }

sm24tat4xbPingResult OBJECT-TYPE
    SYNTAX      DisplayString
    MAX-ACCESS  read-only
    STATUS      current
    DESCRIPTION
        " Show ping result. "
    ::= { sm24tat4xbDiagnostics 4 }

sm24tat4xbPing6IpAddress OBJECT-TYPE
    SYNTAX      DisplayString
    MAX-ACCESS  read-write
    STATUS      current
    DESCRIPTION
        " The destination IPv6 Address. "
    ::= { sm24tat4xbDiagnostics 5 }

sm24tat4xbPing6Size OBJECT-TYPE
    SYNTAX      Integer32(60..1400)
    MAX-ACCESS  read-write
    STATUS      current
    DESCRIPTION
        " Size of ICMP echo packet.
     range : 60-1400. "
    ::= { sm24tat4xbDiagnostics 6 }

sm24tat4xbPing6EgressInterface OBJECT-TYPE
    SYNTAX      Integer32(1..4095)
    MAX-ACCESS  read-write
    STATUS      current
    DESCRIPTION
        "The VLAN ID (VID) of the specific egress IPv6 interface which ICMP packet goes."
    ::= { sm24tat4xbDiagnostics 7 }

sm24tat4xbDoPing6Config OBJECT-TYPE
    SYNTAX      Integer32(1)
    MAX-ACCESS  read-write
    STATUS      current
    DESCRIPTION
        "Do ping-config.
        Get this OID always return zero.
        1 - ping. Uses the ICMP protocol's mandatory ECHO_REQUEST datagram
        to elicit an ICMP ECHO_RESPONSE from a host or gateway. "
    ::= { sm24tat4xbDiagnostics 8 }

sm24tat4xbPing6Result OBJECT-TYPE
    SYNTAX      DisplayString
    MAX-ACCESS  read-only
    STATUS      current
    DESCRIPTION
        " Show ping result. "
    ::= { sm24tat4xbDiagnostics 9 }

sm24tat4xbtracerouteIpAddress OBJECT-TYPE
    SYNTAX      IpAddress
    MAX-ACCESS  read-write
    STATUS      current
    DESCRIPTION
        " The destination IP Address. "
    ::= { sm24tat4xbDiagnostics 10 }

--sm24tat4xbtracerouteProtocol OBJECT-TYPE
--    SYNTAX      Integer32(0..2)
--    MAX-ACCESS  read-write
--    STATUS      current
--    DESCRIPTION
--    " Specify protocol including icmp=0, udp=1 and tcp=2.
--     range : 0-2, default : 0. "
--    ::= { sm24tat4xbDiagnostics 11 }

sm24tat4xbtracerouteWaittime OBJECT-TYPE
    SYNTAX      Integer32(1..60)
    MAX-ACCESS  read-write
    STATUS      current
    DESCRIPTION
        " Specify wait time for waiting probe packets come back.
        range : 1-60(sec), default : 5(sec). "
    ::= { sm24tat4xbDiagnostics 12 }

sm24tat4xbtracerouteMaxTTL OBJECT-TYPE
    SYNTAX      Integer32(1..255)
    MAX-ACCESS  read-write
    STATUS      current
    DESCRIPTION
        " Specify max TTL.
        range : 1-255, default : 30. "
    ::= { sm24tat4xbDiagnostics 13 }

sm24tat4xbtracerouteNqueries OBJECT-TYPE
    SYNTAX      Integer32(1..10)
    MAX-ACCESS  read-write
    STATUS      current
    DESCRIPTION
        " Specify number of probe packets.
        range : 1-10, default : 3. "
    ::= { sm24tat4xbDiagnostics 14 }

sm24tat4xbDotracerouteConfig OBJECT-TYPE
    SYNTAX      Integer32(1)
    MAX-ACCESS  read-write
    STATUS      current
    DESCRIPTION
        "Do traceroute-config.
        Get this OID always return zero.
        1 - ping. Uses the traceroute program to get
        ip address of the middle gateway. "
    ::= { sm24tat4xbDiagnostics 15 }

sm24tat4xbtracerouteResult OBJECT-TYPE
    SYNTAX      DisplayString
    MAX-ACCESS  read-only
    STATUS      current
    DESCRIPTION
        " Show traceroute result. "
    ::= { sm24tat4xbDiagnostics 16 }

sm24tat4xbCableDiagnostics                        OBJECT IDENTIFIER ::= { sm24tat4xbDiagnostics 17 }

sm24tat4xbCableDiagnosticsTest OBJECT-TYPE
    SYNTAX      Integer32
    MAX-ACCESS  read-write
    STATUS      current
    DESCRIPTION
        "Run Cable Diagnostics.
        port, range : 1 - port number."
    ::= { sm24tat4xbCableDiagnostics 1 }

sm24tat4xbCableDiagnosticsTable OBJECT-TYPE
    SYNTAX      SEQUENCE OF SM24TAT4XBCableDiagnosticsEntry
    MAX-ACCESS  not-accessible
    STATUS      current
    DESCRIPTION
        " "
    ::= { sm24tat4xbCableDiagnostics 2 }

sm24tat4xbCableDiagnosticsEntry OBJECT-TYPE
    SYNTAX      SM24TAT4XBCableDiagnosticsEntry
    MAX-ACCESS  not-accessible
    STATUS      current
    DESCRIPTION
        " "
    INDEX    { sm24tat4xbCableDiagnosticsPort  }
    ::= { sm24tat4xbCableDiagnosticsTable 1 }

SM24TAT4XBCableDiagnosticsEntry ::= SEQUENCE {
    sm24tat4xbCableDiagnosticsPort    Integer32,
    sm24tat4xbCableDiagnosticsLinkStatus  DisplayString,
    sm24tat4xbCableDiagnosticsTestResult  DisplayString,
    sm24tat4xbCableDiagnosticsLength      DisplayString
}

sm24tat4xbCableDiagnosticsPort OBJECT-TYPE
    SYNTAX      Integer32(1..65535)
    MAX-ACCESS  not-accessible
    STATUS      current
    DESCRIPTION
        "port index"
    ::= { sm24tat4xbCableDiagnosticsEntry 1 }

sm24tat4xbCableDiagnosticsLinkStatus OBJECT-TYPE
    SYNTAX      DisplayString
    MAX-ACCESS  read-only
    STATUS      current
    DESCRIPTION
        "The status of the cable."
    ::= { sm24tat4xbCableDiagnosticsEntry 2 }

sm24tat4xbCableDiagnosticsTestResult OBJECT-TYPE
    SYNTAX      DisplayString
    MAX-ACCESS  read-only
    STATUS      current
    DESCRIPTION
        "Test Result of the cable."
    ::= { sm24tat4xbCableDiagnosticsEntry 3 }

sm24tat4xbCableDiagnosticsLength OBJECT-TYPE
    SYNTAX      DisplayString
    MAX-ACCESS  read-only
    STATUS      current
    DESCRIPTION
        "The length (in meters) of the cable."
    ::= { sm24tat4xbCableDiagnosticsEntry 4 }

sm24tat4xbSwitchRebootSchedule OBJECT IDENTIFIER ::= { sm24tat4xbMaintenance 6 }

sm24tat4xbSwitchRebootMode OBJECT-TYPE
    SYNTAX      Integer32
    MAX-ACCESS  read-write
    STATUS      current
    DESCRIPTION
        "Switch Reboot Mode.
	    0:disable
		1:enable"
    ::= { sm24tat4xbSwitchRebootSchedule 1 }

sm24tat4xbSwitchRebootTimeTable OBJECT-TYPE
    SYNTAX      SEQUENCE OF SM24TAT4XBSwitchRebootTimeEntry
    MAX-ACCESS  not-accessible
    STATUS      current
    DESCRIPTION
        " Configure the Switch reboot time. "
    ::= { sm24tat4xbSwitchRebootSchedule 2 }

sm24tat4xbSwitchRebootTimeEntry OBJECT-TYPE
    SYNTAX      SM24TAT4XBSwitchRebootTimeEntry
    MAX-ACCESS  not-accessible
    STATUS      current
    DESCRIPTION
        " "
    INDEX    { sm24tat4xbSwitchRebootWeekIndex  }
    ::= { sm24tat4xbSwitchRebootTimeTable 1 }

SM24TAT4XBSwitchRebootTimeEntry ::= SEQUENCE {
    sm24tat4xbSwitchRebootWeekIndex	    Integer32,
    sm24tat4xbSwitchRebootTimeHour        Integer32,
    sm24tat4xbSwitchRebootTimeMinute     Integer32
}

sm24tat4xbSwitchRebootWeekIndex OBJECT-TYPE
    SYNTAX      Integer32 (1..7)
    MAX-ACCESS  not-accessible
    STATUS      current
    DESCRIPTION
        "Switch reboot week index.
	    1: Sun, 2: Mon, 3:Tue, 4: Wed, 5: Thu, 6: Fri, 7: Sat"
    ::= { sm24tat4xbSwitchRebootTimeEntry 1 }

sm24tat4xbSwitchRebootTimeHour OBJECT-TYPE
    SYNTAX      Integer32 (-1..23)
    MAX-ACCESS  read-write
    STATUS      current
    DESCRIPTION
        "Switch Reboot Time (Hour). Range: 0-23.
	    -1:disable"
    ::= { sm24tat4xbSwitchRebootTimeEntry 2 }

sm24tat4xbSwitchRebootTimeMinute OBJECT-TYPE
    SYNTAX      Integer32 (-1..55)
    MAX-ACCESS  read-write
    STATUS      current
    DESCRIPTION
        "Switch Reboot Time (Minute). Range:0,5,10,...,55.
	    -1:disable"
    ::= { sm24tat4xbSwitchRebootTimeEntry 3 }

sm24tat4xbiPerf OBJECT IDENTIFIER ::= { sm24tat4xbMaintenance 7 }

sm24tat4xbiPerfMethod OBJECT-TYPE
    SYNTAX      Integer32
    MAX-ACCESS  read-write
    STATUS      current
    DESCRIPTION
        "The measuring method of iPerf.
	    2:iPerf version 2
		3:iPerf version 3"
    ::= { sm24tat4xbiPerf 2 }

sm24tat4xbiPerfHost OBJECT-TYPE
    SYNTAX      IpAddress
    MAX-ACCESS  read-write
    STATUS      current
    DESCRIPTION
        "The address of iPerf server. "
    ::= { sm24tat4xbiPerf 3 }

sm24tat4xbiPerfPort OBJECT-TYPE
    SYNTAX      Integer32
    MAX-ACCESS  read-write
    STATUS      current
    DESCRIPTION
        "The listen port of iPerf server. The default value is 5001 for iPerf, 5201 for iPerf3. "
    ::= { sm24tat4xbiPerf 4 }

sm24tat4xbiPerfTime OBJECT-TYPE
    SYNTAX      Integer32
    MAX-ACCESS  read-write
    STATUS      current
    DESCRIPTION
        "The time in seconds to transmit for (default 10 secs). "
    ::= { sm24tat4xbiPerf 5 }

sm24tat4xbiPerfInterval OBJECT-TYPE
    SYNTAX      Integer32
    MAX-ACCESS  read-write
    STATUS      current
    DESCRIPTION
        "The time in seconds between periodic bandwidth reports (default no periodic reports). "
    ::= { sm24tat4xbiPerf 6 }

sm24tat4xbiPerfTTL OBJECT-TYPE
    SYNTAX      Integer32
    MAX-ACCESS  read-write
    STATUS      current
    DESCRIPTION
        "The time-to-live, for multicast (default 1). "
    ::= { sm24tat4xbiPerf 7 }

sm24tat4xbiPerfStart OBJECT-TYPE
    SYNTAX      Integer32
    MAX-ACCESS  read-write
    STATUS      current
    DESCRIPTION
        "Start iPerf
	    1:Start."
    ::= { sm24tat4xbiPerf 8 }

sm24tat4xbiPerfResult OBJECT-TYPE
    SYNTAX      DisplayString
    MAX-ACCESS  read-only
    STATUS      current
    DESCRIPTION
        "Test result of iPerf"
    ::= { sm24tat4xbiPerf 9 }

-- =======================================================================================================================
sm24tat4xbTrap                          OBJECT IDENTIFIER ::= { sm24tat4xbProductId 5 }

sm24tat4xbTrapEvent                         OBJECT IDENTIFIER ::= { sm24tat4xbTrap 1 }

sm24tat4xbEmergency NOTIFICATION-TYPE
  OBJECTS    { sm24tat4xbInformation }
  STATUS    current
    DESCRIPTION
        "The severity level is Emergency. Emergency conditions."
    ::= { sm24tat4xbTrapEvent 1 }

sm24tat4xbAlert NOTIFICATION-TYPE
  OBJECTS    { sm24tat4xbInformation }
  STATUS    current
    DESCRIPTION
        "The severity level is Alert. Alert conditions."
    ::= { sm24tat4xbTrapEvent 2 }

sm24tat4xbCritical NOTIFICATION-TYPE
  OBJECTS    { sm24tat4xbInformation }
  STATUS    current
    DESCRIPTION
        "The severity level is Critical. Critical conditions."
    ::= { sm24tat4xbTrapEvent 3 }

sm24tat4xbError NOTIFICATION-TYPE
  OBJECTS    { sm24tat4xbInformation }
  STATUS    current
    DESCRIPTION
        "The severity level is Error. Error conditions."
    ::= { sm24tat4xbTrapEvent 4 }

sm24tat4xbWarning NOTIFICATION-TYPE
  OBJECTS    { sm24tat4xbInformation }
  STATUS    current
    DESCRIPTION
        "The severity level is Warning. Warning conditions."
    ::= { sm24tat4xbTrapEvent 5 }

sm24tat4xbNotice NOTIFICATION-TYPE
  OBJECTS    { sm24tat4xbInformation }
  STATUS    current
    DESCRIPTION
        "The severity level is Notice. Notice conditions."
    ::= { sm24tat4xbTrapEvent 6 }

sm24tat4xbInformational NOTIFICATION-TYPE
  OBJECTS    { sm24tat4xbInformation }
  STATUS    current
    DESCRIPTION
        "The severity level is Informational. Informational conditions."
    ::= { sm24tat4xbTrapEvent 7 }

sm24tat4xbDebug NOTIFICATION-TYPE
  OBJECTS    { sm24tat4xbInformation }
  STATUS    current
    DESCRIPTION
        "The severity level is Debug. Debug conditions."
    ::= { sm24tat4xbTrapEvent 8 }

sm24tat4xbTrapVariable                      OBJECT IDENTIFIER ::= { sm24tat4xbTrap 2 }

sm24tat4xbInformation OBJECT-TYPE
    SYNTAX      DisplayString
    MAX-ACCESS  read-only
    STATUS      current
    DESCRIPTION
        "Trap information."
    ::= { sm24tat4xbTrapVariable 1 }

sm24tat4xbZTPTrap                         OBJECT IDENTIFIER ::= { sm24tat4xbTrap 3 }

sm24tat4xbZTPTrapEvent                    OBJECT IDENTIFIER ::= { sm24tat4xbZTPTrap 0 }

sm24tat4xbZTPOnboardTrap NOTIFICATION-TYPE
  OBJECTS    { sysObjectID, sm24tat4xbSnmpSystemVersion, sm24tat4xbSnmpSystemReadCommunity,
          sm24tat4xbSnmpSystemWriteCommunity, sm24tat4xbSystemInfoSeriesNumber,
          sm24tat4xbSystemInfoHostMACAddress, sm24tat4xbIPInterfacesIPv4Address }
  STATUS    current
    DESCRIPTION
        "The switch information."
    ::= { sm24tat4xbZTPTrapEvent 1 }

END
